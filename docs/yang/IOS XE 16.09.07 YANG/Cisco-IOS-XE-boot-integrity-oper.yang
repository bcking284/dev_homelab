module Cisco-IOS-XE-boot-integrity-oper {
  yang-version 1;
  namespace "http://cisco.com/ns/yang/Cisco-IOS-XE-boot-integrity-oper";
  prefix boot-integrity-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Cisco IOS XE boot integrity visibility.
     Copyright (c) 2018 by Cisco Systems, Inc.
     All rights reserved.";

  revision 2018-01-31 {
    description
      "Initial revision";
    reference "1.0.0";
  }

  grouping pcr-register {
    description
      "List for maintaining the Platform Content
       Register (PCR) indices and content";
    leaf index {
      type uint8;
      description
        "References PCR Register Index";
    }
    leaf pcr-content {
      type string;
      description
        "References PCR Register Content";
    }
  }

  grouping package-signature {
    description
      "List for maintaining system-calculated hashes for each
       of the packages installed or patched to the system";
    leaf name {
      type string;
      description
        "Package Name";
    }
    leaf hash {
      type string;
      description
        "Package Hash";
    }
  }

  grouping boot-integrity {
    description
      "System Boot Integrity Measurements";
    leaf platform {
      type string;
      description
        "Product Identifier";
    }
    leaf boot-ver {
      type string;
      description
        "Boot 0 Version";
    }
    leaf boot-loader-ver {
      type string;
      description
        "Boot Loader Version";
    }
    leaf os-version {
      type string;
      description
        "Operating System Version";
    }
    leaf boot-hash {
      type string;
      description
        "Boot 0 Hash";
    }
    leaf boot-loader-hash {
      type string;
      description
        "Boot Loader Hash";
    }
    leaf os-hash {
      type string;
      description
        "Operating System Hash";
    }
    leaf package-count {
      type uint8;
      description
        "Number of Active Packages";
    }
    list pcr-register {
      key "index";
      description
        "System Platform Configuration Registers";
      uses boot-integrity-ios-xe-oper:pcr-register;
    }
    list package-signature {
      key "name";
      description
        "System Package Signatures";
      uses boot-integrity-ios-xe-oper:package-signature;
    }
    leaf signature {
      type string;
      description
        "System ACT2 PCR Quote Signed Signature";
    }
    leaf sig-version {
      type uint32;
      description
        "System ACT2 PCR Quote Signature Version";
    }
  }

  grouping sudi-certificate {
    description
      "System Secure Unique Device Identifier Certificate
       Chain Measurements ";
    leaf crca-pem {
      type string;
      description
        "Cisco Root CA PEM Certficate";
    }
    leaf cmca-pem {
      type string;
      description
        "Cisco Manufacturing CA PEM Certficate";
    }
    leaf sudi-pem {
      type string;
      description
        "ACT2 RSA SUDI CA PEM Certficate";
    }
    leaf sudi-signature {
      type string;
      description
        "ACT2 RSA SUDI Certificate Generated Signature";
    }
  }

  container boot-integrity-oper-data {
    config false;
    description
      "Enclosing container for the boot integrity 
       measurements of the system";
    container boot-integrity {
      presence "boot-integrity";
      description
        "List of system boot integrity measurements for Boot, 
         Boot Loader, and OS versions, hashes, and signatures
         as well as Platform Configuration Registers (PCR) content.
         These measurements are captured utilizing Trusted Anchor Module (TAM)
         services to communicate with system ACT2 
         (2nd Gen Anti-Counterfeit Technology) hardware chip.";
      uses boot-integrity-ios-xe-oper:boot-integrity;
    }
    container sudi-certificate {
      presence "sudi-certificate";
      description
        "List of system  certificate measurements for Cisco Root CA (CRCA),
         Cisco Manufacturing CA (CMCA), and ACT2 RSA Secure Unique Device 
         Identity (SUDI) CA PEM certifcates and SUDI generated signatures.
         These measurements are captured utilizing Trusted Anchor Module (TAM)
         services to communicate with system ACT2 
         (2nd Gen Anti-Counterfeit Technology) hardware chip.";
      uses boot-integrity-ios-xe-oper:sudi-certificate;
    }
  }
}
