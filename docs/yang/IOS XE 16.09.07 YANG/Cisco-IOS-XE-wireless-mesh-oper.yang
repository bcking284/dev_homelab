module Cisco-IOS-XE-wireless-mesh-oper {
  yang-version 1;
  namespace "http://cisco.com/ns/yang/Cisco-IOS-XE-wireless-mesh-oper";
  prefix wireless-mesh-oper;

  import Cisco-IOS-XE-wireless-types {
    prefix wireless-types;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Wireless Mesh Operational Data
     Copyright (c) 2016-2018 by Cisco Systems, Inc.
     All rights reserved.";

  revision 2018-05-01 {
    description
      "- Change type of bhaul-tx-rate in st-mesh-ap-oper-data from uint32 to mesh-dot11abg-data-rate
       - Added new data to st-mesh-ap-oper-data
       - Change type of data-rate in mesh-link-test-config from uint16 to mesh-linktest-rate
       - Added data-rate-index to mesh-link-test-config";
    reference "3.0.0";
  }
  revision 2018-01-24 {
    description
      "The first generally available version";
    reference "2.0.0";
  }
  revision 2017-09-25 {
    description
      "Initial revision";
    reference "1.0.0";
  }

  grouping st-mesh-node-pkt-queue-stats {
    description
      "Represents the packet stats for different queues in AP radio";
    leaf peak-length {
      type uint16;
      description
        "Represents the peak number of packets waiting in the queue";
    }
    leaf average-len {
      type uint16;
      description
        "Represents the average number of packets waiting in the queue";
    }
    leaf overflows {
      type uint16;
      description
        "Represents the total number of packets dropped due to queue overflow";
    }
  }

  grouping st-mesh-node-pkt-queue-stats-key {
    description
      "Represents the key for packet queue stats table";
    leaf wtp-mac {
      type yang:mac-address;
      description
        "Represents the radio MAC address common to the dot11 interface of the AP";
    }
    leaf q-type {
      type wireless-types:mesh-node-pkt-queue-type;
      description
        "Represents the queue type on the AP radio";
    }
  }

  grouping st-mesh-node-data-rate-stats {
    description
      "Represents the statistics information about a mesh node for different data rates";
    leaf tx-success {
      type uint32;
      description
        "Represents the total number of packets successfully transmitted at a given data rate";
    }
    leaf tx-attempts {
      type uint32;
      description
        "Represents the total number of transmitted attempts at a given data rate";
    }
  }

  grouping st-mesh-node-data-rate-stats-key {
    description
      "Represents the key for data rate statistics table";
    leaf wtp-mac {
      type yang:mac-address;
      description
        "Represents the radio MAC address common to the dot11 interface of the AP";
    }
    leaf neigh-ap-mac {
      type yang:mac-address;
      description
        "Represents the radio MAC address of neighbor Access Point";
    }
    leaf data-rate-index {
      type uint32;
      description
        "Represents the supported data rates of the mesh access point";
    }
  }

  grouping st-mesh-ap-security-stats-parent {
    description
      "Represents the security stats at the parent Mesh Access Point";
    leaf unknown-assoc-req {
      type uint32;
      description
        "Represents the total number of unknown association request received by this node, as a parent mesh node from a child mesh node";
    }
    leaf invalid-assoc-req {
      type uint32;
      description
        "Represents the total number of invalid association request received by this node, as a parent mesh node from a child mesh node";
    }
    leaf unknown-tgr-auth-req {
      type uint32;
      description
        "Represents the total number of unknown TGR Auth request received by this node, as a parent mesh node from a child mesh node";
    }
    leaf invalid-tgr-auth-req {
      type uint32;
      description
        "Represents the total number of invalid TGR Auth request received by this node, as a parent mesh node from a child mesh node";
    }
    leaf unknown-tgr-reassoc-req {
      type uint32;
      description
        "Represents the total number of unknown TGR re-association request received by this node, as a parent mesh node from a child mesh node";
    }
    leaf invalid-tgr-reassoc-req {
      type uint32;
      description
        "Represents the total number of invalid TGR re-association request received by this node, as a parent mesh node from a child mesh node";
    }
  }

  grouping st-mesh-ap-security-stats-child {
    description
      "Represents the security stats at the Child Mesh Access Point";
    leaf assoc-failure {
      type uint32;
      description
        "Represents total number of association request sent by a child mesh node to a parent mesh node, that resulted in a failure";
    }
    leaf assoc-timeout {
      type uint32;
      description
        "Represents total number of association request sent by a child mesh node to a parent mesh node, that timed out";
    }
    leaf assoc-success {
      type uint32;
      description
        "Represents total number of association request sent by a child mesh node to a parent mesh node, that completed";
    }
    leaf auth-failure {
      type uint32;
      description
        "Represents total number of authentication request sent by a child mesh node to a parent mesh node, that resulted in a failure";
    }
    leaf auth-timeout {
      type uint32;
      description
        "Represents total number of authentication request sent by a child mesh node to a parent mesh node, that timed out";
    }
    leaf auth-success {
      type uint32;
      description
        "Represents total number of authentication request sent by a child mesh node to a parent mesh node, that completed";
    }
    leaf tgr-auth-failure {
      type uint32;
      description
        "Represents total number of TGR authentication request sent by a child mesh node to a parent mesh node, that resulted in a failure";
    }
    leaf tgr-auth-timeout {
      type uint32;
      description
        "Represents total number of TGR authentication request sent by a child mesh node to a parent mesh node, that timed out";
    }
    leaf tgr-auth-success {
      type uint32;
      description
        "Represents total number of TGR authentication request sent by a child mesh node to a parent mesh node, that completed";
    }
    leaf tgr-reassoc-failure {
      type uint32;
      description
        "Represents total number of TGR re-association request sent by a child mesh node to a parent mesh node, that resulted in a failure";
    }
    leaf tgr-reassoc-timeout {
      type uint32;
      description
        "Represents total number of TGR re-association request sent by a child mesh node to a parent mesh node, that timed out";
    }
    leaf tgr-reassoc-success {
      type uint32;
      description
        "Represents total number of TGR re-association request sent by a child mesh node to a parent mesh node, that completed";
    }
  }

  grouping st-mesh-ap-security-stats {
    description
      "Represents the security stats at Mesh Access Point";
    leaf wtp-mac {
      type yang:mac-address;
      description
        "Represents the radio MAC address common to the dot11 interface of the AP";
    }
    leaf tx-pkts-total {
      type uint32;
      description
        "Represents the total number of packets transmitted by this mesh node during security negotiation";
    }
    leaf rx-pkts-total {
      type uint32;
      description
        "Represents the total number of packets received by this mesh node during security negotiation";
    }
    leaf rx-pkts-error {
      type uint32;
      description
        "Represents the total number of packets received with error by this mesh node during security negotiation";
    }
    container stats-parent {
      description
        "Represents the security stats at the parent Mesh Access Point";
      uses wireless-mesh-oper:st-mesh-ap-security-stats-parent;
    }
    container stats-child {
      description
        "Represents the security stats at the Child Mesh Access Point";
      uses wireless-mesh-oper:st-mesh-ap-security-stats-child;
    }
  }

  grouping st-mesh-ap-oper-data {
    description
      "Represents the operational data for a Mesh Access Point";
    leaf wtp-mac {
      type yang:mac-address;
      description
        "Represents the radio MAC address common to the dot11 interface of the AP";
    }
    leaf previous-role {
      type wireless-types:ap-role;
      description
        "Represents the previous AP role for this Mesh Access Point";
    }
    leaf configured-role {
      type wireless-types:ap-role;
      description
        "Represents the configured AP role for this Mesh Access Point";
    }
    leaf bhaul-radio-mode {
      type wireless-types:mesh-bhaul-mode;
      description
        "Represents the Backhaul Radio mode (11a, 11b, 11g) on this Access Point";
    }
    leaf ap-mode {
      type wireless-types:enm-ewlc-spam-ap-modes;
      description
        "Represents the AP mode for this Mesh Access Point";
    }
    leaf ap-role {
      type wireless-types:ap-role;
      description
        "Represents the AP role for this Mesh Access Point";
    }
    leaf bhaul-mask {
      type uint32;
      description
        "Represents the mask slotId to determine the backhaul slots";
    }
    leaf bhaul-mask-shutdown {
      type uint32;
      description
        "Represents the mask slotId to determine the backhaul slots shutdown";
    }
    leaf bhaul-mask-uplink {
      type uint32;
      description
        "Represents the mask slotId to determine the backhaul uplink slots";
    }
    leaf bhaul-mask-downlink {
      type uint32;
      description
        "Represents the mask slotId to determine the backhaul downlink slots";
    }
    leaf bhaul-mask-access {
      type uint32;
      description
        "Represents the mask slotId to determine the backhaul access slots";
    }
    leaf bhaul-radio-type {
      type wireless-types:mesh-bhaul-radio-type;
      description
        "Represents the Mesh Backhaul Radio type(802.11a, 802.11bg) on this Access Point";
    }
    leaf bhaul-slot-id {
      type uint8;
      description
        "Represents the Backhaul Radio slot identifier used by this Access Point";
    }
    leaf bhaul-data-rate-type {
      type wireless-types:mesh-bhaul-data-rate-type;
      description
        "Represents the Mesh Backhaul data rate type(auto, 802.11a, 802.11bg, 11n mcs, 11ac) on this Access Point";
    }
    leaf ap-specific-bhaul-tx-rate {
      type boolean;
      description
        "Represents if AP specific Backhaul data rate by this Access Point";
    }
    leaf bhaul-tx-rate {
      type wireless-types:mesh-dot11abg-data-rate;
      description
        "Represents the data rate used in the Backhaul Radio interface of this Access Point";
    }
    leaf bhaul-rate-mcs-index {
      type uint32;
      description
        "Represents the Mesh Backhaul mcs data rate index";
    }
    leaf bhaul-rate-mcs-ss {
      type uint8;
      description
        "Represents the Mesh Backhaul 802.11ac mcs spatial stream";
    }
    leaf rap-primary-ethernet-port {
      type uint8;
      description
        "Represents if strict daisy chain mode is enabled or not in this Mesh Access Point";
    }
    leaf trunk-vlan-enabled {
      type boolean;
      description
        "Represents if vlan trunking is enabled or not for the Root Mesh Access point";
    }
    leaf active-trunk-native-vlan {
      type uint16;
      description
        "Represents trunk native VLAN of Mesh Access Point connected through wire";
    }
    leaf bhaul-child-presence {
      type boolean;
      description
        "Represents if there are any child Mesh Access points present for this Mesh AP";
    }
    leaf bhaul-over-ethernet {
      type boolean;
      description
        "Represents if this Mesh Access point is connected to the Controller through Ethenrnet interface";
    }
    leaf bgn-strict-match {
      type boolean;
      description
        "Represents if Strict match of bridge group name is enabled for this Mesh Access Point";
    }
    leaf use-default-bgn {
      type boolean;
      description
        "Represents if default  bridge group name can be used to find a parent Mesh Access Point by this AP";
    }
    leaf daisy-chain-mode {
      type boolean;
      description
        "Represents if daisy chain mode is enabled or not in this Mesh Access Point";
    }
    leaf rap-strict-daisy-chain-mode {
      type boolean;
      description
        "Represents if strict daisy chain mode is enabled or not in this Mesh Access Point";
    }
    leaf block-child-enabled {
      type boolean;
      description
        "Represents if child Mesh Access points are blocked to join to this Mesh Access Point";
    }
    leaf ethernet-bridging-enabled {
      type boolean;
      description
        "Represents if Ethernet bridging is enabled or not in this Mesh Access Point";
    }
    leaf preferred-parent {
      type yang:mac-address;
      description
        "Represents the preferred parent AP MAC Address configured on this Access Point";
    }
    leaf parent-ap-awpp-addr {
      type yang:mac-address;
      description
        "Represents the AWPP Identity at the parent Mesh Access Point";
    }
    leaf parent-ap-mac-addr {
      type yang:mac-address;
      description
        "Represents the Access Point Identity at the parent Mesh Access Point";
    }
    leaf bridge-group-name {
      type string;
      description
        "Represents the Bridge group name configured on this Access Point";
    }
    leaf psk-key-timestamp {
      type string;
      description
        "Represents the Time at which this PSK key was configured";
    }
    leaf mesh-profile-configured {
      type string;
      description
        "Represents the Mesh profile name configured for the Access Point";
    }
    leaf mesh-profile-inuse {
      type string;
      description
        "Represents the Mesh profile name used by the Access Point";
    }
    leaf neigh-child-cnt {
      type uint32;
      description
        "Represents number of child mesh neighbours for an Access Point";
    }
    leaf depth {
      type uint8;
      description
        "Represents the depth of the Access Point in the Mesh Tree";
    }
  }

  grouping st-mesh-astools {
    description
      "Represents the starnded Mesh Access Points information";
    leaf stranded-ap-mac {
      type yang:mac-address;
      description
        "Represents the radio MAC address common to the dot11 interface of the AP";
    }
    leaf listener-ap-name {
      type string;
      description
        "Represents the MAC Address of the Mesh Access Point which is receiving packets from the stranded AP";
    }
    leaf snr {
      type uint16;
      description
        "Represents the SNR value for the packets received from the stranded AP";
    }
    leaf age {
      type uint16;
      description
        "Represents the time in minutes since this Mesh AP is found to be stranded";
    }
    leaf channel {
      type uint8;
      description
        "Represents the channel information used by the starnded Mesh Access Point";
    }
    leaf stranded-ap-debug {
      type int32;
      description
        "Stranded AP debug flag";
    }
    leaf last-reported-time {
      type yang:date-and-time;
      description
        "Represents the time at which information about this stranded Mesh AP reported";
    }
  }

  grouping st-mesh-gps-info {
    description
      "Represents the GPS related information for the Mesh Access point";
    leaf wtp-mac {
      type yang:mac-address;
      description
        "Represents the radio MAC address common to the dot11 interface of the AP";
    }
    leaf sys-time {
      type yang:date-and-time;
      description
        "Represents the time at which GPS data was collected by Controller";
    }
    leaf collection-time {
      type yang:date-and-time;
      description
        "Represents the time at which GPS data was collected";
    }
    leaf location-flags {
      type uint8;
      description
        "Represents whether the access point has the GPS module installed or not";
    }
    leaf latitude {
      type uint32;
      description
        "Represents latitude information in the GPS data received";
    }
    leaf longitude {
      type uint32;
      description
        "Represents longitude information in the GPS data received";
    }
    leaf altitude {
      type uint32;
      description
        "Represents altitude information in the GPS data received";
    }
    leaf east-velocity {
      type uint32;
      description
        "Represents the velocity information towards east in the GPS data received";
    }
    leaf north-velocity {
      type uint32;
      description
        "Represents the velocity information towards north in the GPS data received";
    }
    leaf up-velocity {
      type uint32;
      description
        "Represents the velocity information towards up in the GPS data received";
    }
  }

  grouping st-mesh-cm-ds-rx-freq {
    description
      "Represents the cable modem center frequency for downstream";
    leaf-list buffer {
      type uint32;
      max-elements "24";
      ordered-by user;
      description
        "Holds the list of cable modem center frequencies for downstream";
    }
  }

  grouping st-mesh-cm-us-tx-freq {
    description
      "Represents the cable modem center frequency for upstream";
    leaf-list buffer {
      type uint32;
      max-elements "8";
      ordered-by user;
      description
        "Holds the list of cable modem center frequencies for upstream";
    }
  }

  grouping st-mesh-cm-ds-rx-pow {
    description
      "Represents the cable modem power level for downstream";
    leaf-list buffer {
      type uint32;
      max-elements "24";
      ordered-by user;
      description
        "Holds the list of cable modem power levels for downstream";
    }
  }

  grouping st-mesh-cm-us-tx-pow {
    description
      "Represents the cable modem power level for upstream";
    leaf-list buffer {
      type uint32;
      max-elements "8";
      ordered-by user;
      description
        "Holds the list of cable modem power levels for upstream";
    }
  }

  grouping st-mesh-cm-us-cton-ratio {
    description
      "Represents the cable modem Carrier to Noise frequency ratio";
    leaf-list buffer {
      type uint32;
      max-elements "8";
      ordered-by user;
      description
        "Holds the list of cable modem Carrier to Noise frequency ratios";
    }
  }

  grouping st-mesh-cable-modem {
    description
      "Represents the Cable Modem related information for the Mesh Access point";
    leaf wtp-mac {
      type yang:mac-address;
      description
        "Represents the mac address of the Mesh Access Point";
    }
    leaf cm-mac-address {
      type yang:mac-address;
      description
        "Represents the cable modem mac address";
    }
    leaf ap-mac-address {
      type yang:mac-address;
      description
        "Represents the cable modem AP mac address";
    }
    leaf ap-cm-int-mac-address {
      type yang:mac-address;
      description
        "Represents the Mesh AP cable modem interface Mac Address";
    }
    leaf cm-sw-version {
      type string;
      description
        "Represents the cable modem software version";
    }
    leaf cm-status {
      type string;
      description
        "Represents the Docsis registration status for the cable modem interface of mesh AP";
    }
    container ds-rx-frequency {
      description
        "Represents the cable modem center frequency for downstream";
      uses wireless-mesh-oper:st-mesh-cm-ds-rx-freq;
    }
    container us-rx-frequency {
      description
        "Represents the cable modem center frequency for upstream";
      uses wireless-mesh-oper:st-mesh-cm-us-tx-freq;
    }
    container ds-rx-power {
      description
        "Represents the cable modem power level for downstream";
      uses wireless-mesh-oper:st-mesh-cm-ds-rx-pow;
    }
    container us-tx-power {
      description
        "Represents the cable modem power level for upstream";
      uses wireless-mesh-oper:st-mesh-cm-us-tx-pow;
    }
    leaf eth-status {
      type string;
      description
        "Represnts the Ethernet status for the mesh AP";
    }
    leaf eth-speed {
      type string;
      description
        "Represents the Ethernet speed for the mesh AP";
    }
    container us-carrier-to-noise-ratio {
      description
        "Represents the cable modem Carrier to Noise frequency ratio";
      uses wireless-mesh-oper:st-mesh-cm-us-cton-ratio;
    }
    leaf cm-serial-number {
      type string;
      description
        "Represents the cable modem serial number";
    }
    leaf cm-event-log {
      type string;
      description
        "Represents the status of cable modem event logging";
    }
    leaf mask-bit {
      type uint32;
      description
        "Represents the value of cable modem mask bit";
    }
  }

  grouping st-mesh-node-neigh-key {
    description
      "Represents the key for mesh node neighbor table";
    leaf wtp-mac {
      type yang:mac-address;
      description
        "Represents the mac address of the Access Point";
    }
    leaf neigh-ap-mac {
      type yang:mac-address;
      description
        "Represents the mac address of neighbor mesh Access Point";
    }
  }

  grouping st-mesh-hop-list {
    description
      "Represents the list of Mesh Access Points";
    leaf-list buffer {
      type yang:mac-address;
      max-elements "8";
      ordered-by user;
      description
        "Holds the list of MAC Addresses each representing a Mesh Access Point";
    }
  }

  grouping st-mesh-dist-vector {
    description
      "Represents the vector information for the Mesh Access Point";
    leaf rap-hops {
      type uint8;
      description
        "Represents the number of hops from the RAP to this Mesh Access Point";
    }
    leaf fwd-route {
      type boolean;
      description
        "Indicates if this route is used for forwarding packets on a mesh AP";
    }
    leaf rap-metrics {
      type uint32;
      description
        "Indicates the ease value to reach root AP from this mesh AP";
    }
    container hop-list {
      description
        "represents the list of mac address from RAP to the parent of this mesh Access Point";
      uses wireless-mesh-oper:st-mesh-hop-list;
    }
  }

  grouping st-mesh-dist-vector-arr {
    description
      "Indicates the distance vectors of the AP";
    list buffer {
      max-elements "4";
      description
        "Holds the distance vector information for the AP";
      uses wireless-mesh-oper:st-mesh-dist-vector;
    }
  }

  grouping st-mesh-smooth-snr {
    description
      "Represents the per Antenna smoothed SNR values";
    leaf-list buffer {
      type uint16;
      max-elements "4";
      ordered-by user;
      description
        "Holds the list of per Antenna smoothed SNR values";
    }
  }

  grouping st-mesh-adj-minfo {
    description
      "Represents neighbor AP related information";
    leaf flags {
      type uint32;
      description
        "Represents the bit flag to indicate if the neighbor AP is a parent or child or a neighbor";
    }
    leaf neigh-mac-addr {
      type yang:mac-address;
      description
        "Represents the mac address of the Neighbor AP";
    }
    leaf ap-identity {
      type yang:mac-address;
      description
        "Represents the  identity of the mesh Access Point";
    }
    leaf neigh-ap-name {
      type string;
      description
        "Represents neighbor AP name";
    }
    leaf bh-rate {
      type string;
      description
        "Represents backhaul data rata";
    }
    leaf node-status {
      type string;
      description
        "Represents neighbor node status";
    }
    leaf worst-dist-vector {
      type uint8;
      description
        "Indicates the worst distance used for this neighbor AP";
    }
    leaf antenna {
      type uint8;
      description
        "Indicates the antenna on which route is received";
    }
    leaf channel {
      type uint8;
      description
        "Indicates the channel of the neighbor Access Point";
    }
    leaf blacklist-timeouts-left {
      type uint16;
      description
        "Indicates the remaining number of blacklist timeouts ";
    }
    leaf potl-parent-timeouts-left {
      type uint8;
      description
        "Indicates the remaining number of potential parent timeout";
    }
    leaf timeouts-left-for-child {
      type uint8;
      description
        "Indicates the remaining number of timeouts for the child";
    }
    leaf num-routes {
      type uint8;
      description
        "Represents the number of distance vectors";
    }
    leaf snr {
      type uint8;
      description
        "Represents the SNR value for the Mesh Access Point";
    }
    leaf snr-up {
      type uint8;
      description
        "Represents the SNR of the link to the AP";
    }
    leaf snr-down {
      type uint8;
      description
        "Represents the SNR of the link from the AP";
    }
    leaf neigh-type {
      type wireless-types:enm-mesh-node-neigh-type;
      description
        "Neighbor Mesh AP's role";
    }
    leaf neigh-state {
      type wireless-types:enm-mesh-node-neigh-state;
      description
        "Neighbor Mesh AP's neighbor info update state";
    }
    leaf link-snr {
      type uint8;
      description
        "Represents the calculated SNR of the link";
    }
    leaf rate {
      type uint32;
      description
        "Represents the current rate of the Neighbor AP";
    }
    leaf adjusted-ease {
      type uint32;
      description
        "Represents the hops adjusted ease value";
    }
    leaf unadjusted-ease {
      type uint32;
      description
        "Represents the ease to the root AP through this AP";
    }
    leaf rap-ease {
      type uint32;
      description
        "Represents the unadjusted ease receieved in last hello message";
    }
    leaf tx-pkts-parent {
      type uint32;
      description
        "Represents the total number of packets transmitted to this node as a parent AP";
    }
    leaf rx-pkts-parent {
      type uint32;
      description
        "Represents the total number of packets received from this node as a parent AP";
    }
    leaf poor-snr {
      type uint32;
      description
        "Indicates the number of packets received with poor SNR";
    }
    leaf last-update {
      type yang:date-and-time;
      description
        "Indicates the time at which the last hello is receievd from this neighbor";
    }
    leaf parent-change-time {
      type yang:date-and-time;
      description
        "Indicates the time at which this AP became parent";
    }
    container vectors {
      description
        "Indicates the distance vectors of this neighbor";
      uses wireless-mesh-oper:st-mesh-dist-vector-arr;
    }
    container smooth-snrs {
      description
        "Represents the per Antenna smoothed SNR values";
      uses wireless-mesh-oper:st-mesh-smooth-snr;
    }
    leaf bridge-group-name {
      type string;
      description
        "Represents the bridge group name of the neighbor AP";
    }
    leaf slot-id {
      type uint8;
      description
        "Represents the radio slot id of neighbor AP";
    }
    leaf hopcount-version {
      type uint8;
      description
        "Represents the hopcount version of neighbor AP";
    }
    leaf chan-width {
      type uint8;
      description
        "Represents the channel width used by the neighbor AP";
    }
    leaf update-flag {
      type uint8;
      description
        "Represents a flag which keep refreshing the record availability";
    }
  }

  grouping st-mesh-neigh-per-stats {
    description
      "Represents the mesh AP PER statistics";
    leaf tx-pkts-total {
      type uint32;
      description
        "Represents the total packets transmitted";
    }
    leaf tx-pkts-success {
      type uint32;
      description
        "Represents the total packets transmitted successfully";
    }
    leaf retry-pkts-total {
      type uint32;
      description
        "Represents the total packets retried";
    }
    leaf rts-attempts {
      type uint32;
      description
        "Represents the number of RTS attempts";
    }
    leaf rts-success {
      type uint32;
      description
        "Represents the number of successful RTS";
    }
  }

  grouping st-mesh-node-dr-stats {
    description
      "Represents the mesh AP data rate stats";
    leaf last-update {
      type uint8;
      description
        "Represnts when the neighbor table was last updated";
    }
    leaf rts-attempts {
      type uint32;
      description
        "Represents the number of RTS attempts";
    }
    leaf rts-success {
      type uint32;
      description
        "Represents the number of successful RTS";
    }
  }

  grouping st-mesh-node-neigh-info {
    description
      "Represents the Mesh AP neighbor related information";
    container mesh-neighs {
      description
        "Represents the Mesh AP neighbor details";
      uses wireless-mesh-oper:st-mesh-adj-minfo;
    }
    container neigh-per-stats {
      description
        "Represents the mesh AP PER statistics";
      uses wireless-mesh-oper:st-mesh-neigh-per-stats;
    }
  }

  grouping st-mesh-adj-modinfo {
    description
      "Represnts the Adjecency information for the mesh Access Point";
    leaf next-channel {
      type uint8;
      description
        "Represnts the channel number on which this mesh AP should scan";
    }
    leaf next-antenna {
      type uint8;
      description
        "Represents the Antenna this AP should use next";
    }
    leaf dlink-antenna {
      type uint8;
      description
        "Represents the downlink antenna for the mesh AP";
    }
    leaf dlink-chan {
      type uint8;
      description
        "Represents the downlink channel for the mesh AP";
    }
    leaf current-antenna {
      type uint8;
      description
        "represents the current Antenna for the mesh AP";
    }
    leaf next-neighbor {
      type uint8;
      description
        "Represents the next neighbor to transmit from this mesh AP";
    }
    leaf rap {
      type uint8;
      description
        "Represents if this is a root mode Mesh AP";
    }
    leaf current-sector-hops {
      type uint8;
      description
        "Represents the number of hops from RAP to this mesh AP in the sector";
    }
    leaf neigh-state {
      type wireless-types:mesh-adj-state;
      description
        "Represents the type of Neighbor Access Point";
    }
    leaf malformed-neigh-pkts {
      type uint32;
      description
        "Represents the total number of packets received from Neighbor AP which could not be decoded";
    }
    leaf poor-neigh-snr {
      type uint32;
      description
        "Represents the total number of packets received from Neighbor AP which have SNR value below threshold";
    }
    leaf blacklist-pkts {
      type uint32;
      description
        "Represents the total number of packets received from excluded Neighbor APs";
    }
    leaf insufficient-memory {
      type uint32;
      description
        "Represents the number of packets dropped due to insufficient memory";
    }
    leaf rx-neigh-req {
      type uint32;
      description
        "Represents the total number of neighbor requests received from Neighbor APs";
    }
    leaf rx-neigh-resp {
      type uint32;
      description
        "Represents the total number of neighbor responses received from Neighbor APs";
    }
    leaf tx-neigh-req {
      type uint32;
      description
        "Represents the total number of neighbor requests sent to Neighbor APs";
    }
    leaf tx-neigh-resp {
      type uint32;
      description
        "Represents the total number of neighbor responses sent to Neighbor APs";
    }
    leaf authentication-failures {
      type uint32;
      description
        "Represents the total number of Authentication failures with Neighbor APs";
    }
    leaf parent-changes {
      type uint32;
      description
        "Represents total number of times this mesh node has changed its parent";
    }
    leaf neigh-timeout {
      type uint32;
      description
        "represents the number of Neigbor timeouts";
    }
    leaf rx-neigh-update {
      type uint32;
      description
        "Represents the number of Neighbor updates received";
    }
    leaf tx-neigh-update {
      type uint32;
      description
        "Represents the number of Neighbor updates transmitted";
    }
    leaf current-best-neigh {
      type uint32;
      description
        "Represnts the number of best neighbor APs";
    }
  }

  grouping st-mesh-ap-node-neigh-info {
    description
      "Represnts the Adjecency and Ancestor information for the mesh Access Point";
    leaf wtp-mac {
      type yang:mac-address;
      description
        "Represents the mac address of the Mesh Access Point";
    }
    container adj-modinfo {
      description
        "Represnts the Adjecency information for the mesh Access Point";
      uses wireless-mesh-oper:st-mesh-adj-modinfo;
    }
    container dr-stats {
      description
        "Represents the mesh AP data rate stats";
      uses wireless-mesh-oper:st-mesh-node-dr-stats;
    }
    container adj-ancestor-list {
      description
        "Represents the mesh AP Ancestor list";
      uses wireless-mesh-oper:st-mesh-hop-list;
    }
    leaf adj-list-len {
      type uint8;
      description
        "Represents the number of ancestors for this mesh Access Point";
    }
  }

  grouping st-mesh-node-battery {
    description
      "Represents the Batter related information for this mesh Access Point";
    leaf wtp-mac {
      type yang:mac-address;
      description
        "Represents the mac address of Mesh Access Point";
    }
    leaf sw-version {
      type string;
      description
        "Represents the Software version for the Battery in outdoor Mesh Access Point";
    }
    leaf serial-number {
      type string;
      description
        "Represents the Serial number of the Battery in outdoor Mesh Access Point";
    }
    leaf alarms {
      type wireless-types:mesh-node-battery-alarm;
      description
        "Indicates the notification status for Battery related Alarms in outdoor Mesh Access Point";
    }
    leaf input-voltage {
      type uint16;
      description
        "Represents the AC voltage across the input terminals of the battery in outdoor mesh Access Point";
    }
    leaf output-voltage {
      type uint16;
      description
        "Represents the voltage across the output terminals of the battery in outdoor Mesh Access Point";
    }
    leaf output-power {
      type uint16;
      description
        "Represents the output power of the battery in outdoor Mesh Access Point";
    }
    leaf internal-voltage {
      type uint16;
      description
        "Represents the internal voltage of the battery in outdoor Mesh Access Point";
    }
    leaf temperature {
      type uint16;
      description
        "Represents the temperature in celsius of the battery in outdoor mesh Access Point";
    }
    leaf current {
      type uint16;
      description
        "Represents the current in the Battery of outdoor Mesh Access Point";
    }
    leaf charge {
      type uint16;
      description
        "Represents the charging status in percentage for the Battery in outdoor Mesh Access Point";
    }
  }

  grouping st-mesh-eth-intf-stats {
    description
      "Represents the statistics for the Mesh AP Ethernet interface";
    leaf rx-ucast-pkts {
      type uint32;
      description
        "Represents the total number of unicast packets received on the Mesh AP Ethernet interface";
    }
    leaf rx-n-ucast-pkts {
      type uint32;
      description
        "Represents the total number of Non-unicast packets received on the Mesh AP Ethernet interface";
    }
    leaf tx-ucast-pkts {
      type uint32;
      description
        "Represents the total number of unicast packets transmitted on the Mesh AP Ethernet interface";
    }
    leaf tx-n-ucast-pkts {
      type uint32;
      description
        "Represents the total number of Non-unicast packets transmitted on the Mesh AP Ethernet interface";
    }
  }

  grouping st-mesh-trunk-vlan-list {
    description
      "Represents the allowed vlans list when in trunk mode for the Mesh Access Point";
    leaf-list buffer {
      type uint16;
      max-elements "16";
      ordered-by user;
      description
        "Holds the list of allowed vlans";
    }
  }

  grouping st-mesh-eth-intf-vlan {
    description
      "Represents VLAN configurations for Mesh AP Ethernet interface";
    leaf mode {
      type wireless-types:ethernet-port-type;
      description
        "Represents the Ethernet interafce mode as whether Trunk or Access";
    }
    leaf vlan-id {
      type uint16;
      description
        "Represents the vlan identifier for the Ethernet interface of Mesh Access Point";
    }
    container trunk-vlan-list {
      description
        "Represents the allowed vlans list when in trunk mode for the Mesh Access Point";
      uses wireless-mesh-oper:st-mesh-trunk-vlan-list;
    }
    leaf trunk-vlan-list-count {
      type uint16;
      description
        "Represents the total number of allowed vlans for the Ethernet interface of Mesh Access Point";
    }
  }

  grouping st-mesh-eth-intf-vlan-config {
    description
      "Represents the VLAN configurations for Mesh AP Ethernet interfaces";
    container current-config {
      description
        "Represents current vlan configurations for Mesh AP Ethernet interface";
      uses wireless-mesh-oper:st-mesh-eth-intf-vlan;
    }
    container stored-config {
      description
        "Represents stored vlan configurations for Mesh AP Ethernet interface";
      uses wireless-mesh-oper:st-mesh-eth-intf-vlan;
    }
  }

  grouping st-mesh-eth-info {
    description
      "Represents information related to the status of Mesh AP Ethernet interfaces";
    leaf intf-name {
      type string;
      description
        "Represents the name of the Mesh AP Ethernet Interface";
    }
    leaf port-number {
      type uint8;
      description
        "Represents the Ethernet interface port number of the Mesh AP";
    }
    leaf status {
      type boolean;
      description
        "Represents the status of Mesh AP Ethernet interface";
    }
    leaf speed {
      type uint8;
      description
        "Represents the Speed for the Mesh AP Ethernet interface";
    }
    leaf duplex {
      type uint8;
      description
        "Represents the Duplex for the Mesh AP  Ethernet interface";
    }
    container eth-stats {
      description
        "Represents the statistics for the Mesh AP Ethernet interface";
      uses wireless-mesh-oper:st-mesh-eth-intf-stats;
    }
    container eth-vlan-config {
      description
        "Represents the vlan configurations for Mesh AP Ethernet interface";
      uses wireless-mesh-oper:st-mesh-eth-intf-vlan-config;
    }
  }

  grouping st-mesh-eth-info-arr {
    description
      "List of Mesh AP Ethernet interfaces with their status information";
    list buffer {
      max-elements "5";
      description
        "Holds the list of AP Ethernet interfaces with their status information";
      uses wireless-mesh-oper:st-mesh-eth-info;
    }
  }

  grouping st-mesh-node-env-info {
    description
      "Represents the Mesh AP Ethernet interface related information";
    leaf number-of-ports {
      type uint32;
      description
        "Indicates the number of Ethernet ports on the mesh AP";
    }
    leaf bhaul-intf-name {
      type string;
      description
        "Represents the backhaul interface name for the Mesh AP";
    }
    container eth-if-status {
      description
        "Represents the status of Mesh AP Ethernet interfaces";
      uses wireless-mesh-oper:st-mesh-eth-info-arr;
    }
  }

  grouping st-mesh-temperature {
    description
      "Represents the temperature related information of Mesh AP ";
    leaf status {
      type uint32;
      description
        "Represents the status of Mesh AP ";
    }
    leaf degree {
      type uint32;
      description
        "Represents the degree in celsius of Mesh AP ";
    }
    leaf heater-status {
      type uint32;
      description
        "Represents the heater status of the Mesh AP";
    }
    leaf temp-state {
      type uint32;
      description
        "Represents the temperature state of the Mesh AP";
    }
    leaf temp-fahrenheit {
      type uint32;
      description
        "Represents the temperature info of a Mesh AP in fahrenheit";
    }
  }

  grouping st-mesh-peripheral-info {
    description
      "Represents the peripheral device information for this mesh Access Point";
    container temperature {
      description
        "Represents the temperature information of the mesh AP";
      uses wireless-mesh-oper:st-mesh-temperature;
    }
    leaf cm-installed {
      type uint8;
      description
        "Represents if cable modem is applicable for this Mesh AP";
    }
    leaf fiber-sfp-installed {
      type uint8;
      description
        "Represents if Fiber SFP is applicable for this mesh AP";
    }
    leaf poe-out-status {
      type uint8;
      description
        "Represents the POE out status for this mesh AP";
    }
    leaf orientation {
      type uint8;
      description
        "Represents the orientation for this mesh AP";
    }
  }

  grouping st-mesh-node-component-info {
    description
      "Represents the information realted to peripheral components for Mesh Access Point";
    leaf wtp-mac {
      type yang:mac-address;
      description
        "Represents the MAC address of the Access Point";
    }
    container env-info {
      description
        "Represents the Mesh AP Ethernet interface related information";
      uses wireless-mesh-oper:st-mesh-node-env-info;
    }
    container battery-state {
      description
        "Represents the Batter related information for this mesh Access Point";
      uses wireless-mesh-oper:st-mesh-node-battery;
    }
    container peripheral-info {
      description
        "Represents the peripheral device information for this mesh Access Point";
      uses wireless-mesh-oper:st-mesh-peripheral-info;
    }
  }

  grouping st-bgn-channel-comp-key {
    description
      "Represents the key for subset channel list table";
    leaf bgn {
      type string;
      description
        "Represents the bridge group name for the access point in the mesh network";
    }
    leaf channel {
      type uint8;
      description
        "Represents the channel number in subset channel list";
    }
  }

  grouping st-subset-channel-list {
    description
      "Represents the information related to subset channel list for a mesh network";
    leaf rap-local-count {
      type uint8;
      description
        "Represents the number of Root Access Points using the bridge group name and channel";
    }
  }

  grouping mesh-linktest-snr-profile {
    description
      "Represents Mesh Linktest SNR Profile";
    leaf-list buffer-snr {
      type uint32;
      max-elements "21";
      ordered-by user;
      description
        "Represents the list of SNR values during the linktest";
    }
  }

  grouping mesh-link-test-nf-profile {
    description
      "Represents Mesh Linktest NF Profile";
    leaf-list buffer-nf {
      type uint32;
      max-elements "21";
      ordered-by user;
      description
        "Represents the list of NF values during the linktest";
    }
  }

  grouping mesh-link-test-rssi-profile {
    description
      "Represents Mesh Linktest RSSI Profile";
    leaf-list buffer-rssi {
      type uint32;
      max-elements "21";
      ordered-by user;
      description
        "Represents the list of RSSI values";
    }
  }

  grouping mesh-link-test-result {
    description
      "Represents the results of Mesh Linktest";
    leaf elapsed-time {
      type uint32;
      description
        "Represents the time elapsed for the Mesh Linktest";
    }
    leaf last-elapsed-timestamp {
      type yang:date-and-time;
      description
        "Represents the time elapsed after the last response";
    }
    leaf last-rx-rate {
      type uint32;
      description
        "Represents the Rx rate received  in the last response";
    }
    leaf link-test-buffer-allocation-error {
      type uint32;
      description
        "Represents the number of rx buffer allocation error";
    }
    leaf link-test-queue-full-error {
      type uint32;
      description
        "Represents the no of rx queue full error";
    }
    leaf last-rx-timestamp {
      type yang:date-and-time;
      description
        "Represents the time at which the last packet was received";
    }
    container snr-profile {
      description
        "Represents Mesh Linktest SNR Profile";
      uses wireless-mesh-oper:mesh-linktest-snr-profile;
    }
    container nf-profile {
      description
        "Represents Mesh Linktest NF Profile";
      uses wireless-mesh-oper:mesh-link-test-nf-profile;
    }
    container rssi-profile {
      description
        "Represents Mesh Linktest RSSI Profile";
      uses wireless-mesh-oper:mesh-link-test-rssi-profile;
    }
    leaf total-tx-pkts {
      type uint32;
      description
        "Represents the total number of packets transmitted";
    }
    leaf total-rx-pkts {
      type uint32;
      description
        "Represents the total number of packets recieved";
    }
    leaf good-rx-pkts {
      type uint32;
      description
        "Represents the total number of good packets recieved";
    }
    leaf duplicate-rx-pkts {
      type uint32;
      description
        "Represents the total number of duplicate packets recieved";
    }
    leaf short-rx-pkts {
      type uint32;
      description
        "Represents the total number of linktest packets which were shorter than expected";
    }
    leaf big-rx-pkts {
      type uint32;
      description
        "Represents the total number of packets which were bigger than expected";
    }
    leaf rx-pkts-physical-errors {
      type uint32;
      description
        "Represents the total number of packets received with error at physical layer";
    }
    leaf rx-pkts-crc-errors {
      type uint32;
      description
        "Represents the total number of packets with CRC error";
    }
    leaf rx-pkts-seq-errors {
      type uint32;
      description
        "Represents the total number of packets received with out of order sequence number";
    }
    leaf rx-pkts-unknown-errors {
      type uint32;
      description
        "Represents the total number of packets received with unknown error";
    }
    leaf rx-pkts-prev-seq {
      type uint32;
      description
        "Represents the sequence number of the last packet received";
    }
    leaf rx-pkts-lost {
      type uint32;
      description
        "Represents the total number of packets lost during linktest";
    }
    leaf rx-pkts-average-snr {
      type int32;
      description
        "Represents the average SNR(singal to noise) during  linktest";
    }
    leaf rx-pkts-highest-snr {
      type int32;
      description
        "Represents the highest SNR(singal to noise) during linktest";
    }
    leaf rx-pkts-lowest-snr {
      type int32;
      description
        "Represents the lowest SNR(singal to noise) during linktest";
    }
    leaf rx-pkts-average-nf {
      type int32;
      description
        "Represents the average NF(noise floor) during linktest";
    }
    leaf rx-pkts-highest-nf {
      type int32;
      description
        "Represents the highest NF(noise floor) during linktest";
    }
    leaf rx-pkts-lowest-nf {
      type int32;
      description
        "Represents the lowest NF(noise floor) during linktest";
    }
    leaf rx-pkts-average-rssi {
      type int32;
      description
        "Represents the average RSSI during linktest";
    }
    leaf rx-pkts-highest-rssi {
      type int32;
      description
        "Represents the highest RSSI during linktest";
    }
    leaf rx-pkts-lowest-rssi {
      type int32;
      description
        "Represents the lowest RSSI during linktest";
    }
  }

  grouping mesh-link-test-mac-endpoints {
    description
      "Represents the MAC address of APs participating in linktest";
    leaf source-mac {
      type yang:mac-address;
      description
        "Represents the MAC address of the source AP";
    }
    leaf destination-mac {
      type yang:mac-address;
      description
        "Represents the MAC address of the destination AP";
    }
  }

  grouping mesh-link-test-config {
    description
      "Represents the Mesh linktest configuration parameters";
    leaf data-rate {
      type wireless-types:mesh-linktest-rate;
      description
        "Represents the data rate in Mbps which will is supported by both APs";
    }
    leaf pkts-per-sec {
      type uint32;
      description
        "Represents the number of packets per seconds to be transmitted";
    }
    leaf packet-size {
      type uint16;
      description
        "Represents the size of the packets in bytes";
    }
    leaf duration {
      type uint16;
      description
        "Represents the time interval for the linktest in seconds";
    }
    leaf status {
      type int32;
      description
        "Represents the current status of the linktest";
    }
    leaf data-rate-index {
      type wireless-types:mesh-linktest-rate-idx;
      description
        "Represents the data rate index used for linktest traffic";
    }
  }

  grouping mesh-link-test {
    description
      "Represents the Mesh Linktest parameters";
    leaf linktest-id {
      type uint32;
      description
        "Represents the Mesh linktest ID";
    }
    leaf started-at {
      type yang:date-and-time;
      description
        "Represents the time at which linktest started";
    }
    container config {
      description
        "Represents the Mesh linktest config parameters";
      uses wireless-mesh-oper:mesh-link-test-config;
    }
    container results {
      description
        "Represents the Mesh linktest results parameters";
      uses wireless-mesh-oper:mesh-link-test-result;
    }
    leaf record-in-use {
      type uint8;
      description
        "Represents whether the linktest is in progress";
    }
  }

  container mesh-oper-data {
    config false;
    description
      "Mesh operational data";
    list mesh-q-stats {
      key "wtp-mac q-type";
      description
        "Represents the Mesh Access point packet queue statistics";
      uses wireless-mesh-oper:st-mesh-node-pkt-queue-stats-key;
      uses wireless-mesh-oper:st-mesh-node-pkt-queue-stats;
    }
    list mesh-dr-stats {
      key "wtp-mac neigh-ap-mac data-rate-index";
      description
        "Represents the Mesh Access point data rate statistics";
      uses wireless-mesh-oper:st-mesh-node-data-rate-stats-key;
      uses wireless-mesh-oper:st-mesh-node-data-rate-stats;
    }
    list mesh-sec-stats {
      key "wtp-mac";
      description
        "Represents the Mesh Access point security  statistics";
      uses wireless-mesh-oper:st-mesh-ap-security-stats;
    }
    list mesh-oper-data {
      key "wtp-mac";
      description
        "Represents the Mesh Access point operational data";
      uses wireless-mesh-oper:st-mesh-ap-oper-data;
    }
    list mesh-astools {
      key "stranded-ap-mac";
      description
        "Represents the information about stranded Mesh Access point";
      uses wireless-mesh-oper:st-mesh-astools;
    }
    list mesh-gps-info {
      key "wtp-mac";
      description
        "Represents the GPS related information for the Mesh Access point";
      uses wireless-mesh-oper:st-mesh-gps-info;
    }
    list mesh-cm {
      key "wtp-mac";
      description
        "Represents the Cable Modem related information for the Mesh Access point";
      uses wireless-mesh-oper:st-mesh-cable-modem;
    }
    list mesh-neigh {
      key "wtp-mac neigh-ap-mac";
      description
        "Represents the Mesh AP neighbor related information";
      uses wireless-mesh-oper:st-mesh-node-neigh-key;
      uses wireless-mesh-oper:st-mesh-node-neigh-info;
    }
    list mesh-ap-neigh {
      key "wtp-mac";
      description
        "Represnts the Adjecency and Ancestor information for the mesh Access Point";
      uses wireless-mesh-oper:st-mesh-ap-node-neigh-info;
    }
    list mesh-subset-channel-list {
      key "bgn channel";
      description
        "Represents the subset channel list table";
      uses wireless-mesh-oper:st-bgn-channel-comp-key;
      uses wireless-mesh-oper:st-subset-channel-list;
    }
    list mesh-comp-info {
      key "wtp-mac";
      description
        "Represents the information related to peripheral components for Mesh Access Point";
      uses wireless-mesh-oper:st-mesh-node-component-info;
    }
    list mesh-linktest-parameters {
      key "linktest-id";
      description
        "Represents Mesh linktest related information";
      uses wireless-mesh-oper:mesh-link-test;
      uses wireless-mesh-oper:mesh-link-test-mac-endpoints;
    }
  }
}
