module cisco-xe-openconfig-vlan-ext {
    namespace "http://cisco.com/ns/yang/cisco-xe-openconfig-vlan-ext";
    
    prefix oc-vlan-ext;

    import openconfig-vlan {
       prefix oc-vlan;
    }

    import openconfig-vlan-types {
       prefix oc-vlan-types;
    }

    import openconfig-interfaces {
       prefix oc-if;
    }

    organization "Cisco Systems";

    description
       "Augmentation for oc-vlan";

////////////////////////////////////////////////////////////////////////////
// REVISION
///////////////////////////////////////////////////////////////////////////
 revision 2017-06-14 {
   description "Initial Draft to add a new oper only list for default vlans";
 }


////////////////////////////////////////////////////////////////////////////
// Grouping
///////////////////////////////////////////////////////////////////////////

 grouping default-vlans {
    description "Top-level grouping for default vlans";

      list default-vlan {
        config false;
        key "vlan-id";
        description "Default VLANs keyed by id";

        leaf vlan-id {
          type uint16 {
            range "1 | 1002..1005";
          }
          description "Valid default vlans are 1,1002,1003,1004,1005";
        }

        leaf name {
           type string;
           description "VLAN name";
        }

        leaf status {
          type enumeration {
            enum ACTIVE {
               description "VLAN is active";
            }
            enum SUSPENDED {
               description "VLAN is inactive / suspended";
            }
           }
           default ACTIVE;
           description "Admin state of the VLAN";
        }
        
        list ports {
           config false;
              description
                "List of interfaces / subinterfaces associated with the VLAN.";

           leaf interface {
              type string;
              description
                "Reference to a base interface.
                 If a reference to a subinterface is required, 
                 this leaf must be specified to indicate the base interface.";
              }

           leaf subinterface {
              type uint32;
              description
                "Reference to a subinterface -- this requires the base
                 interface to be specified using the interface leaf in
                 this container.  If only a reference to a base interface
                 is requuired, this leaf should not be set.";
           }
        }
      }
  }


////////////////////////////////////////////////////////////////////////////
// Augment
//////////////////////////////////////////////////////////////////////////
  augment "/oc-vlan:vlans" {
     uses default-vlans;
  }
}
