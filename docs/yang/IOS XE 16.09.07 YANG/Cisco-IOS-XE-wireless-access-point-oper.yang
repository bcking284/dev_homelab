module Cisco-IOS-XE-wireless-access-point-oper {
  yang-version 1;
  namespace "http://cisco.com/ns/yang/Cisco-IOS-XE-wireless-access-point-oper";
  prefix wireless-access-point-oper;

  import Cisco-IOS-XE-wireless-ap-types {
    prefix ap-types;
  }
  import Cisco-IOS-XE-wireless-enum-types {
    prefix wireless-enum-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for access point operational data.
     Copyright (c) 2016-2018 by Cisco Systems, Inc.
     All rights reserved.";

  revision 2018-06-28 {
    description
      "- Add AP name for which bandwidth is allocated, number of active TSPEC and SIP calls
       - Remove voice client from qos client data
       - Add SIP active and rejected call counters
       - Add SIP call-control metrics";
    reference "5.0.0";
  }
  revision 2018-04-02 {
    description
      "Replaced an existing attribute lookup_neigh_mac with 
       neighbor_ap_name";
    reference "4.0.0";
  }
  revision 2018-03-22 {
    description
      "Enum value change";
    reference "3.0.0";
  }
  revision 2018-01-24 {
    description
      "The first generally available version";
    reference "2.0.0";
  }
  revision 2017-05-05 {
    description
      "Initial revision";
    reference "1.0.0";
  }

  typedef enum-ap-state {
    type enumeration {
      enum "ap-down" {
        value 1;
        description
          "Access Point state is Down";
      }
      enum "ap-up" {
        value 2;
        description
          "Access Point state is Up";
      }
      enum "unregistered" {
        value 3;
        description
          "Access Point state is un-registered";
      }
      enum "registered" {
        value 4;
        description
          "Access Point state is Registered";
      }
      enum "downloading" {
        value 5;
        description
          "Access Point state is Image Download";
      }
    }
    description
      "Operational state of Access Point";
  }

  typedef enum-cdp-enable-state {
    type enumeration {
      enum "cdp-enabled" {
        value 1;
        description
          "CDP is enabled";
      }
      enum "cdp-disabled" {
        value 2;
        description
          "CDP is Disabled";
      }
    }
    description
      "CDP state, enabled or disabled";
  }

  typedef enum-lisp-query-state {
    type enumeration {
      enum "lisp-query-triggered" {
        value 1;
        description
          "LISP query is triggered";
      }
      enum "lisp-query-done" {
        value 2;
        description
          "LISP query is Complete";
      }
      enum "lisp-query-not-needed" {
        value 3;
        description
          "LISP query is not Done";
      }
      enum "lisp-query-failed" {
        value 4;
        description
          "LISP query is Failed";
      }
    }
    description
      "State of Lisp query";
  }

  typedef enm-cert-type {
    type enumeration {
      enum "wireless-cert-mic" {
        value 1;
        description
          "Cert type: Manufacturer Installed Certificate";
      }
      enum "wireless-cert-ssc" {
        value 2;
        description
          "Cert type: Self Signed Certificate";
      }
      enum "wireless-cert-lsc" {
        value 3;
        description
          "Cert type: Locally Significant Certificate";
      }
    }
    description
      "enumeration to define certificate types with which AP can join";
  }

  typedef enm-vlan-state {
    type enumeration {
      enum "vlan-tag-off" {
        value 0;
        description
          "Ethernet vlan tag is disabled";
      }
      enum "vlan-tag-on" {
        value 1;
        description
          "Ethernet vlan tag is enabled";
      }
      enum "vlan-tag-failover" {
        value 2;
        description
          "Ethernet vlan tag has fallen back to disabled on AP";
      }
    }
    description
      "enumeration to define vlan tag states";
  }

  typedef enm-last-failure-type {
    type enumeration {
      enum "failure-none" {
        value 0;
        description
          "No failure";
      }
      enum "discovery" {
        value 1;
        description
          "discovery failure";
      }
      enum "join" {
        value 2;
        description
          "Join failure";
      }
      enum "config" {
        value 3;
        description
          "Failed to push configuration to the AP";
      }
      enum "dtls" {
        value 4;
        description
          "Failed to establish dtls session with the AP";
      }
    }
    description
      "enumeration to define last failure type";
  }

  typedef enm-ap-discovery-failure-reason {
    type enumeration {
      enum "disc-fail-none" {
        value 0;
        description
          "Discovery request rejected unknown reason for discovery failure";
      }
      enum "failure-decoding-board-data" {
        value 1;
        description
          "Discovery request rejected board data payload decode failed";
      }
      enum "failure-decoding-radio-info" {
        value 2;
        description
          "Discovery request rejected Radio info payload decode failed";
      }
      enum "failure-decoding-descriptor" {
        value 3;
        description
          "Discovery request rejected WTP descriptor decode failed";
      }
      enum "max-concurrent-downloads-reached" {
        value 4;
        description
          "Discovery request rejected Maximum concurrent downloads reached";
      }
      enum "higher-priority-ap-joined-after-ap" {
        value 5;
        description
          "Discovery request rejected High priority ap joined";
      }
      enum "max-ap-limit-reached" {
        value 6;
        description
          "Discovery request rejected maximum APs associated";
      }
      enum "max-concurrent-joins-reached" {
        value 7;
        description
          "Discovery request rejected maximum concurrent AP joins happened";
      }
      enum "disc-failure-encoding-descriptor" {
        value 8;
        description
          "Discovery response failed AC descriptor encode failed";
      }
      enum "failure-encoding-name" {
        value 9;
        description
          "Discovery response failed AC name encode failed";
      }
      enum "failure-encoding-ipv4-address" {
        value 10;
        description
          "Discovery response failed AC IPV4 encode failed";
      }
      enum "failure-encoding-ipv6-address" {
        value 11;
        description
          "Discovery response failed AC IPV6 encode failed";
      }
      enum "disc-failure-encoding-mwar-type-payload" {
        value 12;
        description
          "Discovery response failed AC type encode failed";
      }
      enum "disc-failure-encoding-radio-info" {
        value 13;
        description
          "Discovery response failed Encode radio info failed";
      }
      enum "disc-failure-sending-response" {
        value 14;
        description
          "Discovery response failed";
      }
      enum "disc-failure-non-wireless-mgmt-interface" {
        value 15;
        description
          "Discovery request rejected non wireless management interface";
      }
    }
    description
      "enumeration to define discovery failure reason";
  }

  typedef enm-ap-join-failure-reason {
    type enumeration {
      enum "join-failure-none" {
        value 0;
        description
          "AP join failed - unknown reason";
      }
      enum "failure-decoding-software-version" {
        value 1;
        description
          "AP join failed - decoding of sw version failed";
      }
      enum "failure-decoding-hardware-version" {
        value 2;
        description
          "AP join failed - decoding of hw version failed";
      }
      enum "failure-decoding-boot-version" {
        value 3;
        description
          "AP join failed - decoding of boot version failed";
      }
      enum "failure-decoding-wtp-descriptor" {
        value 4;
        description
          "AP join failed - decoding of wtp descr failed";
      }
      enum "unsupported-ap" {
        value 5;
        description
          "AP join failed - unsupported AP type";
      }
      enum "join-failure-reqrejected-notfabriccapable" {
        value 6;
        description
          "AP join failure - not facbric capable";
      }
      enum "failure-decoding-module-number" {
        value 7;
        description
          "AP join failed - decoding of model number failed";
      }
      enum "failure-decoding-serial-number" {
        value 8;
        description
          "AP join failed - decoding of serial number failed";
      }
      enum "failure-decoding-board-id" {
        value 9;
        description
          "AP join failed - decoding of board id failed";
      }
      enum "failure-decoding-board-revision" {
        value 10;
        description
          "AP join failed - decoding of board revision failed";
      }
      enum "failure-decoding-base-mac-address" {
        value 11;
        description
          "AP join failed - decoding of base mac address";
      }
      enum "failure-decoding-location-data" {
        value 12;
        description
          "AP join failed - decoding of location data failed";
      }
      enum "failure-decoding-ap-name" {
        value 13;
        description
          "AP join failed - decoding of wtp name failed";
      }
      enum "failure-decoding-ipv4-address" {
        value 14;
        description
          "AP join failed - decoding of IPV4 failed";
      }
      enum "failure-decoding-board-data-options" {
        value 15;
        description
          "AP join failed - decoding of board data opt failed";
      }
      enum "invalid-radio-slot-id" {
        value 16;
        description
          "AP join failed - Invalid radio slot";
      }
      enum "join-failure-reqrejected-decodemaxmsgsize" {
        value 17;
        description
          "AP join failure - decode maximum message size";
      }
      enum "failure-decoding-session-id" {
        value 18;
        description
          "AP join failed - decode of sessionid failed";
      }
      enum "join-failure-encoding-radio-info" {
        value 19;
        description
          "AP join failed - Encoding of wtp radio info failed";
      }
      enum "failure-encoding-max-message-length" {
        value 20;
        description
          "AP join failed - Encoding of maximum message length failed";
      }
      enum "join-failure-encoding-descriptor" {
        value 21;
        description
          "AP join failed - Encoding of AC descriptor failed";
      }
      enum "failure-encoding-ac-name" {
        value 22;
        description
          "AP join failed - Encoding of AC name failed";
      }
      enum "failure-encoding-capwap-control-ipv4-address" {
        value 23;
        description
          "AP join failed - Encoding of control ipv4 header failed";
      }
      enum "join-failure-encoding-mwar-type-payload" {
        value 24;
        description
          "AP join failed - Encoding of controller type failed";
      }
      enum "failure-encoding-auth-token-payload" {
        value 25;
        description
          "AP join failed - Encoding of auth key token failed";
      }
      enum "join-failure-respsendfailed-encrespencdudplite" {
        value 26;
        description
          "AP join failure - encrespencdudplite";
      }
      enum "ap-delete-in-progress" {
        value 27;
        description
          "AP join failure - in progress";
      }
      enum "join-failure-sending-response" {
        value 28;
        description
          "AP join failure - send response failed";
      }
      enum "ap-auth-pending" {
        value 29;
        description
          "AP join failure - AP auth pending";
      }
      enum "join-failure-reqrejected-decodecapwapcapabilities" {
        value 30;
        description
          "AP join failure - decode capwap capabilities";
      }
      enum "join-failure-internal-error" {
        value 31;
        description
          "AP join failure - internal error";
      }
    }
    description
      "enumeration to define failure reason";
  }

  typedef enm-ap-config-failure-reason {
    type enumeration {
      enum "config-failure-none" {
        value 0;
        description
          "AP Config failure - unknown reason";
      }
      enum "unknown-ap" {
        value 1;
        description
          "AP Config failure - unknown AP";
      }
      enum "regulatory-domain-check-failed" {
        value 2;
        description
          "AP Config failure - regulatory domain check failed";
      }
      enum "capwap-data-failed" {
        value 3;
        description
          "AP Config failure - capwap data failed";
      }
      enum "invalid-regulatory-domain" {
        value 4;
        description
          "AP Config failure - Invalid regulatory domain";
      }
      enum "response-build-failed" {
        value 5;
        description
          "AP Config failure - Could not build the response";
      }
      enum "response-send-failed" {
        value 6;
        description
          "AP Config failure - Config status response failed";
      }
      enum "config-failure-internal-error" {
        value 7;
        description
          "AP Config failure - Internal error";
      }
    }
    description
      "enumeration to define configure failure reason";
  }

  typedef enm-ap-disconnect-reason {
    type enumeration {
      enum "wtp-disconnect-none" {
        value 0;
        description
          "AP disconnected - Reason unknown";
      }
      enum "tx-request-failed" {
        value 1;
        description
          "AP disconnected - Maximum limit reached";
      }
      enum "wtp-reset-config-cmd-sent" {
        value 2;
        description
          "AP disconnected - Reset command sent to AP";
      }
      enum "wtp-clear-config" {
        value 3;
        description
          "AP disconnected - Clear config done on AP";
      }
      enum "heart-beat-timer-expiry" {
        value 4;
        description
          "AP disconnected - Heart beat time expired";
      }
      enum "flex-profile-added" {
        value 5;
        description
          "AP disconnected - Flex profile added";
      }
      enum "flex-profile-deleted" {
        value 6;
        description
          "AP disconnected - Flex profile deleted";
      }
      enum "policy-tag-added" {
        value 7;
        description
          "AP disconnected - Policy tag added";
      }
      enum "policy-tag-deleted" {
        value 8;
        description
          "AP disconnected - Policy tag deleted";
      }
      enum "site-tag-added" {
        value 9;
        description
          "AP disconnected - Site tag added";
      }
      enum "site-tag-deleted" {
        value 10;
        description
          "AP disconnected - Site tag deleted";
      }
      enum "site-tag-config-modified" {
        value 11;
        description
          "AP disconnected - Site tag configuration modified";
      }
      enum "rf-tag-added" {
        value 12;
        description
          "AP disconnected - RF Tag added";
      }
      enum "rf-tag-deleted" {
        value 13;
        description
          "AP disconnected - RF Tag deleted";
      }
      enum "ap-profile-added" {
        value 14;
        description
          "AP disconnected - AP profile added";
      }
      enum "ap-profile-deleted" {
        value 15;
        description
          "AP disconnected - AP profile deleted";
      }
      enum "tag-modified" {
        value 16;
        description
          "AP disconnected - AP tag modified";
      }
      enum "lag-modified" {
        value 17;
        description
          "AP disconnected - AP lag modified";
      }
      enum "wtp-disconnect-ap-regulatory-domain-change" {
        value 18;
        description
          "AP disconnected - Regulatory domain changed";
      }
      enum "wtp-disconnect-oeap-disabled" {
        value 19;
        description
          "AP disconnected - Oeap disabled";
      }
      enum "wtp-disconnect-mesh-config-change" {
        value 20;
        description
          "AP disconnected - Mesh configuration modified";
      }
      enum "wtp-disconnect-unsupported-ap" {
        value 21;
        description
          "AP disconnected - Unsupported AP";
      }
      enum "wtp-disconnect-dtls-handshake-failure" {
        value 22;
        description
          "AP disconnected - DTLS handshake failed";
      }
      enum "wtp-disconnect-dtls-certificate-verify-failure" {
        value 23;
        description
          "AP disconnected - DTLS certificate verify failed";
      }
      enum "wtp-disconnect-dtls-aaa-verify-failure" {
        value 24;
        description
          "AP disconnected - AAA verify failed";
      }
      enum "wtp-disconnect-dtls-handshake-timer-expiry" {
        value 25;
        description
          "AP disconnected - DTLS handshake timer expired";
      }
      enum "wtp-disconnect-dtls-alert-from-ap" {
        value 26;
        description
          "AP disconnected - DTLS received alert from AP";
      }
    }
    description
      "enumeration to define ap disconnect reason";
  }

  typedef qos-pm-state {
    type enumeration {
      enum "wtp-disconnect-regulatory" {
        value 0;
        description
          "QoS policy map state is unknown";
      }
      enum "wtp-disconnect-oeapdisabled" {
        value 1;
        description
          "QoS policy is missing from PM database";
      }
      enum "qos-pm-state-policy-invalid" {
        value 2;
        description
          "QoS policy validation check failed";
      }
      enum "qos-pm-state-db-access-failed" {
        value 3;
        description
          "Error accessing QoS PM database";
      }
      enum "qos-pm-state-install-failed" {
        value 4;
        description
          "QoS policy map installation is failed with NACK";
      }
      enum "qos-pm-state-install-failed-fatbind-sched" {
        value 5;
        description
          "Fail to push policy info to AP while FATBIND subevent failed";
      }
      enum "qos-pm-state-install-failed-send-to-ap" {
        value 6;
        description
          "Fail to push policy info to AP";
      }
      enum "qos-pm-state-install-failed-bind-fail" {
        value 7;
        description
          "Policy bind failure response from the AP";
      }
      enum "qos-pm-state-install-failed-unbind-fail" {
        value 8;
        description
          "Policy unbind failure response from the AP";
      }
      enum "qos-pm-state-install-failed-at-add-mobile" {
        value 9;
        description
          "Fail to Encode QoS info in ADD Mobile Payload";
      }
      enum "qos-pm-state-install-success" {
        value 10;
        description
          "QoS policy map installation is successful";
      }
      enum "qos-pm-state-max" {
        value 11;
        description
          "MAX state type";
      }
    }
    description
      "This object represents QoS policy map state";
  }

  typedef qos-pm-type {
    type enumeration {
      enum "qos-pm-type-none" {
        value 0;
        description
          "QoS policy map type is none";
      }
      enum "qos-pm-type-local" {
        value 1;
        description
          "QoS policy map type is local";
      }
      enum "qos-pm-type-pmap" {
        value 2;
        description
          "QoS policy map type is PMAP";
      }
      enum "qos-pm-type-aaa" {
        value 3;
        description
          "QoS policy map type is AAA";
      }
      enum "qos-pm-type-local-wlan" {
        value 4;
        description
          "QoS policy map type is local WLAN";
      }
      enum "qos-pm-type-qos-internal" {
        value 5;
        description
          "QoS policy map type is internal";
      }
    }
    description
      "This object represents QoS policy map type";
  }

  typedef w-config-type {
    type enumeration {
      enum "config-auto" {
        value 1;
        description
          "Configuration type is Auto";
      }
      enum "customized" {
        value 2;
        description
          "Configuration type is Static";
      }
    }
    description
      "Possible values for configuration type";
  }

  typedef ap-dot11-radio-role {
    type enumeration {
      enum "dot11-radio-role-updownlink" {
        value 0;
        description
          "radio role is up and down link";
      }
      enum "dot11-radio-role-uplink" {
        value 1;
        description
          "radio role is up link";
      }
      enum "dot11-radio-role-downlink" {
        value 2;
        description
          "radio role is down link";
      }
      enum "dot11-radio-role-access" {
        value 3;
        description
          "radio role is access";
      }
      enum "dot11-radio-role-shutdown" {
        value 4;
        description
          "radio is shutdown";
      }
      enum "dot11-radio-role-unknown" {
        value 5;
        description
          "radio role is unknown";
      }
      enum "dot11-radio-role-uplinkaccess" {
        value 6;
        description
          "radio role is up link access";
      }
      enum "dot11-radio-role-downlinkaccess" {
        value 7;
        description
          "radio role is down link access";
      }
      enum "dot11-radio-role-updownlinkaccess" {
        value 8;
        description
          "radio role is up and down link access";
      }
    }
    description
      "Enum for Dot11 Radio Role of AP";
  }

  typedef enum-radio-admin-state {
    type enumeration {
      enum "enabled" {
        value 1;
        description
          "Radio Admin State is Enabled";
      }
      enum "disabled" {
        value 2;
        description
          "Radio Admin State is Disabled";
      }
    }
    description
      "Radio Admin state";
  }

  typedef enum-radio-oper-state {
    type enumeration {
      enum "radio-up" {
        value 0;
        description
          "Radio Operational State Enabled";
      }
      enum "radio-down" {
        value 1;
        description
          "Radio Operational State Disabled";
      }
    }
    description
      "Radio Operational state";
  }

  typedef enum-radio-cfg-state {
    type enumeration {
      enum "radio-cfg-enabled" {
        value 0;
        description
          "Radio Config State Enabled";
      }
      enum "radio-cfg-disabled" {
        value 1;
        description
          "Radio Config State Disabled";
      }
    }
    description
      "Radio config state";
  }

  typedef enum-radio-rrm-event-type {
    type enumeration {
      enum "radio-channel-change" {
        value 0;
        description
          "Radio channel change event";
      }
      enum "radio-tx-pwr-change" {
        value 1;
        description
          "Radio Tx Power change event";
      }
      enum "radio-if-down" {
        value 2;
        description
          "Radio interface Down event";
      }
      enum "radio-if-up" {
        value 3;
        description
          "Radio interface Up event";
      }
    }
    description
      "Radio event type";
  }

  typedef enum-ap-upgrade-status {
    type enumeration {
      enum "ap-upgrade-status-ongoing" {
        value 0;
        description
          "Upgrade still in progress";
      }
      enum "ap-upgrade-status-complete" {
        value 1;
        description
          "Upgrade algorithm is complete";
      }
      enum "ap-upgrade-status-aborted" {
        value 2;
        description
          "Upgrade algorithm was aborted";
      }
      enum "ap-upgrade-status-paused" {
        value 3;
        description
          "Upgrade algorithm is paused";
      }
    }
    description
      "Status of the AP upgrade algorithm";
  }

  typedef enum-ap-upgrade-ap-status {
    type enumeration {
      enum "ap-upgrade-status-na" {
        value 0;
        description
          "Not applicable";
      }
      enum "ap-upgrade-status-rebooted" {
        value 1;
        description
          "AP is rebooted";
      }
      enum "ap-upgrade-status-joined-back" {
        value 2;
        description
          "AP joined the same controller successfully";
      }
      enum "ap-upgrade-status-joined-member" {
        value 3;
        description
          "AP joined a member controller after reboot";
      }
      enum "ap-upgrade-status-missing" {
        value 4;
        description
          "AP is missing after reboot";
      }
    }
    description
      "Status of the AP during upgrade";
  }

  typedef enum-ap-upgrade-ap-mode {
    type enumeration {
      enum "ap-upgrade-mode-na" {
        value 0;
        description
          "Invalid AP upgrade mode";
      }
      enum "ap-upgrade-mode-source" {
        value 1;
        description
          "AP upgrade is running in source mode";
      }
      enum "ap-upgrade-mode-destination" {
        value 2;
        description
          "AP upgrade is running in destination mode";
      }
    }
    description
      "AP upgrade mode";
  }

  typedef flag-ap-capability {
    type bits {
      bit bridge-mode-capable {
        position 0;
        description
          "Ap capability for bridge mode";
      }
      bit mesh-daisy-chaining-capable {
        position 1;
        description
          "Ap capability for daisy chaining mode";
      }
      bit cap-three-spatial-streams-capable {
        position 2;
        description
          "Ap capability for spatial streams mode";
      }
      bit antenna-selection-restricted-capable {
        position 3;
        description
          "Ap capability for antenna selection mode";
      }
      bit avc-cnf-capable {
        position 4;
        description
          "Ap capability for avc fnf mode";
      }
      bit rxsop-threshold-capable {
        position 5;
        description
          "Ap capability for rxsop threshold mode";
      }
      bit fabric-capability {
        position 6;
        description
          "Ap capability for fabric mode";
      }
      bit rogue-rldp-capable {
        position 7;
        description
          "Ap capability for rogue rldp mode";
      }
      bit barbados-external-antenna-sku-capable {
        position 8;
        description
          "Barbados Ap capability for external antenna mode";
      }
      bit barbados-internal-antenna-sku-capable {
        position 9;
        description
          "Barbados Ap capability for internal antenna mode";
      }
      bit barbados-location-antenna-sku-capable {
        position 10;
        description
          "Barbados Ap capability for location antenna mode";
      }
      bit remote-lan-capable {
        position 11;
        description
          "Ap capability for remote lan mode";
      }
      bit dot11ac-160mhz-channel-width-capable {
        position 12;
        description
          "Ap capability for dot11 channel width mode";
      }
      bit location-optimized-monitor-mode-capable {
        position 13;
        description
          "Ap capability for optimized monitor  mode";
      }
      bit avc-fnf-fabric-capable {
        position 14;
        description
          "Ap capability for avc fabric mode";
      }
      bit telent-capable {
        position 15;
        description
          "Ap capability for telnet mode";
      }
      bit ap-packet-capture-capable {
        position 16;
        description
          "Ap capability for packet catpure mode";
      }
      bit ap-cts-capable {
        position 17;
        description
          "Ap capability for cts mode";
      }
      bit ap-qca-spectrum-intelligence-capable {
        position 18;
        description
          "Ap capability for spectrum intelligence mode";
      }
      bit fips-capable {
        position 19;
        description
          "Ap capability for fips mode";
      }
      bit is-dot1x-port-auth-capable {
        position 20;
        description
          "Ap capability for dot1x port authentication mode";
      }
      bit ap-tracing-capable {
        position 21;
        description
          "AP capability for tracing enable from Controller";
      }
      bit ap-wpa3-capable {
        position 22;
        description
          "Ap capability for WPA3 authentication";
      }
      bit is-lag-capable {
        position 23;
        description
          "AP capability for lag mode";
      }
      bit ap-eta-capable {
        position 24;
        description
          "Ap capability for Encrypted Traffic Analytics";
      }
      bit is-li-capable {
        position 25;
        description
          "AP capability for LI";
      }
      bit office-extend-capable {
        position 26;
        description
          "AP capability for office extend mode";
      }
      bit eth2-rlan-capable {
        position 27;
        description
          "AP capability for Ethernet2 as RLAN port, when LAG is disabled";
      }
      bit nbn-capable {
        position 28;
        description
          "AP capability for NBN features";
      }
    }
    description
      "AP Capabilities";
  }

  grouping reboot-statistics {
    description
      "Access Point reboot Statistics";
    leaf reboots {
      type uint16;
      description
        "AP reboot count due to manual reset";
    }
    leaf ac-initiated {
      type uint16;
      description
        "AP reboot count due to ac initiation";
    }
    leaf link-failure {
      type uint16;
      description
        "AP reboot count due to link failure";
    }
    leaf sw-failure {
      type uint16;
      description
        "AP reboot count due to software failure";
    }
    leaf hw-failure {
      type uint16;
      description
        "AP reboot count due to Hardware failure";
    }
    leaf unknown-failure {
      type uint16;
      description
        "AP reboot count due to unknown failure";
    }
    leaf reboot-reason {
      type wireless-types:spam-ap-reboot-reason;
      description
        "Reason for Access Point last reboot";
    }
    leaf reboot-types {
      type wireless-types:spam-ap-reboot-types;
      description
        "Type of Access Point reboot";
    }
  }

  grouping wtp-board-data {
    description
      "AP Board details";
    leaf model {
      type string;
      description
        "Access Point model";
    }
    leaf wtp-serial-num {
      type string;
      description
        "Access Point Serial Number";
    }
    leaf card-id {
      type uint16;
      description
        "Access Point card ID";
    }
    leaf card-rev {
      type uint16;
      description
        "Access Point card Revision number";
    }
    leaf wtp-enet-mac {
      type yang:mac-address;
      description
        "Acess Point Ethernet MAC Address";
    }
  }

  grouping ap-ip-cfg-data {
    description
      "IP address of AP";
    leaf is-static-ap-ipaddr {
      type boolean;
      description
        "Value of True implies 
         Access Point is using static IP Address, and value of False
         implies Access Point is using DHCP IP";
    }
    leaf ap-ip-addr {
      type inet:ipv4-address;
      description
        "Static IPv4 Address configuration for the AP.";
    }
    leaf ap-ipv6-addr {
      type inet:ip-address;
      description
        "Static IPv6 Address configuration for the AP.";
    }
    leaf ap-ip-netmask {
      type inet:ipv4-address;
      description
        "Netmask of the IPv4 address of the AP.";
    }
    leaf ap-prefix {
      type uint32;
      description
        "Prefix length of the IPv6 Address of the AP.";
    }
    leaf ap-ip-gateway {
      type inet:ipv4-address;
      description
        "Gateway for the IPv4 Address of the AP.";
    }
    leaf ap-ipv6-gateway {
      type inet:ip-address;
      description
        "Gateway for the IPv6 Address of the AP.";
    }
    leaf ap-ipv6-method {
      type uint8;
      description
        "Method used by AP to join over IPv6.";
    }
    leaf ap-fallback-ip {
      type inet:ip-address;
      description
        "The fallback address: AP will join over this address when it can't join over static-ip.";
    }
    leaf domain-name {
      type string;
      description
        "Access Point Domain name";
    }
    leaf ap-name-server {
      type inet:ip-address;
      description
        "Access Point Name Server IP Address";
    }
    leaf ap-name-server-type {
      type wireless-types:enm-ip-address-type;
      description
        "Type of the IP address of the name server";
    }
  }

  grouping ap-link-audit-cfg-data {
    description
      "Link audit data";
    leaf linkaudit-flag {
      type uint8;
      description
        "Link Audit state.
         Value 1 specifies Link Audit is enabled.
         Value 0 specifies Link Audit is disabled";
    }
    leaf linkaudit-delay-time {
      type uint32;
      description
        "Link latency recorded for this Access Point";
    }
    leaf linkaudit-max-time {
      type uint32;
      description
        "Maximum Link Latency recorded for the Access Point";
    }
    leaf linkaudit-min-time {
      type uint32;
      description
        "Minimum Link Latency recorded for the Access Point";
    }
    leaf linkaudit-rcv-time {
      type uint32;
      description
        "current Data Link Latency recorded for the Access point";
    }
  }

  grouping ap-tcp-mss-cfg-data {
    description
      "Configured TCP MSS value for client";
    leaf tcp-adjust-mss-state {
      type boolean;
      description
        "Adjusted TCP MSS value for client";
    }
    leaf tcp-adjust-mss-size {
      type uint16;
      description
        "TCP Maximum Segment Size for the AP.
         Permissible value are between 536 and 1363.
         This will also enable the TCP MSS flag for this AP.
         Value of 0 will disable the TCP MSS flag for this AP";
    }
  }

  grouping ap-universal-provision-cfg-data {
    description
      "Universal AP config";
    leaf is-universal-pid {
      type boolean;
      description
        "Value of True implies AP is Universal Access Point.
         A value of False implies AP is not universal Access Point";
    }
    leaf universal-prime-status {
      type string;
      description
        "Priming method of the Universal Access Point";
    }
  }

  grouping ap-pow-cfg-data {
    description
      "AP power config";
    leaf power-injector-state {
      type wireless-enum-types:power-injector-state;
      description
        "Power injector state";
    }
    leaf power-injector-sel {
      type wireless-enum-types:power-injector-selection;
      description
        "Specify power level";
    }
    leaf power-injector-macaddr {
      type yang:mac-address;
      description
        "Mac address of the switch port 
         that has a power Injector and is valid only when
         'power_injector_sel' is in 'installed' mode.
         If SET to 00:00:00:00:00:00, AP will detect the MAC address
         of the current switch port that has a Power Injector";
    }
    leaf pre-std-switch-enabled {
      type boolean;
      description
        "Pre-Standard state of the Access Point, enabled or disabled.
         Value of 'true' denotes Pre-Standard state is Enabled,
         Value of 'false' denotes Pre-Standard state is Disabled";
    }
    leaf power-injector-enabled {
      type boolean;
      description
        "Power Injector state, Enabled or Disabled.
         Value of 'true' denotes Power Injector state is Enabled,
         Value of 'false' denotes Power Injector state is Disabled";
    }
    leaf power-type {
      type wireless-enum-types:power-type;
      description
        "Type of power source being used for the Access Point";
    }
    leaf power-mode {
      type wireless-enum-types:power-mode-type;
      description
        "This notification is generated whenever an AP detects low 
         power from Ethernet.";
    }
  }

  grouping ap-sys-stats-data {
    description
      "Access Point system stats for CPU and memory usage";
    leaf cpu-usage {
      type uint8;
      description
        "Access Point CPU usage";
    }
    leaf memory-usage {
      type uint8;
      description
        "Access Point Memory usage";
    }
  }

  grouping ap-ether-cfg-data {
    description
      "Access Point Ethernet configuration data";
    leaf ether-port-speed {
      type wireless-enum-types:ap-eth-port-speed;
      description
        "Ethernet port speed";
    }
    leaf ethernet-port-duplex {
      type wireless-enum-types:ap-eth-port-duplex;
      description
        "True if Ethernet port is in Duplex mode";
    }
  }

  grouping ap-controller-cfg-data {
    description
      "Primary, Secondary Controller configuration for the Access Point";
    leaf primary-controller-name {
      type string;
      description
        "Name of the Primary Controller configured for the Access Point";
    }
    leaf secondary-controller-name {
      type string;
      description
        "Name of the Secondary Controller configured for the Access Point";
    }
    leaf primary-controller-ip-addr {
      type inet:ip-address;
      description
        "IP address of the Primary Controller configured for Access Point";
    }
    leaf secondary-controller-ip-addr {
      type inet:ip-address;
      description
        "IP address of the Secondary Controller configured for Access Point";
    }
    leaf tertiary-controller-name {
      type string;
      description
        "Name of the Tertiary Controller configured for the Access Point";
    }
    leaf tertiary-controller-ip-addr {
      type inet:ip-address;
      description
        "IP address of the Tertiary Controller configured for Access Point";
    }
    leaf backup-primary-controller-name {
      type string;
      description
        "Backup Primary Controller name during AP fallback";
    }
    leaf backup-secondary-controller-name {
      type string;
      description
        "Backup Secondary Controller name during AP fallback";
    }
    leaf backup-primary-controller-ip-addr {
      type inet:ip-address;
      description
        "Backup Primary Controller IP Address during AP fallback";
    }
    leaf backup-secondary-controller-ip-addr {
      type inet:ip-address;
      description
        "Backup Secondary Controller IP Address during AP fallback";
    }
    leaf fallback-enabled {
      type boolean;
      description
        "Value of True implies AP Fallback is Enabled";
    }
  }

  grouping ap-mgmt-cfg-data {
    description
      "Access Point Management configuration data";
    leaf is-telnet-enabled {
      type boolean;
      description
        "Value of 'true' indicates Telnet session
         can be established to the AP";
    }
    leaf is-ssh-enabled {
      type boolean;
      description
        "Value of 'true' indicates SSH session
         can be established to the AP";
    }
  }

  grouping ap-ext-module-cfg-data {
    description
      "AP External Module configuration data";
    leaf is-ext-module-enabled {
      type boolean;
      description
        "Specifies whether AP External Module is enabled or not";
    }
  }

  grouping ap-lawful-interception-cfg-data {
    description
      "Lawful Interception configuration data for Access Point";
    leaf is-lawful-interception-enabled {
      type boolean;
      description
        "Specifies whether Lawful Interception is enabled or not";
    }
    leaf timer-interval {
      type uint32;
      description
        "Timer interval in seconds for periodic Lawful Interception updates";
    }
  }

  grouping ap-persistent-ssid-cfg-data {
    description
      "Persistent SSID Broadcast configuration";
    leaf is-persistent-ssid-supported {
      type boolean;
      description
        "Specifies if Persistent SSID Broadcast is supported on this AP or AP mode";
    }
    leaf is-persistent-ssid-enabled {
      type boolean;
      description
        "Specifies whether Persistent SSID Broadcast is enabled or not";
    }
  }

  grouping ap-country-code-cfg-data {
    description
      "Access Point Country code configuration";
    leaf country-code {
      type string;
      description
        "Country Code configured for the Access Point";
    }
    leaf country-string {
      type string;
      description
        "Country Name for the Access Point";
    }
  }

  grouping ap-retransmit-cfg-data {
    description
      "AP retransmission configuration";
    leaf count {
      type uint8;
      description
        "Total number of times config data is retransmitted";
    }
    leaf interval {
      type uint8;
      description
        "Time duration after which config data will be retransmitted";
    }
  }

  grouping ap-timer-cfg-data {
    description
      "Access Point Timer configuration";
    leaf primary-discovery-timer {
      type uint8;
      description
        "Primary Discovery timer value that is configured";
    }
    leaf primed-join-timer {
      type uint8;
      description
        "Primary join timer value that is configured";
    }
    leaf fast-heart-beat-timeout {
      type uint8;
      description
        "Timeout value for the heart beat timer";
    }
    leaf discovery-timeout {
      type uint8;
      description
        "Discovery timeout value that is configured";
    }
    leaf heart-beat-timeout {
      type uint8;
      description
        "Heart beat timeout value that is configured";
    }
  }

  grouping ap-report-interval {
    description
      "Report interval value for Access Point Radio";
    leaf radio-24ghz {
      type uint32;
      description
        "Report interval for 2.4GHz radio in seconds";
    }
    leaf radio-5ghz {
      type uint32;
      description
        "Report interval for 5GHz radio in seconds";
    }
  }

  grouping st-ap-oper-config {
    description
      "Access Point Operational data";
    leaf wtp-mac {
      type yang:mac-address;
      description
        "MAC Address of the Access Point Radio";
    }
    leaf radio-id {
      type uint32;
      description
        "Radio identifier of the Access Point";
    }
    leaf admin-state {
      type wireless-enum-types:admin-state;
      description
        "Admin state of the Access Point";
    }
    container ap-ip-cfg {
      description
        "Access Point IP Address configuration";
      uses wireless-access-point-oper:ap-ip-cfg-data;
    }
    container ap-ctrlr-cfg {
      description
        "Controller configuration for the Access Point";
      uses wireless-access-point-oper:ap-controller-cfg-data;
    }
    container ap-mgmt-cfg {
      description
        "Access Point Management data";
      uses wireless-access-point-oper:ap-mgmt-cfg-data;
    }
    container ap-prov-cfg {
      description
        "Access Point universal provision configuration";
      uses wireless-access-point-oper:ap-universal-provision-cfg-data;
    }
    container ap-pow-cfg {
      description
        "Access Point power configuration";
      uses wireless-access-point-oper:ap-pow-cfg-data;
    }
    container ap-sys-stats-cfg {
      description
        "Access Point system statistics";
      uses wireless-access-point-oper:ap-sys-stats-data;
    }
    container ipv4-tcp-mss-cfg {
      description
        "Configured IPv4 TCP MSS value for client";
      uses wireless-access-point-oper:ap-tcp-mss-cfg-data;
    }
    container ipv6-tcp-mss-cfg {
      description
        "Configured IPv6 TCP MSS value for client";
      uses wireless-access-point-oper:ap-tcp-mss-cfg-data;
    }
    container ap-country-cfg {
      description
        "Access Point country code configuration";
      uses wireless-access-point-oper:ap-country-code-cfg-data;
    }
    container ether-port-cfg {
      description
        "Ethernet port configuration of the Access Point";
      uses wireless-access-point-oper:ap-ether-cfg-data;
    }
    container link-audit-cfg {
      description
        "Link audit data";
      uses wireless-access-point-oper:ap-link-audit-cfg-data;
    }
    container timer-cfg {
      description
        "Access Point timer configuration";
      uses wireless-access-point-oper:ap-timer-cfg-data;
    }
    container retransmit-cfg {
      description
        "Access Point retransmission configuration";
      uses wireless-access-point-oper:ap-retransmit-cfg-data;
    }
    leaf lsc-provision-inprogress {
      type boolean;
      description
        "True if AP is under LSC provision state";
    }
    leaf fips-enabled {
      type boolean;
      description
        "Is FIPS mode enabled";
    }
    leaf wlancc-enabled {
      type boolean;
      description
        "Is wireless common criteria mode enabled";
    }
    leaf location {
      type string;
      description
        "User specified location of the AP.
         While configuring AP, user should specify a location for
         the AP so that its easy to figure out for some one where
         the AP is located.";
    }
    leaf stat-tmr {
      type uint32;
      description
        "Time interval in seconds after which
         Dot11 radio Stats is sent from Access Point to Switch. If not 
         configured this value is 0 which means never send the stats.";
    }
    container rogue-cfg {
      description
        "Captures the rogue parameters";
      uses ap-types:st-rogue-params;
    }
    leaf slot-id {
      type uint32;
      description
        "slot id of the radio";
    }
    leaf third-party {
      type uint32;
      description
        "third party data";
    }
    leaf mtu {
      type uint32;
      description
        "Maximum transmission unit size for the client";
    }
    leaf is-jumbo-mtu-enabled {
      type boolean;
      description
        "Flag to specify whether the jumbo mtu is enabled/disabled";
    }
    leaf is-hreap {
      type uint32;
      description
        "Specify whether the remote AP is H-REAP or REAP";
    }
    leaf public-saftey-state {
      type uint32;
      description
        "Specify the public safety state";
    }
    leaf wtp-mode {
      type wireless-types:enm-ewlc-spam-ap-modes;
      description
        "Mode of the AP to which the Mobile Station is associated";
    }
    leaf ap-sub-mode {
      type boolean;
      description
        "Specifies if this AP is used as WIPS AP.
         value of 'true' indicates this AP is a WIPS AP.
         value of 'false' indicates this AP is not a WIPS AP.
         This applies only when the AP is either in Local or in Monitor mode";
    }
    leaf ap-remote-debug-mode {
      type boolean;
      description
        "Specifies if the Remote Mode is supported on this AP or not";
    }
    leaf led-state-enabled {
      type boolean;
      description
        "Specifies whether the LED state of this Access Point is enabled or disabled.";
    }
    leaf reset-button-state {
      type boolean;
      description
        "Specifies the Access Point Reset button state";
    }
    leaf mfp-validation {
      type boolean;
      description
        "Specifies whether the AP should
         validate the management frames received by it
         in accordance with the MFP version or not.";
    }
    leaf mfp-validation-str {
      type string;
      description
        "Specifies whether the AP should
         validate the management frames received by it
         in accordance with the MFP version or not.";
    }
    leaf user-cfg-mode {
      type uint32;
      description
        "Specify the AP user mode (Customized/Automatic)";
    }
    leaf user-name {
      type string;
      description
        "AP user name";
    }
    leaf dot1x-user-cfgmode {
      type uint32;
      description
        "Specifies AP 802.1X User Mode (Global/Customized).
         A value of 0 denotes Not Configured";
    }
    leaf dot1x-username {
      type string;
      description
        "802.1x supplicant username that is to be
         inherited by all Access Points that join the Controller.";
    }
    leaf dot1x-password {
      type string;
      description
        "802.1x supplicant Password that is to be
         inherited by all Access Points that join the Controller.";
    }
    leaf log-host-ipaddr {
      type inet:ip-address;
      description
        "Cisco AP System Logging Host ip address";
    }
    leaf log-trap-level {
      type wireless-types:syslog-trap-level;
      description
        "Logging Trap Severity Level";
    }
    leaf link-encryption-enabled {
      type boolean;
      description
        "Specifies whether encryption between
         controller and AP is enabled or not. Encryption
         can only be enabled if ESM card in controller is plugged in.
         
         A value of 'true' enables encryption between controller and AP.
         A value of 'false' disables encryption between controller and AP.";
    }
    leaf home-ap-enabled {
      type boolean;
      description
        "Specifies whether home AP mode is enabled or not";
    }
    leaf ap-antenna-band-mode {
      type wireless-enum-types:ant-band-mode;
      description
        "Specifies the mode of Antenna band. For 
         access points, in which this variable is not relevant,
         value of 'Not Applicable' will be returned.
         In the dual band mode, only two dual band antennas are used, 
         connected to ports 1 and 2. In this case, both bands share these antennas.";
    }
    leaf console-login-status {
      type wireless-enum-types:console-login-status;
      description
        "Console Login State";
    }
    leaf floor {
      type uint32;
      description
        "Floor on which AP resides";
    }
    leaf remote-lan-override {
      type boolean;
      description
        "Override remote lan on that AP";
    }
    container reporting-interval {
      description
        "Reporting Interval for Client Stats";
      uses wireless-access-point-oper:ap-report-interval;
    }
    container tunnel {
      description
        "Captures the rogue parameters";
      uses ap-types:st-tunnel-cfg;
    }
    container ap-ext-module-cfg {
      description
        "AP External Module configuration parameters";
      uses wireless-access-point-oper:ap-ext-module-cfg-data;
    }
    leaf dot1x-eap-type {
      type ap-types:enm-ap-dot1x-eap-type;
      description
        "Dot1x EAP Type";
    }
    leaf lsc-ap-auth-type {
      type ap-types:enm-lsc-ap-auth-state-type;
      description
        "LSC AP Auth Type";
    }
    container ap-lawful-interception-cfg {
      description
        "Lawful Interception configuration parameters";
      uses wireless-access-point-oper:ap-lawful-interception-cfg-data;
    }
    container persistent-ssid-cfg {
      description
        "Persistent SSID broadcast configuration parameters";
      uses wireless-access-point-oper:ap-persistent-ssid-cfg-data;
    }
    leaf ap-lag-enabled {
      type boolean;
      description
        "AP Lag status, TRUE indicates the LAG support is enabled, FALSE indicates the LAG support is disabled.";
    }
    leaf vlan-tag-state {
      type wireless-access-point-oper:enm-vlan-state;
      description
        "Indicates the status of Ethernet vlan tagging on AP";
    }
    leaf vlan-tag-id {
      type uint16;
      description
        "Vlan id used for tagging AP Ethernet packets";
    }
  }

  grouping wtp-descriptor-data {
    description
      "Structure stores the details about the WTP";
    leaf max-radio-slots {
      type uint8;
      description
        "Maximum radio slots supported by the AP";
    }
    leaf radio-slots-in-use {
      type uint8;
      description
        "Radio slots in use in AP";
    }
    leaf encryption-capabilities {
      type boolean;
      description
        "Encryption capabilities of the AP";
    }
    container hw-ver {
      description
        "Hardware version of the AP";
      uses wireless-types:version-info;
    }
    container sw-ver {
      description
        "Software version of the AP";
      uses wireless-types:version-info;
    }
    container boot-ver {
      description
        "boot version of the AP";
      uses wireless-types:version-info;
    }
    container boot-sw-ver {
      description
        "Boot software version of the AP";
      uses wireless-types:version-info;
    }
  }

  grouping board-data-opt {
    description
      "AP Board details";
    leaf antenna-type {
      type uint8;
      description
        "AP Antenna type";
    }
    leaf remote {
      type uint8;
      description
        "Denote whether the AP is remote or local";
    }
    leaf join-priority {
      type uint8;
      description
        "AP join priority";
    }
  }

  grouping wtp-ssid-and-policy-info {
    description
      "AP tag relation information";
    leaf policy-tag-name {
      type string;
      description
        "policy tag associated with AP";
    }
    leaf ssid-tag-name {
      type string;
      description
        "TO BE REMOVED";
    }
  }

  grouping wtp-site-tag-info {
    description
      "Site tag associated with the AP";
    leaf site-tag-name {
      type string;
      description
        "AP site tag name";
    }
    leaf ap-profile {
      type string;
      description
        "AP profile associated with the AP ";
    }
    leaf flex-profile {
      type string;
      description
        "Flex profile associated with a remote AP";
    }
  }

  grouping wtp-rf-tag-info {
    description
      "RF tag information for the AP";
    leaf rf-tag-name {
      type string;
      description
        "RF tag name associated with the AP";
    }
    leaf dot11a-rf-profile {
      type string;
      description
        "5GHz band RF profile associated with the AP ";
    }
    leaf dot11b-rf-profile {
      type string;
      description
        "2.4GHz RF profile associated with the AP";
    }
  }

  grouping wtp-tags-data {
    description
      "WTP tag associatios";
    container ssid-mapping {
      description
        "Policy tag information for the AP";
      uses wireless-access-point-oper:wtp-ssid-and-policy-info;
    }
    container site-tag {
      description
        "Site tag information for the AP";
      uses wireless-access-point-oper:wtp-site-tag-info;
    }
    container rf-tag {
      description
        "RF tag information for the AP";
      uses wireless-access-point-oper:wtp-rf-tag-info;
    }
    leaf misconfigured-tag {
      type uint8;
      description
        "Indicates if an AP is associated to misconfigured tag";
    }
    leaf tag-source {
      type ap-types:enm-ap-tag-source;
      description
        "Specifies the source of resolved tags for the AP";
    }
    leaf location {
      type string;
      description
        "Specifies the location where tags came from";
    }
    leaf clients-joined {
      type uint64;
      description
        "Total number of clients joined this AP";
    }
    leaf clients-on-11a {
      type uint64;
      description
        "Total number of clients joined this AP on 802.11a";
    }
    leaf clients-on-11b {
      type uint64;
      description
        "Total number of clients joined this AP on 802.11b";
    }
    leaf is-ap-misconfigured {
      type wireless-enum-types:ap-misconfig-state;
      description
        "True if AP is misconfigured";
    }
    leaf is-policy-tag-misconfigured {
      type wireless-enum-types:ap-misconfig-state;
      description
        "True if policy tag is misconfigured";
    }
    leaf is-site-tag-misconfigured {
      type wireless-enum-types:ap-misconfig-state;
      description
        "True if site tag is misconfigured";
    }
    leaf is-rf-tag-misconfigured {
      type wireless-enum-types:ap-misconfig-state;
      description
        "True if rf tag is misconfigured";
    }
    leaf is-flex-profile-misconfigured {
      type wireless-enum-types:ap-misconfig-state;
      description
        "True if flex profile is misconfigured";
    }
    leaf is-ap-profile-misconfigured {
      type wireless-enum-types:ap-misconfig-state;
      description
        "True if ap profile is misconfigured";
    }
    leaf is-rf-profile-24-misconfigured {
      type wireless-enum-types:ap-misconfig-state;
      description
        "True of 2.4Ghz RF profile is misconfigured";
    }
    leaf is-rf-profile-5-misconfigured {
      type wireless-enum-types:ap-misconfig-state;
      description
        "true of 5Ghz RF profile is misconfigured";
    }
    leaf is-ap-tag-registration-done {
      type wireless-enum-types:ap-tag-register-state;
      description
        "Enum for ap tag registration";
    }
  }

  grouping st-resolved-tags-data {
    description
      "Resolved tags information";
    leaf resolved-policy-tag {
      type string;
      description
        "Resolved Policy tag information for the AP";
    }
    leaf resolved-site-tag {
      type string;
      description
        "Resolved Site tag information for the AP";
    }
    leaf resolved-rf-tag {
      type string;
      description
        "Resolved RF tag information for the AP";
    }
  }

  grouping wtp-udi-info {
    description
      "WTP UDI information";
    leaf prod-id {
      type string;
      description
        "Product ID of the device ";
    }
    leaf ver-id {
      type string;
      description
        "Version ID of the device";
    }
    leaf serial-num {
      type string;
      description
        "Serial number of the device ";
    }
    leaf ent-name {
      type string;
      description
        "Name of the device";
    }
    leaf ent-desc {
      type string;
      description
        "Description for the device";
    }
  }

  grouping hyperlocation-ap-data {
    description
      "Hyperlocation AP data";
    leaf hyperlocation-method {
      type wireless-types:enm-hyperlocation-method;
      description
        "Hyperlocation method details";
    }
    leaf per-ap-hl-tlv-rcvd {
      type wireless-types:enm-hyperlocation-ap-tlv-received;
      description
        "Indicates whether Hyperlocation flag (TLV) was received from AP";
    }
    leaf cmx-ip {
      type inet:ip-address;
      description
        "IP address of CMX assigned to the AP for Hyperlocation";
    }
  }

  grouping xm-info {
    description
      "External module details";
    leaf-list goodness-field {
      type int8;
      max-elements "16";
      ordered-by user;
      description
        "External module goodness field";
    }
    leaf numeric-id {
      type uint16;
      description
        "External module id";
    }
    leaf-list version {
      type uint8;
      max-elements "2";
      ordered-by user;
      description
        "External module version";
    }
    leaf-list product-id {
      type int8;
      max-elements "18";
      ordered-by user;
      description
        "External module product id";
    }
    leaf-list serial-number {
      type int8;
      max-elements "11";
      ordered-by user;
      description
        "External module serial number";
    }
    leaf max-power {
      type uint32;
      description
        "External module maximum supported power";
    }
    leaf-list eeprom-size {
      type uint8;
      max-elements "4";
      ordered-by user;
      description
        "External module EEPROM Size";
    }
    leaf xm-cookie-version {
      type uint8;
      description
        "External module cookie version";
    }
    container inventory {
      description
        "Inventory data";
      uses wireless-access-point-oper:wtp-udi-info;
    }
    leaf module-name {
      type string;
      description
        "External module name";
    }
    leaf version-string {
      type string;
      description
        "External module Version";
    }
    leaf serial-number-string {
      type string;
      description
        "External module Serial Number";
    }
    leaf product-id-string {
      type string;
      description
        "External module product id";
    }
    leaf module-type {
      type string;
      description
        "Defines the type of external module:
         WSM (.11n), 11ac Wave1,
         3G module, 3G/4G Module,
         Expansion Module,
         Hyperlocation Module w/Antenna,
         Hyperlocation Module w/BLE Antenna,
         Hyperlocation Module";
    }
    leaf module-description {
      type string;
      description
        "External module description";
    }
    leaf module-capabilities {
      type string;
      description
        "Capabilities supported by external module (RLAN, 3G etc.,)
         Each capability will be appended by status & can be UP/DOWN
         Format of output:
         Capability-1 (UP/DOWN), Capability-2 (UP/DOWN),.., & so on
         Example: RLAN (DOWN), 3G (UP)";
    }
    leaf module-state {
      type string;
      description
        "Current state information sent by external module
         For example:
         UP,
         DOWN: Not enough power resource,
         DOWN: *NOT* Authentic";
    }
  }

  grouping wtp-xm-info {
    description
      "WTP extension module information";
    leaf is-module-present {
      type boolean;
      description
        "specifies whether an external module is present or not";
    }
    leaf enable {
      type boolean;
      description
        "External module enabled";
    }
    container xm {
      description
        "External module info";
      uses wireless-access-point-oper:xm-info;
    }
  }

  grouping cdp-cache-list {
    description
      "Cache of AP CDP neighbors";
    leaf-list buffer {
      type uint32;
      max-elements "4";
      ordered-by user;
      description
        "CDP cache list buffer";
    }
  }

  grouping capwap-wtp-data {
    description
      "Base AP operational data";
    leaf ap-operation-state {
      type wireless-access-point-oper:enum-ap-state;
      description
        "Operation State of the AP. When AP associates with the
         Switch its state will be associated. When AP is 
         disassociated from the Switch, its state will be 
         disassociating. The state is downloading when the AP is 
         downloading its firmware.";
    }
    leaf wtp-mac {
      type yang:mac-address;
      description
        "MAC address of AP radio interface";
    }
    leaf ip-addr {
      type string;
      description
        "IP Address of the Access Point";
    }
    leaf ipv6-joined {
      type uint8;
      description
        "True if the AP has joined in IPv6 mode";
    }
    leaf wtp-ip-addr {
      type inet:ipv4-address;
      description
        "IPv4 Address of the Access Point";
    }
    leaf admin-state {
      type uint8;
      description
        "Admin state of the Access Point";
    }
    leaf location {
      type string;
      description
        "User specified location of this AP.
         While configuring AP, user should specify a location for
         the AP so that its easy to figure out for some one where
         the AP is located.";
    }
    leaf country-code {
      type string;
      description
        "Country Code configured for the Access Point";
    }
    leaf name {
      type string;
      description
        "Access Point Name";
    }
    container board-data {
      description
        "Access Point Board Data";
      uses wireless-access-point-oper:wtp-board-data;
    }
    container descriptor-data {
      description
        "Access Point FW,HW information";
      uses wireless-access-point-oper:wtp-descriptor-data;
    }
    leaf max-ctrl-pkt-size {
      type uint16;
      description
        "Maximum size of CAPWAP control packet";
    }
    container board-data-opt {
      description
        "Access Point Additional Board data option";
      uses wireless-access-point-oper:board-data-opt;
    }
    leaf num-slots {
      type uint8;
      description
        "Number of Radio Interfaces present in the Access Point";
    }
    leaf clear-mode {
      type boolean;
      description
        "Remove the current mode on AP and choose a mode from Site tag config";
    }
    leaf wtp-mode {
      type wireless-types:enm-ewlc-spam-ap-modes;
      description
        "Mode of the AP to which the Mobile Station is associated.";
    }
    leaf wtp-type-mib-enum {
      type uint8;
      description
        "model of the AP.";
    }
    leaf dart-is-connected {
      type uint8;
      description
        "Xor Dart connector status.";
    }
    leaf dart-is-connected-str {
      type string;
      description
        "Xor Dart connector status in string";
    }
    leaf is-cisco-ap {
      type boolean;
      description
        "True if this is a Cisco AP";
    }
    leaf is-master {
      type boolean;
      description
        "True if the AP is configured as MASTER AP during efficient image download";
    }
    leaf num-ports {
      type uint8;
      description
        "Number of ports on AP";
    }
    leaf lag-enabled {
      type boolean;
      description
        "True if Capwap LAG is enabled";
    }
    leaf lag-capable {
      type boolean;
      description
        "True if AP is CAPWAP LAG capable";
    }
    leaf multi-window-support {
      type boolean;
      description
        "True if AP support capwap multi window";
    }
    leaf window-size-received {
      type uint16;
      description
        "Maximum capwap window size supported by the Access Point";
    }
    leaf window-size-active {
      type uint16;
      description
        "AP capwap window size";
    }
    leaf model {
      type string;
      description
        "Model number of the AP";
    }
    leaf sw-version {
      type string;
      description
        "AP Software Version";
    }
    leaf capwap-iifid {
      type uint32;
      description
        "iifid capwap available";
    }
    container tag-info {
      description
        "Tags associated with AP";
      uses wireless-access-point-oper:wtp-tags-data;
    }
    container resolved-tag-info {
      description
        "Resolved tags for the AP";
      uses wireless-access-point-oper:st-resolved-tags-data;
    }
    container hyperlocation-data {
      description
        "Information on hyperlocation feature";
      uses wireless-access-point-oper:hyperlocation-ap-data;
    }
    container xm-data {
      description
        "External module data";
      uses wireless-access-point-oper:wtp-xm-info;
    }
    container backup-sw-version {
      description
        "Backup image version of the AP.";
      uses wireless-types:version-info;
    }
    container mini-ios-version {
      description
        "Recovery image version of the AP.";
      uses wireless-types:version-info;
    }
    leaf cert-type {
      type wireless-access-point-oper:enm-cert-type;
      description
        "Enum values denoting AP Certificate Type.
         1 : manufactureinstalled : Manufacture Installed Certificate type (MIC).
         2 : selfsigned : Self Signed Certificate type (SSC).
         3 : localsignificance : Local Significance.";
    }
    leaf ap-boot-time {
      type yang:date-and-time;
      description
        "Last AP reboot Date and Time";
    }
    leaf join-time {
      type yang:date-and-time;
      description
        "Date and Time at which AP joined";
    }
    leaf join-time-taken {
      type uint32;
      description
        "Time taken in hundredths of a second for the AP to join the controller";
    }
    leaf last-up-time {
      type uint32;
      description
        "Last Uptime";
    }
    leaf ap-model-short {
      type string;
      description
        "AP model info";
    }
    leaf cdp-enable {
      type wireless-access-point-oper:enum-cdp-enable-state;
      description
        "True if CDP is enabled or not on the Access Point";
    }
    container cdp-cache-index-list {
      description
        "CDP cache index list";
      uses wireless-access-point-oper:cdp-cache-list;
    }
    leaf is-fabric-ap {
      type boolean;
      description
        "True if AP is fabric AP";
    }
    leaf lisp-state {
      type wireless-access-point-oper:enum-lisp-query-state;
      description
        "Lisp query state";
    }
    leaf sniffer-ap-ifid {
      type uint32;
      description
        "Sniffer product ifid";
    }
    leaf int-if-num {
      type uint32;
      description
        "Port on the Switch on which this APs traffic is coming through.";
    }
    leaf monitor-mode-opt-type {
      type wireless-enum-types:lomm-mode-type;
      description
        "Monitor mode optimization type on the Access Point
         all      - All optimization is enabled 
         tracking - Tracking is optimized 
         wips     - WIPS optimization is enabled
         none     - No optimization is enabled";
    }
    leaf max-number-of-ethernet-slots {
      type uint32;
      description
        "Maximum number of Ethernet interfaces supported on the AP";
    }
    list radio-slot-data {
      key "wtp-mac radio-slot-id";
      description
        "Information about radio slot";
      uses wireless-access-point-oper:radio-slot-base-info;
      uses wireless-types:radio-slot-key;
    }
    container reboot-stats {
      description
        "Access Point reboot statistics";
      uses wireless-access-point-oper:reboot-statistics;
    }
    leaf ap-crash-file {
      type string;
      description
        "Name of Access Point crash file";
    }
    leaf ap-radio-2g-crash-file {
      type string;
      description
        "Name of 2.4GHz radio crash file";
    }
    leaf ap-radio-5g-crash-file {
      type string;
      description
        "Name of 5GHz radio crash file";
    }
    leaf-list slot-type {
      type uint8;
      max-elements "4";
      ordered-by user;
      description
        "Container of slots";
    }
    leaf ap-capability {
      type wireless-access-point-oper:flag-ap-capability;
      description
        "AP capability flags";
    }
    leaf mesh-ap-role {
      type wireless-types:ap-role;
      description
        "Role of bridge mode AP. It can either be Root AP or Mesh AP.";
    }
    leaf ap-li-oper-state {
      type boolean;
      description
        "True if Lawful-Interception is enabled on AP";
    }
    leaf num-rlan-ports {
      type uint8;
      description
        "Number of RLAN ports supported";
    }
    leaf rlan-slot-id {
      type uint8;
      description
        "Slot id used for RLAN";
    }
    leaf rlan-port-can-be-zero {
      type boolean;
      description
        "True if AP sends zero as first RLAN port";
    }
    leaf usb-override {
      type boolean;
      description
        "Indicates if USB status is to be overridden.
         When enabled, USB status is taken from AP's local info.
         When disabled, USB status is taken from AP profile";
    }
    container usb-data {
      description
        "Detailed data about USB module and product information";
      uses wireless-access-point-oper:wtp-xm-info;
    }
  }

  grouping radio-slot-base-info {
    description
      "Base info of radio slot";
    leaf reg-domain-set {
      type boolean;
      description
        "True if Regulatory domain is valid";
    }
    leaf reg-domain-code {
      type uint16;
      description
        "Regulatory domain code for radio slot";
    }
    leaf radio-type {
      type uint32;
      description
        "Radio type of the slot";
    }
    leaf radio-mode {
      type uint8;
      description
        "Mode of the radio slot - 
         local, monitor, remote, sniffer etc.";
    }
    leaf radio-subtype {
      type uint8;
      description
        "Subtype of the radio slot.
         main(1)   :radio operates normally. 
         rxOnly(2) :NOS radio type,which is explicitly used for monitor mode operation.
         slaveAc(3):x-ale radio type is only for local mode.";
    }
    leaf radio-subband {
      type uint8;
      description
        "Sub band on which this radio slot operates.";
    }
    leaf admin-state {
      type uint8;
      description
        "AP radio slot Admin status.
         A value of 'true' indicates Admin state as Up.
         A value of 'false' indicates Admin state as Down.";
    }
    leaf oper-state {
      type uint8;
      description
        "AP radio slot operational status";
    }
    leaf config-state {
      type uint8;
      description
        "AP radio slot config state";
    }
    leaf slot-shut-reason {
      type wireless-types:enm-shut-down-reason;
      description
        "Reason for AP radio slot shutdown";
    }
  }

  grouping ap-ethernet-intf-id {
    description
      "AP Ethernet interface info";
    leaf wtp-mac {
      type yang:mac-address;
      description
        "AP Ethernet interface MAC Address";
    }
    leaf if-index {
      type uint16;
      description
        "AP Ethernet interface index";
    }
  }

  grouping ap-ethernet-intf-info {
    description
      "AP Ethernet interface statistics";
    leaf if-name {
      type string;
      description
        "Ethernet interface Name";
    }
    leaf speed {
      type wireless-enum-types:ap-eth-port-speed;
      description
        "AP Ethernet interface speed";
    }
    leaf rx-pkts {
      type uint32;
      description
        "Number of packets received from Mobile Station";
    }
    leaf tx-pkts {
      type uint32;
      description
        "Number of packets sent to Mobile Station";
    }
    leaf discard-pkts {
      type uint32;
      description
        "Number of packets discarded in AP Ethernet interface";
    }
    leaf ethernet-mac {
      type yang:mac-address;
      description
        "Ethernet MAC Address of the AP";
    }
    leaf admin-state {
      type boolean;
      description
        "AP's interface admin status
         A value of 'true' indicates admin state as Up
         A value of 'false' indicates admin state as Down";
    }
    leaf oper-status {
      type wireless-enum-types:oper-state;
      description
        "Operational state of the Ethernet interface on the AP";
    }
    leaf rx-ucast-pkts {
      type uint32;
      description
        "Total number of unicast packets received on the interface.";
    }
    leaf rx-non-ucast-pkts {
      type uint32;
      description
        "Total number of non-unicast or multicast packets received on the interface";
    }
    leaf tx-ucast-pkts {
      type uint32;
      description
        "Total number of unicast packets transmitted on the interface.";
    }
    leaf tx-non-ucast-pkts {
      type uint32;
      description
        "Total number of non-unicast or multicast packets transmitted on the interface";
    }
    leaf duplex {
      type uint32;
      description
        "Interface's duplex mode";
    }
    leaf link-speed {
      type uint32;
      description
        "Speed of the interface in units of 1,000,000 bits per second";
    }
    leaf rx-total-bytes {
      type uint32;
      description
        "Total number of bytes in the error-free packets received on the interface.";
    }
    leaf tx-total-bytes {
      type uint32;
      description
        "Total number of bytes in the error-free packets transmitted on the interface.";
    }
    leaf input-crc {
      type uint32;
      description
        "Total number of packets packets received with CRC error on the interface.";
    }
    leaf input-aborts {
      type uint32;
      description
        "Total number of packets aborted while receiving on the interface.";
    }
    leaf input-errors {
      type uint32;
      description
        "Sum of all errors in the packets while receiving on the interface.";
    }
    leaf input-frames {
      type uint32;
      description
        "Total number of packet received incorrectly having a CRC 
         error and a non-integer number of octets on the interface.";
    }
    leaf input-overrun {
      type uint32;
      description
        "Number of times the receiver
         hardware was incapable of handing received data to a 
         hardware buffer because the input rate exceeded the 
         receiver's capability to handle the data.";
    }
    leaf input-drops {
      type uint32;
      description
        "Total number of packets dropped
         while receiving on the interface because the queue was full";
    }
    leaf input-resource {
      type uint32;
      description
        "Total number of resource errors in packets received on the interface.";
    }
    leaf unknown-protocol {
      type uint32;
      description
        "Total number of packet discarded on
         the interface due to unknown protocol.";
    }
    leaf runts {
      type uint32;
      description
        "Number of packets that
         are discarded because they are smaller than the 
         medium's minimum packet size.";
    }
    leaf giants {
      type uint32;
      description
        "Number of packets that are discarded
         because they exceed the medium's maximum packet size.";
    }
    leaf throttle {
      type uint32;
      description
        "Total number of times the interface advised a sending NIC that it was 
         overwhelmed by packets being sent and to slow the pace of delivery.";
    }
    leaf resets {
      type uint32;
      description
        "Number of times that an interface has been completely reset.";
    }
    leaf output-collision {
      type uint32;
      description
        "Total number of packet retransmitted due to an Ethernet collision.";
    }
    leaf output-no-buffer {
      type uint32;
      description
        "Total number of packets discarded because there was no buffer space.";
    }
    leaf output-resource {
      type uint32;
      description
        "Total number of resource errors in packets transmitted on the interface.";
    }
    leaf output-underrun {
      type uint32;
      description
        "Number of times the transmitter has been running 
         faster than the router can handle.";
    }
    leaf output-errors {
      type uint32;
      description
        "Sum of all errors that prevented 
         the final transmission of packets out of the interface.";
    }
    leaf output-total-drops {
      type uint32;
      description
        "Total number of packets dropped while transmitting 
         from the interface because the queue was full.";
    }
    leaf cdp-enabled {
      type boolean;
      description
        "Specifies whether CDP is enabled or not";
    }
  }

  grouping ap-name-mac-map {
    description
      "Mapping between AP name and base radio mac";
    leaf instance-id {
      type uint32;
      description
        "Instance ID of the process handling the AP";
    }
    leaf wtp-name {
      type string;
      description
        "Access Point Name";
    }
    leaf wtp-mac {
      type yang:mac-address;
      description
        "Access Point Radio MAC Address";
    }
    leaf eth-mac {
      type yang:mac-address;
      description
        "Access Point Ethernet MAC Address";
    }
  }

  grouping ewlc-cdp-cache-data-key {
    description
      "Compound key of the table with device id as one of the attributes";
    leaf mac-addr {
      type yang:mac-address;
      description
        "Radio MAC address of the AP";
    }
    leaf cdp-cache-device-id {
      type string;
      description
        "The Device-ID string as reported in the CDP message";
    }
  }

  grouping cdp-cache-data-index-key {
    description
      "Compound key of the table with device index as one of the attributes";
    leaf wtp-mac-addr {
      type yang:mac-address;
      description
        "Radio MAC address of the AP";
    }
    leaf device-index {
      type uint32;
      description
        "A unique value for each device from which CDP messages are being received";
    }
  }

  grouping cdp-cache-neighbour-ip-addr {
    description
      "List of IP address.";
    leaf-list ip-address-value {
      type inet:ip-address;
      max-elements "9";
      ordered-by user;
      description
        "IP address value";
    }
  }

  grouping cdp-cache-data-op {
    description
      "An entry of the CDP cache data table";
    leaf ap-name {
      type string;
      description
        "Access Point Name";
    }
    leaf packet-expire-time {
      type uint32;
      description
        "The time left, in seconds, before the CDP neighbor entry gets aged-out";
    }
    leaf last-updated-time {
      type yang:date-and-time;
      description
        "Date and Time when cdp cache data was last updated";
    }
    leaf version {
      type uint8;
      description
        "Cisco Discovery Protocol version";
    }
    leaf cdp-cache-if-index {
      type int32;
      description
        "Local port on which LWAPP encapsulated CDP packets are received";
    }
    leaf cdp-cache-address {
      type string;
      description
        "Network-layer address of the device's SNMP-agent as reported in the CDP message";
    }
    leaf cdp-cache-version {
      type string;
      description
        "Software version of the neighboring device.";
    }
    leaf cdp-cache-device-port {
      type string;
      description
        "The Port-ID string as reported in the most 
         recent CDP message. This will typically be the value 
         of the ifName object (e.g., 'Ethernet0'). 
         The zero-length string indicates no Port-ID 
         field (TLV) was reported in the most recent CDP message.";
    }
    leaf cdp-cache-local-port {
      type string;
      description
        "Local port on which encapsulated CDP packets was received to AP";
    }
    leaf cdp-cache-platform {
      type string;
      description
        "The Device's Hardware Platform as reported in the 
         most recent CDP message. The zero-length string indicates 
         that no Platform field (TLV) was reported 
         in the most recent CDP message.";
    }
    leaf cdp-cache-capabilities {
      type uint32;
      description
        "The Device's Functional Capabilities as reported in the
         most recent CDP message.  For latest set of specific
         values, see the latest version of the CDP specification.
         The zero-length string indicates no Capabilities field
         (TLV) was reported in the most recent CDP message.";
    }
    leaf cdp-cache-capabilities-string {
      type string;
      description
        "The Device's Functional Capabilities as reported in the
         most recent CDP message.  For latest set of specific
         values, see the latest version of the CDP specification.
         The zero-length string indicates no Capabilities field
         (TLV) was reported in the most recent CDP message.";
    }
    leaf cdp-cache-ap-address {
      type inet:ip-address;
      description
        "An indication of the type of address contained 
         in the corresponding instance of 
         clcCdpApCacheAddress for the AP.";
    }
    leaf cdp-addr-count {
      type uint8;
      description
        "Number of network-layer addresses(IPv4 and IPv6) of the 
         device's SNMP-agent as reported in the most recent CDP message.";
    }
    leaf cdp-cache-ip-address-value {
      type inet:ip-address;
      description
        "The (first) network-layer address of the device's
         SNMP-agent as reported in the most recent CDP message.
         For example, if the the corresponding instance of
         clcCdpApCacheApAddressType had the value 
         'ip(1)', then this object would be an IP-address.";
    }
    container ip-address {
      description
        "All network-layer addresses(IPv4 and IPv6) of the device's
         SNMP-agent as reported in the most recent CDP message.";
      uses wireless-access-point-oper:cdp-cache-neighbour-ip-addr;
    }
    leaf cdp-cache-duplex {
      type wireless-enum-types:cdp-cache-duplex;
      description
        "This object denotes the duplex mode of the
         Ethernet interface between the AP and it's 
         neighboring CDP device, as reported in the most recent 
         CDP message. The value unknown(1) indicates no duplex
         mode field (TLV) was reported in the most recent CDP 
         message or the neighboring device is not connected to the 
         AP though ethernet interface.";
    }
    leaf cdp-cache-interface-speed {
      type uint32;
      description
        "This variable denotes the speed of the Ethernet
         interface between the AP  and it's neighboring CDP
         device. The unit is Mbps. This variable would be
         populated at AP join and periodically thereafter.
         The value none(1), would be shown if the interface 
         is not an ethernet interface.";
    }
  }

  grouping st-ap-discovery-info {
    description
      "AP Discovery Information";
    leaf wtp-mac {
      type yang:mac-address;
      description
        "Access Point radio MAC address";
    }
    leaf ethernet-mac {
      type yang:mac-address;
      description
        "Ethernet MAC Address of the Access Point";
    }
    leaf ap-ip-address {
      type inet:ip-address;
      description
        "IP address of the Access Point";
    }
    leaf num-discovery-req-recvd {
      type uint16;
      description
        "Number of discovery requests received from the AP";
    }
    leaf num-successful-discovery-resp-sent {
      type uint16;
      description
        "Number of discovery responses sent successfully to the AP";
    }
    leaf num-unsuccessful-discovery-req-processing {
      type uint16;
      description
        "Number of unsuccessful discovery requests processed";
    }
    leaf last-discovery-failure-type {
      type wireless-access-point-oper:enm-ap-discovery-failure-reason;
      description
        "Failure type of previous discovery request";
    }
    leaf last-discovery-failure-timestamp {
      type yang:date-and-time;
      description
        "Date and time of the last discovery message from the AP";
    }
    leaf last-successful-discovery-attempt-timestamp {
      type yang:date-and-time;
      description
        "Date and time of last successful discovery request";
    }
    leaf last-unsuccessful-discovery-attempt-timestamp {
      type yang:date-and-time;
      description
        "Date and time of last unsuccessful discovery request";
    }
  }

  grouping st-ap-join-info {
    description
      "AP Join Info Record";
    leaf wtp-mac {
      type yang:mac-address;
      description
        "Access Point MAC address";
    }
    leaf ip-addr {
      type string;
      description
        "Access Point IP Address";
    }
    leaf ethernet-mac {
      type yang:mac-address;
      description
        "Access Point Ethernet MAC Address";
    }
    leaf name {
      type string;
      description
        "Access Point Name";
    }
    leaf num-join-req-recvd {
      type uint16;
      description
        "Number of join requests received from the AP";
    }
    leaf num-successful-join-resp-sent {
      type uint16;
      description
        "Number of successful join response sent to the AP";
    }
    leaf num-unsuccessful-join-req-processing {
      type uint16;
      description
        "Number of unsuccessful join requests processed for the AP";
    }
    leaf last-join-failure-type {
      type wireless-access-point-oper:enm-ap-join-failure-reason;
      description
        "Last Join request failure reason for the AP";
    }
    leaf last-join-failure-timestamp {
      type yang:date-and-time;
      description
        "Time stamp of the last join failure message";
    }
    leaf last-successful-join-attempt-timestamp {
      type yang:date-and-time;
      description
        "Last successful join request time";
    }
    leaf last-unsuccessful-join-attempt-timestamp {
      type yang:date-and-time;
      description
        "Last unsuccessful join request time";
    }
    leaf num-config-req-recvd {
      type uint16;
      description
        "Number of configuration requests received from the AP";
    }
    leaf num-successful-config-resp-sent {
      type uint16;
      description
        "Number of successful configuration responses sent to the AP";
    }
    leaf num-unsuccessful-config-req-processing {
      type uint16;
      description
        "Number of unsuccessful configuration requests processed for the AP";
    }
    leaf last-config-failure-type {
      type wireless-access-point-oper:enm-ap-config-failure-reason;
      description
        "Last configuration failure type";
    }
    leaf last-config-failure-timestamp {
      type yang:date-and-time;
      description
        "Time stamp of the last config failure message";
    }
    leaf last-successful-config-attempt-timestamp {
      type yang:date-and-time;
      description
        "Last successful configuration time for the AP";
    }
    leaf last-unsuccessful-config-attempt-timestamp {
      type yang:date-and-time;
      description
        "Last unsuccessful configuration time for the AP";
    }
    leaf last-msg-decrypt-failure-reason {
      type string;
      description
        "Last message decrypt failure reason for the AP";
    }
    leaf last-ap-disconnect-reason {
      type wireless-access-point-oper:enm-ap-disconnect-reason;
      description
        "Last AP disconnect reason";
    }
    leaf last-ap-disconnect-timestamp {
      type yang:date-and-time;
      description
        "Time stamp of the last ap disconnection";
    }
    leaf last-error-type {
      type wireless-access-point-oper:enm-last-failure-type;
      description
        "Last error type";
    }
    leaf last-error-reason {
      type string;
      description
        "Last error reason";
    }
    leaf last-error-timestamp {
      type yang:date-and-time;
      description
        "Last error timestamp";
    }
    leaf is-joined {
      type boolean;
      description
        "True if AP has joined to the controller";
    }
    leaf last-update {
      type yang:date-and-time;
      description
        "Last update timestamp";
    }
  }

  grouping ap-state {
    description
      "Details of APs joins and disjoins with reason";
    leaf is-ap-joined {
      type boolean;
      description
        "Boolean value to know whether AP has joined or disjoined";
    }
    leaf timestamp {
      type yang:date-and-time;
      description
        "The timestamp at which AP joined/disjoined";
    }
    leaf last-disconnect-timestamp {
      type yang:date-and-time;
      description
        "The timestamp at which AP disjoined recently";
    }
    leaf num-of-time-disconnect {
      type uint32;
      description
        "Number of times AP disconnect with same reason";
    }
    leaf ap-disconnect-reason {
      type wireless-access-point-oper:enm-ap-disconnect-reason;
      description
        "AP disconnect reason";
    }
  }

  grouping all-ap-history {
    description
      "Details of all the APs joins and disjoins with reason";
    leaf ap-name {
      type string;
      description
        "Name of the AP";
    }
    leaf ethernet-mac {
      type yang:mac-address;
      description
        "The Ethernet MAC of AP";
    }
    list ap-state-ptr {
      description
        "List of AP join and disjoin";
      uses wireless-access-point-oper:ap-state;
    }
  }

  grouping qos-client-policy {
    description
      "This object specifies QoS policy map for client";
    leaf qos-pm-name {
      type string;
      description
        "Name of QoS policy-map";
    }
    leaf qos-pm-name-sent-to-ap {
      type string;
      description
        "Name of QoS policy-map sent to AP";
    }
    leaf qos-pm-sent-ap-name {
      type string;
      description
        "AP name where the QoS policy map sent";
    }
    leaf qos-pm-state {
      type wireless-access-point-oper:qos-pm-state;
      description
        "State of QoS policy map";
    }
    leaf qos-pm-type {
      type wireless-access-point-oper:qos-pm-type;
      description
        "Type of QoS policy map";
    }
    leaf qos-pm-status-str {
      type string;
      description
        "Display status string for QoS policy map";
    }
    leaf qos-pm-bind-timestamp {
      type yang:date-and-time;
      description
        "Timestamp at which QoS policy map got binded";
    }
    leaf-list pm-idx-sent-to-ap {
      type uint8;
      max-elements "64";
      ordered-by user;
      description
        "Policy map bind index sent to AP";
    }
    leaf qos-stats-last-cleared-timestamp {
      type yang:date-and-time;
      description
        "Timestamp at which QoS stats got cleared";
    }
  }

  grouping qos-bssid-policy {
    description
      "This object specifies QoS policy map for BSSID";
    leaf qos-pm-name {
      type string;
      description
        "Name of QoS policy-map";
    }
    leaf qos-pm-state {
      type wireless-access-point-oper:qos-pm-state;
      description
        "State of QoS policy map";
    }
    leaf qos-pm-type {
      type wireless-access-point-oper:qos-pm-type;
      description
        "Type of QoS policy map";
    }
    leaf qos-pm-status-str {
      type string;
      description
        "Display status string for QoS policy map";
    }
    leaf qos-pm-bind-timestamp {
      type yang:date-and-time;
      description
        "Timestamp at which QoS policy map got binded";
    }
    leaf qos-stats-last-cleared-timestamp {
      type yang:date-and-time;
      description
        "Timestamp at which QoS stats got cleared";
    }
  }

  grouping wmm-cac-stats {
    description
      "This object specifies the WMM TSPEC call statistics";
    leaf total-num-of-call-in-progress {
      type uint16;
      description
        "Total number of voice calls in progress";
    }
    leaf num-of-roam-call-in-progress {
      type uint16;
      description
        "Total number of roaming voice calls in progress";
    }
    leaf total-num-of-call-accepted {
      type uint16;
      description
        "Total number of calls accepted since AP joined";
    }
    leaf total-num-of-roam-calls-accepted {
      type uint16;
      description
        "Total number of roam calls accepted since AP joined";
    }
    leaf total-num-of-calls-rejected {
      type uint16;
      description
        "Total number of calls rejected since AP joined";
    }
    leaf total-num-of-roam-calls-rejected {
      type uint16;
      description
        "Total number of roam calls rejected since AP joined";
    }
    leaf total-num-of-calls-rejected-insuff-bw {
      type uint16;
      description
        "Total number of calls rejected due to insufficient bandwidth";
    }
    leaf total-num-of-calls-rejected-qos {
      type uint16;
      description
        "Total number of calls rejected due to wlan QoS settings";
    }
    leaf total-num-of-calls-rejected-phy-rate {
      type uint16;
      description
        "Total number of calls rejected due to un-acceptable PHY rate";
    }
    leaf total-num-of-calls-rejected-invalid-tspec {
      type uint16;
      description
        "Total number of calls rejected due to invalid TSPEC parameters";
    }
    leaf total-num-of-exp-bw-reqs-received {
      type uint16;
      description
        "Total number of exp bw reqs received since AP join";
    }
    leaf total-num-of-exp-bw-reqs-accepted {
      type uint16;
      description
        "Total number of exp bw req calls admitted as expbwreqs since AP joined";
    }
  }

  grouping load-based-cac-stats {
    description
      "This object specifies the Load based voice call statistics";
    leaf tot-available-mt-chan {
      type int32;
      description
        "total MT available for the channel";
    }
    leaf tot-available-mt-voice {
      type int32;
      description
        "total MT avaliable for voice";
    }
    leaf pb {
      type uint32;
      description
        "overall percent busy - for lbcac usage only";
    }
    leaf pv {
      type uint32;
      description
        "percent of chan occupied by voice traffic";
    }
    leaf queue-util {
      type uint32;
      description
        "Current queue utilization";
    }
    leaf total-lbcac-checks {
      type uint32;
      description
        "Total count of lbcac checks since AP join";
    }
    leaf total-lbcac-passed {
      type uint32;
      description
        "Total count of lbcac checks passed";
    }
    leaf total-bw-check-fails {
      type uint32;
      description
        "Total count of admit criteria #1 failed";
    }
    leaf total-qu-check-fails {
      type uint32;
      description
        "Total count of admit criteria #2 failed";
    }
    leaf avg-bw-request-mt {
      type int32;
      description
        "Average bandwidth request size received";
    }
    leaf na-direct {
      type int16;
      description
        "Estimate number of additional tspecs we can admit";
    }
    leaf na-roam {
      type int16;
      description
        "Estimate number of roaming calls we can admit";
    }
  }

  grouping sip-cac-stats {
    description
      "SIP CAC statistics";
    leaf sip-cac-non-roam-calls-in-progress {
      type uint16;
      description
        "Total number of calls in progress";
    }
    leaf sip-cac-roam-calls-in-progress {
      type uint16;
      description
        "Total number of roam calls in progress";
    }
    leaf sip-cac-total-not-roam-calls-ap {
      type uint16;
      description
        "Total number of calls accepted since AP join";
    }
    leaf sip-cac-total-roam-calls-ap {
      type uint16;
      description
        "Total number of roam calls accepted since AP join";
    }
    leaf sip-cac-preferred-calls-received {
      type uint16;
      description
        "Total number of Preferred calls received";
    }
    leaf sip-cac-preferred-calls-accepted {
      type uint16;
      description
        "Total number of Preferred calls accepted";
    }
    leaf sip-cac-preferred-calls-ongoing {
      type uint16;
      description
        "Total number of ongoing preferred calls";
    }
    leaf sip-cac-total-not-roam-calls-rejected-in-suff-bw {
      type uint16;
      description
        "Total number of calls rejected insuff Bandwidth";
    }
    leaf sip-cac-total-roam-calls-rejected-in-suff-bw {
      type uint16;
      description
        "Total number of roam calls rejected insuff bandwidth";
    }
  }

  grouping bssid-cac {
    description
      "This object represents CAC parameters for BSSID";
    leaf avail-rate {
      type uint32;
      description
        "Available bandwidth rate";
    }
    leaf cac-state {
      type uint8;
      description
        "CAC state";
    }
    leaf config-rate {
      type uint32;
      description
        "Configured bandwidth rate";
    }
    leaf up {
      type string {
        length "0 .. 1";
      }
      description
        "Bitwise UP values";
    }
  }

  grouping tclas {
    description
      "Structure of Traffic classification";
    leaf used {
      type uint8;
      description
        "Flag to check if Tclas is already in used or free";
    }
    leaf classifier-mask {
      type uint8;
      description
        "Mask for classifier";
    }
    leaf src-ip {
      type inet:ip-address;
      description
        "Source IP Address";
    }
    leaf dst-ip {
      type inet:ip-address;
      description
        "Destination IP Address";
    }
    leaf src-port {
      type uint16;
      description
        "Source Port";
    }
    leaf dst-port {
      type uint16;
      description
        "Destination Port";
    }
    leaf dscp {
      type uint8;
      description
        "DSCP value";
    }
    leaf rate {
      type uint32;
      description
        "traffic rate";
    }
    leaf protocol {
      type uint8;
      description
        "Protocol type like UDP/TCP";
    }
  }

  grouping tclas-set {
    description
      "TCLAS Informational elements structure";
    leaf used {
      type uint8;
      description
        "Flag to check if Tclas element is in already used or Empty";
    }
    leaf tspec-id {
      type uint8;
      description
        "TSPEC identifier";
    }
    leaf processing {
      type uint8;
      description
        "AND/OR=TCLAS Processing Element, EWLC_TCLAS_PROCESS_xxx";
    }
    leaf user-priority {
      type uint8;
      description
        "User priority value";
    }
    leaf npu-db-offset {
      type uint16;
      description
        "NPU offset";
    }
    list tclas {
      max-elements "3";
      description
        "Array of tclas info structure, MAX can have 3 elements";
      uses wireless-access-point-oper:tclas;
    }
    leaf tclas-count {
      type uint8;
      description
        "TCLAS count";
    }
  }

  grouping qos-bssid-key {
    description
      "Composite key structure for bssid record in DB";
    leaf ssid-name {
      type string;
      description
        "SSID name";
    }
    leaf radio-slot-id {
      type uint8;
      description
        "Slot id for radio";
    }
    leaf wtp-mac {
      type yang:mac-address;
      description
        "AP mac address";
    }
  }

  grouping qos-ap-radio-key {
    description
      "This object specifies the composite key structure for AP Radio record in DB";
    leaf radio-slot-id {
      type uint8;
      description
        "Slot id for radio";
    }
    leaf ap-mac {
      type yang:mac-address;
      description
        "AP mac address";
    }
  }

  grouping qos-bssid-data {
    description
      "This object indicates QoS BSSID data in DB";
    leaf ap-mac {
      type yang:mac-address;
      description
        "AP MAC address";
    }
    container bssid-up-stream-qos-pm {
      description
        "Upstream QoS policy map for bssid";
      uses wireless-access-point-oper:qos-bssid-policy;
    }
    container bssid-down-stream-qos-pm {
      description
        "Downstream QoS policy map for bssic";
      uses wireless-access-point-oper:qos-bssid-policy;
    }
    list cac {
      max-elements "4";
      description
        "CAC element for bssid";
      uses wireless-access-point-oper:bssid-cac;
    }
    leaf num-cac-entries {
      type uint32;
      description
        "Total number of CAC entries";
    }
    leaf downstream-policy {
      type uint32;
      description
        "Downstream policy type";
    }
    leaf wlan-id {
      type uint32;
      description
        "WLAN identifier";
    }
    leaf local-mode {
      type boolean;
      description
        "Flag indicating whether the bssid is in local mode";
    }
  }

  grouping apf-call-record {
    description
      "Structure to carry call parameter information sent by the AP for SIP Call";
    leaf uplink-dest-ip-address {
      type inet:ip-address;
      description
        "Destination ip address for uplink";
    }
    leaf downlink-dest-ip-address {
      type inet:ip-address;
      description
        "Destination ip address for downlink";
    }
    leaf-list uplink-dest-ip-port {
      type uint32;
      max-elements "2";
      ordered-by user;
      description
        "Destination ip port for uplink";
    }
    leaf-list downlink-dest-ip-port {
      type uint32;
      max-elements "2";
      ordered-by user;
      description
        "Destination ip port for downlink";
    }
    leaf call-id {
      type string;
      description
        "Call identifier";
    }
    leaf called-party {
      type string;
      description
        "Destinatio of Call";
    }
    leaf calling-party {
      type string;
      description
        "Initiator of Call";
    }
    leaf wme-client {
      type boolean;
      description
        "WME supported Client";
    }
    leaf call-on-hold {
      type boolean;
      description
        "No of Call on hold";
    }
    leaf call-code {
      type uint32;
      description
        "Parameter that carries error or status codes that are specific to session protocol";
    }
    leaf call-established-timestamp {
      type yang:date-and-time;
      description
        "Timestamp at which the call is established";
    }
    leaf up {
      type uint8;
      description
        "UP value";
    }
  }

  grouping aaa-qos-params {
    description
      "This object specifies QoS AAA params for client";
    leaf aaa-avgdtus {
      type uint32;
      description
        "AAA override value for avg data rate-upstream";
    }
    leaf aaa-avgrtdtus {
      type uint32;
      description
        "AAA override value for avg real data rate-upstream";
    }
    leaf aaa-bstdtus {
      type uint32;
      description
        "AAA override value for burst data rate-upstream";
    }
    leaf aaa-bstrtdtus {
      type uint32;
      description
        "AAA override value for burst real time data rate-upstream";
    }
    leaf aaa-avgdtds {
      type uint32;
      description
        "AAA override value for avg data rate-downstream";
    }
    leaf aaa-avgrtdtds {
      type uint32;
      description
        "AAA override value for avg real data rate-downstream ";
    }
    leaf aaa-bstdtds {
      type uint32;
      description
        "AAA override value for burst data rate-downstream";
    }
    leaf aaa-bstrtdtds {
      type uint32;
      description
        "AAA override value for burst real time data rate-downstream";
    }
    leaf aaa-qos-profile {
      type uint8;
      description
        "AAA override value for profile";
    }
  }

  grouping qos-client-data {
    description
      "This object specifies the QoS Client data in DB";
    leaf client-mac {
      type yang:mac-address;
      description
        "Client mac address";
    }
    leaf wtp-mac {
      type yang:mac-address;
      description
        "AP mac address on which client joined";
    }
    container client-installed-up-stream-pm {
      description
        "QoS Upstream policy map installed for client";
      uses wireless-access-point-oper:qos-client-policy;
    }
    container client-installed-down-stream-pm {
      description
        "QoS Downstream policy map installed for client";
      uses wireless-access-point-oper:qos-client-policy;
    }
    leaf local-mode {
      type boolean;
      description
        "Flag indicating whether the client has joined in local mode";
    }
    leaf is-active-tspec-call {
      type boolean;
      description
        "Flag to show TSPEC call is Active on this client or not";
    }
    leaf tspec-call-established-timestamp {
      type yang:date-and-time;
      description
        "Timestamp at which TSPEC call has been established";
    }
    list tclas-set {
      max-elements "2";
      description
        "TCLAS informational elements";
      uses wireless-access-point-oper:tclas-set;
    }
    leaf is-tspec-client {
      type boolean;
      description
        "Flag indicating whether this is a tspec client";
    }
    leaf bandwidth-alloc {
      type uint32;
      description
        "TSpec call bandwidth allocated";
    }
    leaf bw-alloc-ap-mac {
      type yang:mac-address;
      description
        "AP mac for which Call bandwidth is allocated";
    }
    leaf bw-alloc-ap-name {
      type string;
      description
        "AP name for which Call bandwidth is allocated";
    }
    leaf bw-alloc-radio-slot-id {
      type uint8;
      description
        "AP Radio slot for which Call bandwidth is allocated";
    }
    leaf roam-call {
      type uint8;
      description
        "Allocated bandwidth is for roam call or not";
    }
    leaf active-sip-call {
      type uint8;
      description
        "No of Active SIP call on this client";
    }
    list call-record {
      max-elements "2";
      description
        "SIP Call record elements on this client";
      uses wireless-access-point-oper:apf-call-record;
    }
    container aaa-qos-params {
      description
        "AAA QoS parameter elements on this client";
      uses wireless-access-point-oper:aaa-qos-params;
    }
  }

  grouping qos-ap-radio-data {
    description
      "This object specifies the QoS AP Radio data in DB";
    leaf wmm-voice-bw-allocated {
      type int32;
      description
        "Voice Bandwidth allocated for Calls";
    }
    leaf wmm-max-voice-bandwidth {
      type int32;
      description
        "Max RF bandwidth for Calls";
    }
    leaf wmm-bw-in-use {
      type int32;
      description
        "Bandwidth is used in Voice Call (% of config bandwidth)";
    }
    container wmm-cac-stats {
      description
        "CAC stats data for this Radio on AP";
      uses wireless-access-point-oper:wmm-cac-stats;
    }
    container cac-voice-loadbased-stats {
      description
        "Load based CAC voice stats for this Radio on AP";
      uses wireless-access-point-oper:load-based-cac-stats;
    }
    leaf exp-bw-required-enabled {
      type uint8;
      description
        "expbw required is enabled flag";
    }
    leaf lbcac-measure {
      type boolean;
      description
        "load-based CAC setting measure";
    }
    leaf wmm-voice-roam-bw-in-use {
      type int32;
      description
        "Bandwidth is used in Voice roam Call (% of config bandwidth)";
    }
    leaf sip-cac-preferred-calls-mtu-used {
      type int32;
      description
        "Total bandwidth is used for SIP preferred Call (% of config bandwidth)";
    }
    container sip-cac-stats {
      description
        "SIP CAC statistics";
      uses wireless-access-point-oper:sip-cac-stats;
    }
    leaf total-active-calls {
      type uint16;
      description
        "Total active calls include both TSpec and SIP calls";
    }
    leaf total-rejected-calls {
      type uint16;
      description
        "Total Rejected calls include both TSpec and SIP calls";
    }
    leaf cumulative-call-count {
      type uint32;
      description
        "completed sip call count";
    }
    leaf cumulative-seconds-used {
      type uint32;
      description
        "call duration for completed sip calls";
    }
  }

  grouping qos-bssid-record-statistics {
    description
      "QoS BSSID Record related Statistics";
    leaf bssid-rec-created {
      type uint32;
      description
        "Number of Bssid records created successfully";
    }
    leaf bssid-rec-create-failed {
      type uint32;
      description
        "Number of Bssid record creation failures";
    }
    leaf bssid-rec-create-failed-insert {
      type uint32;
      description
        "Number of Bssid record Insertion failures in qos db";
    }
    leaf bssid-rec-deleted {
      type uint32;
      description
        "Number of Bssid records deleted successfully";
    }
    leaf bssid-rec-delete-failed {
      type uint32;
      description
        "Number of Bssid record deletion failures";
    }
  }

  grouping qos-bssid-policy-statistics {
    description
      "QoS BSSID Policy Statistics";
    leaf bssid-install-req-sent-to-ap {
      type uint32;
      description
        "Number of Bssid policy Install requests sent to AP";
    }
    leaf bssid-install-success-from-ap {
      type uint32;
      description
        "Number of Install success received from AP for Bssid policy";
    }
    leaf bssid-install-fail-from-ap {
      type uint32;
      description
        "Number of Install Failures received from AP for Bssid policy";
    }
    leaf bssid-install-fail-invalid-policy {
      type uint32;
      description
        "Number of Bssid policy Install Failures due to Invalid Policy Format";
    }
    leaf bssid-install-fail-missing-policy {
      type uint32;
      description
        "Number of Bssid policy Install Failures due to Missing Policy in PMDB";
    }
    leaf bssid-install-fail-capwap-sent {
      type uint32;
      description
        "Number of Bssid policy Install Failures due to Capwap Send Failures";
    }
    leaf bssid-uninstall-req-sent-to-ap {
      type uint32;
      description
        "Number of Bssid policy Uninstall requests sent to AP";
    }
    leaf bssid-uninstall-req-sent-to-ap-failed {
      type uint32;
      description
        "Number of Bssid policy Uninstall requests Failed to send to AP";
    }
    leaf bssid-uninstall-success-from-ap {
      type uint32;
      description
        "Number of Uninstall success received from Ap for Bssid policy";
    }
    leaf bssid-uninstall-fail-from-ap {
      type uint32;
      description
        "Number of Uninstall failures received from Ap for Bssid policy";
    }
  }

  grouping qos-client-record-statistics {
    description
      "QoS Client Record related Statistics";
    leaf client-rec-created {
      type uint32;
      description
        "Number of Client records created successfully";
    }
    leaf client-rec-create-failed {
      type uint32;
      description
        "Number of Client record creation failures";
    }
    leaf client-rec-create-failed-insert {
      type uint32;
      description
        "Number of Bssid record Insertion failures in qos db";
    }
    leaf client-rec-deleted {
      type uint32;
      description
        "Number of Client records deleted successfully";
    }
    leaf client-rec-delete-failed {
      type uint32;
      description
        "Number of Client record deletion Failures";
    }
    leaf dot11-client-record-not-found {
      type uint32;
      description
        "Number of time fail to get the client data form dot11 oper data";
    }
    leaf stby-client-rec-created {
      type uint32;
      description
        "Number of standby Client policy map record creates";
    }
    leaf stby-client-rec-create-failed {
      type uint32;
      description
        "Number of standby Client policy map record create failures";
    }
    leaf stby-client-rec-create-failed-insert {
      type uint32;
      description
        "Number of standby Client pm record insertion failures";
    }
    leaf stby-client-rec-deleted {
      type uint32;
      description
        "Number of standby Client pm record deletes";
    }
    leaf stby-client-rec-delete-failed {
      type uint32;
      description
        "Number of standby Client pm record delete failures";
    }
  }

  grouping qos-client-policy-statistics {
    description
      "QoS Client Policy Statistics";
    leaf client-thinbind-req-sent-to-ap {
      type uint32;
      description
        "Number of THINBIND requests sent to AP";
    }
    leaf client-fatbind-req-sent-to-ap {
      type uint32;
      description
        "Number of FATBIND requests sent to AP";
    }
    leaf client-install-success-from-ap {
      type uint32;
      description
        "Number of client policy Install success received from AP";
    }
    leaf client-install-fail-from-ap {
      type uint32;
      description
        "Number of client policy Install failure received from AP";
    }
    leaf client-install-fail-invalid-policy {
      type uint32;
      description
        "Number of client policy Install Failures due to Invalid Policy Format";
    }
    leaf client-install-fail-missing-policy {
      type uint32;
      description
        "Number of client policy Install Failures due to Missing Policy in PMDB";
    }
    leaf client-install-fail-capwap-sent {
      type uint32;
      description
        "Number of client policy Install Failures due to Capwap Send Failures";
    }
    leaf client-blacklist-req-issued {
      type uint32;
      description
        "Number of Client Blacklisting Requests Issued";
    }
    leaf client-blacklist-req-failed {
      type uint32;
      description
        "Number of Client Blacklisting update failures";
    }
    leaf client-uninstall-req-sent-to-ap {
      type uint32;
      description
        "Number of Client policy Uninstall requests sent to AP";
    }
    leaf client-uninstall-req-sent-to-ap-failed {
      type uint32;
      description
        "Number of Client policy Uninstall requests Failed to send to AP";
    }
    leaf client-uninstall-success-from-ap {
      type uint32;
      description
        "Number of Client policy Uninstall success received from AP";
    }
    leaf client-uninstall-fail-from-ap {
      type uint32;
      description
        "Number of Client policy Uninstall Failures received from AP";
    }
    leaf num-of-fastlane-upstream-client {
      type uint32;
      description
        "Number of Fastlane upstream Clients";
    }
    leaf num-of-fastlane-downstream-client {
      type uint32;
      description
        "Number of Fastlane downstream Clients";
    }
  }

  grouping qos-client-voice-statistics {
    description
      "QoS Client Voice Statistics";
    leaf total-num-of-tspec-rcvd {
      type uint32;
      description
        "Total Number of TSPEC requests recceived";
    }
    leaf new-tspec-from-assoc-req {
      type uint32;
      description
        "Number of New TSPEC received from Assoc Request";
    }
    leaf tspec-renewal-from-assoc-req {
      type uint32;
      description
        "Number of TSPEC renewal received from Assoc Request";
    }
    leaf new-tspec-as-add-ts {
      type uint32;
      description
        "Number of new Add TS requests received";
    }
    leaf tspec-renewal-from-add-ts {
      type uint32;
      description
        "Number of Add TS renewal requests received";
    }
    leaf tspec-process-failed-get-record {
      type uint32;
      description
        "Number of DB failures while processing TSPEC";
    }
    leaf total-sip-invite-on-caller {
      type uint32;
      description
        "Total number of SIP Invite received on Caller";
    }
    leaf total-sip-invite-on-callee {
      type uint32;
      description
        "Total number of SIP Invite received on Callee";
    }
    leaf total-num-of-call-report {
      type uint32;
      description
        "Total number of call-report received";
    }
    leaf total-sip-failure-trap-send {
      type uint32;
      description
        "Total number of SIP failure trap send";
    }
    leaf num-of-calls-accepted {
      type uint32;
      description
        "Total Number of calls accepted";
    }
    leaf num-of-calls-rejected-insuff-bw {
      type uint32;
      description
        "Number of calls rejected due to Insufficient BW";
    }
    leaf num-of-calls-rejected-qos {
      type uint32;
      description
        "Number of calls rejected due to QoS policy";
    }
    leaf num-of-calls-rejected-phy-rate {
      type uint32;
      description
        "Number of calls rejected due to PHY rate";
    }
    leaf num-of-calls-rejected-invalid-tspec {
      type uint32;
      description
        "Number of calls rejected due to Invalid TSPEC";
    }
    leaf num-of-roam-calls-accepted {
      type uint32;
      description
        "Total Number of roam calls accepted";
    }
    leaf num-of-roam-calls-rejected {
      type uint32;
      description
        "Total Number of roam calls rejected";
    }
    leaf num-of-active-sip-calls {
      type uint32;
      description
        "Total Number of active SIP calls";
    }
    leaf num-of-active-tspec-calls {
      type uint32;
      description
        "Total Number of active TSPEC calls";
    }
  }

  grouping qos-generic-statistics {
    description
      "QoS Generic Statistics";
    leaf qos-purge-req-sent-to-ap {
      type uint32;
      description
        "Number of Purge requests sent to AP";
    }
    leaf qos-purge-req-sent-to-ap-failed {
      type uint32;
      description
        "Number of Purge requests failed to send to AP";
    }
    leaf qos-stats-req-sent-to-ap {
      type uint32;
      description
        "Number of QoS Statistics requests sent to AP";
    }
    leaf qos-stats-update-rcv-from-ap {
      type uint32;
      description
        "Number of QoS Statistics update received from AP";
    }
    leaf qos-stats-update-sent-to-ios {
      type uint32;
      description
        "Number of QoS Statistics update sent to IOS";
    }
  }

  grouping qos-ha-statistics {
    description
      "QoS HA Statistics";
    leaf bssid-qos-ha-delete-bssid-record-post-partial-del {
      type uint32;
      description
        "Total Number of bssid record deleted successfully after partial delete scenario in HA sync";
    }
    leaf bssid-qos-ha-delete-ap-post-reconciliation {
      type uint32;
      description
        "Number of AP deletes due to BSSID sync failures in HA";
    }
    leaf client-table-create-cb {
      type uint32;
      description
        "Total Number of client table create callbacks on standby";
    }
    leaf client-table-modify-cb {
      type uint32;
      description
        "Total Number of client table modify callbacks on standby";
    }
    leaf client-table-delete-cb {
      type uint32;
      description
        "Total Number of client table delete callbacks on standby";
    }
    leaf ap-radio-table-create-cb {
      type uint32;
      description
        "Total Number of ap radio table create callbacks on standby";
    }
    leaf ap-radio-table-modify-cb {
      type uint32;
      description
        "Total Number of ap radio modify callbacks on standby";
    }
    leaf ap-radio-table-delete-cb {
      type uint32;
      description
        "Total Number of ap radio delete callbacks on standby";
    }
    leaf wlan-table-create-cb {
      type uint32;
      description
        "Total Number of wlan table create callbacks on standby";
    }
    leaf wlan-table-modify-cb {
      type uint32;
      description
        "Total Number of wlan table modify callbacks on standby";
    }
    leaf wlan-table-delete-cb {
      type uint32;
      description
        "Total Number of wlan table delete callbacks on standby";
    }
    leaf qos-ha-client-recreate-cb {
      type uint32;
      description
        "Total Number of client recreate request received post SSO";
    }
    leaf partial-delete-client-ha-cb {
      type uint32;
      description
        "Total Number of partial delete request received in client SSO";
    }
    leaf partial-delete-client-rec-deleted {
      type uint32;
      description
        "Total Number of client record deleted during partial delete handling";
    }
    leaf partial-delete-client-rec-delete-failed {
      type uint32;
      description
        "Total Number of client record delete failed during partial delete handling";
    }
  }

  grouping qos-global-statistics {
    description
      "QoS Global Statistics";
    container qos-bssid-record-stats {
      description
        "QoS BSSID Record related Statistics";
      uses wireless-access-point-oper:qos-bssid-record-statistics;
    }
    container qos-bssid-policy-stats {
      description
        "QoS BSSID policy related Statistics";
      uses wireless-access-point-oper:qos-bssid-policy-statistics;
    }
    container qos-client-record-stats {
      description
        "QoS Client Record related Statistics";
      uses wireless-access-point-oper:qos-client-record-statistics;
    }
    container qos-client-policy-stats {
      description
        "QoS Client policy related Statistics";
      uses wireless-access-point-oper:qos-client-policy-statistics;
    }
    container qos-client-voice-stats {
      description
        "QoS Client Voice related Statistics";
      uses wireless-access-point-oper:qos-client-voice-statistics;
    }
    container qos-generic-stats {
      description
        "QoS Generic Statistics";
      uses wireless-access-point-oper:qos-generic-statistics;
    }
    container qos-ha-stats {
      description
        "QoS HA Statistics";
      uses wireless-access-point-oper:qos-ha-statistics;
    }
  }

  grouping ewlc-radio-station-cfg-data {
    description
      "Configuration related to wireless stations";
    leaf country-string {
      type string;
      description
        "AP Country Code";
    }
  }

  grouping ewlc-phy-tx-power-cfg-data {
    description
      "This object indicates the configured tx-power";
    leaf phy-tx-power-config-type {
      type wireless-access-point-oper:w-config-type;
      description
        "Type of Tx power configuration, Auto or Static";
    }
    leaf current-tx-power-level {
      type uint16;
      description
        "Current Tx Power level";
    }
  }

  grouping ewlc-phy-tx-power-level-cfg-data {
    description
      "Information related to various power levels supported by the AP";
    leaf num-supp-power-levels {
      type uint8;
      description
        "Total number of power levels supported on the AP radio";
    }
    leaf tx-power-level-1 {
      type int16;
      description
        "Tx power level value at index 1 for the AP radio";
    }
    leaf tx-power-level-2 {
      type int16;
      description
        "Tx power level value at index 2 for the AP radio";
    }
    leaf tx-power-level-3 {
      type int16;
      description
        "Tx power level value at index 3 for the AP radio";
    }
    leaf tx-power-level-4 {
      type int16;
      description
        "Tx power level value at index 4 for the AP radio";
    }
    leaf tx-power-level-5 {
      type int16;
      description
        "Tx power level value at index 5 for the AP radio";
    }
    leaf tx-power-level-6 {
      type int16;
      description
        "Tx power level value at index 6 for the AP radio";
    }
    leaf tx-power-level-7 {
      type int16;
      description
        "Tx power level value at index 7 for the AP radio";
    }
    leaf tx-power-level-8 {
      type int16;
      description
        "Tx power level value at index 8 for the AP radio";
    }
    leaf curr-tx-power-in-dbm {
      type int16;
      description
        "Current Transmit Power on the AP radio in dBm";
    }
  }

  grouping ewlc-phy-ht-cfg-data {
    description
      "802.11n configuration";
    leaf ht-enable {
      type uint8;
      description
        "True if 802.11n is enabled on the AP radio";
    }
    leaf curr-freq {
      type uint8;
      description
        "Current operating frequency on the AP radio";
    }
    leaf chan-width {
      type uint8;
      description
        "Channel width of the AP radio";
    }
    leaf ext-chan {
      type uint8;
      description
        "Current extended channel. Valid if the channel width is more than 20Mhz";
    }
    leaf vht-enable {
      type uint8;
      description
        "True if 802.11ac is enabled";
    }
    leaf leg-tx-bf-enabled {
      type uint8;
      description
        "True if Legacy Tx Beamforming Setting enabled";
    }
  }

  grouping ewlc-phy-ht-info-data {
    description
      "802.11n information";
    leaf num-rx-ant {
      type uint8;
      description
        "Number of receive Antennas";
    }
    leaf num-tx-ant {
      type uint8;
      description
        "Number of Transmit Antennas";
    }
    leaf num-ss {
      type uint8;
      description
        "Number of spatial streams supported by the radio";
    }
  }

  grouping ewlc-phy-ht-cap-data {
    description
      "802.11n capbilities";
    leaf slot-id {
      type uint8;
      description
        "Access Point radio slot identifier";
    }
    leaf vht-capable {
      type uint8;
      description
        "True if AP radio is 802.11ac capable";
    }
    leaf ht-capable {
      type boolean;
      description
        "True if AP radio is 802.11n capable";
    }
  }

  grouping rrm-antenna {
    description
      "Antenna selection related information";
    leaf-list value {
      type uint8;
      max-elements "16";
      ordered-by user;
      description
        "Antenna selection information";
    }
  }

  grouping ewlc-antenna-cfg-data {
    description
      "Information related to Antenna configuration";
    leaf diversity-selection {
      type uint8;
      description
        "Diversity selection type, values connectorA, connectorB or enabled.
         Not applicable to 802.11a radio band";
    }
    leaf antenna-mode {
      type uint8;
      description
        "Antenna Mode. For 802.11a this attribute will always be omni.
         Not applicable to 802.11b radio band";
    }
    leaf ht-rx-antenna-selection {
      type uint8;
      description
        "True if this Antenna is allowed to receive";
    }
    leaf ht-tx-antenna-selection {
      type uint8;
      description
        "True if this Antenna is allowed to transmit";
    }
    leaf num-of-antennas {
      type uint8;
      description
        "Number of Antennas present on this AP radio";
    }
    container antenna-selection {
      description
        "Antenna selection information";
      uses wireless-access-point-oper:rrm-antenna;
    }
  }

  grouping ewlc-chan-pwr-info-data {
    description
      "Allowed power levels on the given channel";
    leaf antenna-gain {
      type uint8;
      description
        "Antenna gain value for the given AP radio";
    }
    leaf int-antenna-gain {
      type uint8;
      description
        "Internal Antenna gain value for the given radio";
    }
    leaf ext-antenna-gain {
      type uint8;
      description
        "External Antenna gain value for the given AP radio";
    }
  }

  grouping cfg-entity-radio-station-cfg {
    description
      "Configuration related to wireless stations";
    container cfg-data {
      description
        "Station Configuration";
      uses wireless-access-point-oper:ewlc-radio-station-cfg-data;
    }
  }

  grouping cfg-entity-phy-tx-power-cfg {
    description
      "Tx-power configured on the radio";
    container cfg-data {
      description
        "Phy Tx Power Configuration";
      uses wireless-access-point-oper:ewlc-phy-tx-power-cfg-data;
    }
  }

  grouping cfg-entity-phy-tx-power-level-cfg {
    description
      "Configured tx power level on the radio";
    container cfg-data {
      description
        "Tx power level Configuration";
      uses wireless-access-point-oper:ewlc-phy-tx-power-level-cfg-data;
    }
  }

  grouping cfg-entity-phy-ht-cfg {
    description
      "802.11n configuration";
    container cfg-data {
      description
        "802.11n Configuration";
      uses wireless-access-point-oper:ewlc-phy-ht-cfg-data;
    }
  }

  grouping cfg-entity-phy-ht-info {
    description
      "802.11n information";
    container data {
      description
        "802.11n information";
      uses wireless-access-point-oper:ewlc-phy-ht-info-data;
    }
  }

  grouping cfg-entity-phy-ht-cap {
    description
      "Configuration related to 802.11n capabilities";
    container data {
      description
        "802.11n Capabilities";
      uses wireless-access-point-oper:ewlc-phy-ht-cap-data;
    }
  }

  grouping cfg-entity-antenna-cfg {
    description
      "Configuration related to Antenna";
    container cfg-data {
      description
        "Antenna Configuration";
      uses wireless-access-point-oper:ewlc-antenna-cfg-data;
    }
  }

  grouping entity-channel-power-info {
    description
      "Tx Power information for all Radio channels";
    container data {
      description
        "Channel Power information for AP radio";
      uses wireless-access-point-oper:ewlc-chan-pwr-info-data;
    }
  }

  grouping ewlc-radio-band-info {
    description
      "Information of the given radio band";
    leaf band-id {
      type uint8;
      description
        "Band identifier of the radio interface";
    }
    leaf reg-domain-code {
      type uint16;
      description
        "Regulatory domain of the radio interface";
    }
    container phy-tx-pwr-cfg {
      description
        "Configured radio Tx-power in dBm";
      uses wireless-access-point-oper:cfg-entity-phy-tx-power-cfg;
    }
    container phy-tx-pwr-lvl-cfg {
      description
        "Tx-power level configured on the radio";
      uses wireless-access-point-oper:cfg-entity-phy-tx-power-level-cfg;
    }
    container antenna-cfg {
      description
        "Antenna configuration";
      uses wireless-access-point-oper:cfg-entity-antenna-cfg;
    }
  }

  grouping st-radio-event {
    description
      "AP radio event information";
    leaf event-type {
      type wireless-access-point-oper:enum-radio-rrm-event-type;
      description
        "Last radio event type";
    }
    leaf event-timestamp {
      type yang:date-and-time;
      description
        "Date and Time for the last radio event";
    }
  }

  grouping ewlc-radio-operation-config {
    description
      "Radio operational configuration";
    leaf radio-type {
      type uint32;
      description
        "Type of the radio. Radio type can be 802.11bg, 802.11a or dual-band";
    }
    leaf admin-state {
      type wireless-access-point-oper:enum-radio-admin-state;
      description
        "Admin state of the radio interface";
    }
    leaf oper-state {
      type wireless-access-point-oper:enum-radio-oper-state;
      description
        "Operational state of the radio interface. Even though the admin state is enabled there are various reasons for which the operational state of the radio can be down";
    }
    leaf config-state {
      type wireless-access-point-oper:enum-radio-cfg-state;
      description
        "Radio config state. The possible values are ENABLED or DISABLED";
    }
    leaf radio-mode {
      type uint8;
      description
        "Current radio mode. Possible values are
         0 - Invalid mode
         1 - Local mode
         2 - Monitor mode
         3 - Remote mode
         4 - Rouge detector
         5 - Sniffer mode
         6 - Bridge mode
         7 - Spectrum mode
         8 - Remote bridge
         9 - hybrid mode
         10 - Sensor mode";
    }
    leaf radio-sub-mode {
      type uint8;
      description
        "Radio mode selection process, possible values are
         0 - None
         1 - Auto, radio mode is selected automatically
         2 - Manual, radio mode is selected manually";
    }
    leaf radio-subtype {
      type uint8;
      description
        "Radio sub type indicating the radios capabilities, possible values are:
         0 - Main
         1 - Rx-only, radio can only receive
         2 - Remote lan
         3 - Radio can both receive and transmit";
    }
    leaf radio-subband {
      type wireless-enum-types:slot-radio-sub-band;
      description
        "Radio sub band, Valid only if the radio is in 5 GHz band";
    }
    leaf current-band-id {
      type uint8;
      description
        "Radio's current operating band, possible values are 2.4GHz/5 GHz";
    }
    leaf xor-radio-mode {
      type wireless-types:enum-xor-radio-mode;
      description
        "XOR radio mode possible values are Client serving/Monitor/sensor";
    }
    leaf slot-shut-reason {
      type wireless-types:enm-shut-down-reason;
      description
        "Reason for radio state down. Valid only if Admin state of AP and Radio is UP";
    }
    container station-cfg {
      description
        "Radio configuration related to wireless stations";
      uses wireless-access-point-oper:cfg-entity-radio-station-cfg;
    }
    container phy-ht-cfg {
      description
        "802.11n radio Configuration";
      uses wireless-access-point-oper:cfg-entity-phy-ht-cfg;
    }
    container phy-ht-info {
      description
        "802.11n radio Information";
      uses wireless-access-point-oper:cfg-entity-phy-ht-info;
    }
    container phy-ht-cap {
      description
        "Capabilities related to 802.11n";
      uses wireless-access-point-oper:cfg-entity-phy-ht-cap;
    }
    container xor-phy-ht-info {
      description
        "Information related to 802.11n for a dual-band radio";
      uses wireless-access-point-oper:cfg-entity-phy-ht-info;
    }
    container xor-phy-ht-cap {
      description
        "802.11n capabilities for a dual-band radio";
      uses wireless-access-point-oper:cfg-entity-phy-ht-cap;
    }
    container chan-pwr-info {
      description
        "Mapping between all channels and allowed power levels on that channel";
      uses wireless-access-point-oper:entity-channel-power-info;
    }
    container last-event {
      description
        "Information related to the last radio event";
      uses wireless-access-point-oper:st-radio-event;
    }
    leaf antenna-pid {
      type string;
      description
        "Radio Antenna PID";
    }
    list radio-band-info {
      key "band-id";
      description
        "Radio Band Information";
      uses wireless-access-point-oper:ewlc-radio-band-info;
    }
    list vap-oper-config {
      key "ap-vap-id";
      description
        "Vap operation configuration";
      uses wireless-access-point-oper:ewlc-vap-operational-config;
    }
    leaf reg-domain-check-status {
      type uint16;
      description
        "True if the regulatory domain check has passed";
    }
    leaf dot11-radio-role {
      type wireless-access-point-oper:ap-dot11-radio-role;
      description
        "AP radio role";
    }
  }

  grouping st-mac-slot-id-comp-key {
    description
      "Object with mac and slot id. This object are used as key to multiple tables";
    leaf ap-mac {
      type yang:mac-address;
      description
        "Mac address of the AP";
    }
    leaf slot-id {
      type uint32;
      description
        "Radio slot identifier";
    }
  }

  grouping ewlc-radio-operaional-stats {
    description
      "Table indicates multiple statistics information related to a radio";
    leaf aid-user-list {
      type uint16;
      description
        "Number of Users associated with this radio";
    }
    leaf tx-fragment-count {
      type uint32;
      description
        "This counter shall be incremented for an acknowledged MPDU
         with an individual address in the address 1 field or an MPDU
         with a multicast address in the address 1 field of type Data
         or Management.";
    }
    leaf multicast-tx-frame-cnt {
      type uint32;
      description
        "This counter shall increment only when the multicast bit
         is set in the destination MAC address of a successfully
         transmitted MSDU.  When operating as a STA in an ESS, where
         these frames are directed to the AP, this implies having
         received an acknowledgment to all associated MPDUs.";
    }
    leaf failed-count {
      type uint32;
      description
        "This counter shall increment when an MSDU is not transmitted
         successfully due to the number of transmit attempts exceeding
         either the  bsnAPIfDot11ShortRetryLimit or dot11LongRetryLimit.";
    }
    leaf retry-count {
      type uint32;
      description
        "This counter shall increment when an MSDU is successfully
         transmitted after one or more retransmissions.";
    }
    leaf multiple-retry-count {
      type uint32;
      description
        "This counter shall increment when an MSDU is successfully
         transmitted after more than one retransmission.";
    }
    leaf frame-duplicate-count {
      type uint32;
      description
        "This counter shall increment when a frame is received
         that the Sequence Control field indicates is a
         duplicate.";
    }
    leaf rts-success-count {
      type uint32;
      description
        "This counter shall increment when a CTS is received in
         response to an RTS.";
    }
    leaf rts-failure-count {
      type uint32;
      description
        "This counter shall increment when a CTS is not received in
         response to an RTS.";
    }
    leaf ack-failure-count {
      type uint32;
      description
        "This counter shall increment when an ACK is not received
         when expected.";
    }
    leaf rx-fragment-count {
      type uint32;
      description
        "This counter shall be incremented for each successfully
         received MPDU of type Data or Management.";
    }
    leaf multicast-rx-frame-cnt {
      type uint32;
      description
        "This counter shall increment when a MSDU is received
         with the multicast bit set in the destination
         MAC address.";
    }
    leaf fcs-error-count {
      type uint32;
      description
        "This counter shall increment when an FCS error is
         detected in a received MPDU.";
    }
    leaf tx-frame-count {
      type uint32;
      description
        "This counter shall increment for each successfully
         transmitted MSDU.";
    }
    leaf wep-undecryptable-count {
      type uint32;
      description
        "This counter shall increment when a frame is received with
         the WEP subfield of the Frame Control field set to one and the
         WEPOn value for the key mapped to the TA's MAC address
         indicates that the frame should not have been encrypted or
         that frame is discarded due to the receiving STA not
         implementing the privacy option.";
    }
    leaf tx-frames-dropped {
      type uint32;
      description
        "Total number of tx frames dropped";
    }
    leaf total-num-of-call-in-progress {
      type uint16;
      description
        "Total number of calls in progress";
    }
    leaf num-of-roam-call-in-progress {
      type uint16;
      description
        "Total number of roam calls in progress";
    }
    leaf total-num-of-voice-calls-ap {
      type uint16;
      description
        "Total number of voice call AP's";
    }
    leaf total-num-of-roam-calls-accepted {
      type uint16;
      description
        "Total number of roam calls accepted";
    }
    leaf total-num-of-exp-bw-reqs-received {
      type uint16;
      description
        "Total number of expired bandwidth req's recevied";
    }
    leaf total-num-of-exp-bw-reqs-accepted {
      type uint16;
      description
        "Total number of expired bandwidth req's accepted";
    }
    leaf total-num-of-voice-calls-rejected-ap {
      type uint16;
      description
        "Total number of voice call rejected AP";
    }
    leaf total-num-of-roam-calls-rejected {
      type uint16;
      description
        "Total number of roam calls rejected";
    }
    leaf total-num-of-calls-rejected-insuff-bw {
      type uint16;
      description
        "Total number of calls rejected insuff bandwidth";
    }
    leaf total-num-of-calls-rejected-invalid-tspec {
      type uint16;
      description
        "Total number of calls rejected from invalid TSPEC";
    }
    leaf total-num-of-calls-rejected-phy-rate {
      type uint16;
      description
        "Total number of calls rejected from phy rate";
    }
    leaf total-num-of-calls-rejected-qos {
      type uint16;
      description
        "Total number of calls rejected from qos";
    }
    leaf num-of-dual-band-client {
      type uint32;
      description
        "Number of dual-band clients connected";
    }
    leaf num-of-dual-band-client-added {
      type uint32;
      description
        "Number of dual-band clients added";
    }
    leaf num-of-dual-band-client-expired {
      type uint32;
      description
        "Number of dual-band clients expired";
    }
    leaf num-of-dual-band-client-replaced {
      type uint32;
      description
        "Number of dual-band clients replaced";
    }
    leaf num-of-dual-band-client-detected {
      type uint32;
      description
        "Number of dual-band clients detected";
    }
    leaf num-of-suppressed-client {
      type uint32;
      description
        "Number of clients suppressed to make them join on the other radio";
    }
    leaf num-of-suppressed-client-expired {
      type uint32;
      description
        "Number of expired client";
    }
    leaf num-of-suppressed-client-replaced {
      type uint32;
      description
        "Number of replaced client";
    }
    leaf total-airtime-used-inst {
      type uint64;
      description
        "Total Air Time used instantaneously for particular AP per slot";
    }
    leaf total-airtime-used-cum {
      type uint64;
      description
        "Total Air Time used cumulatively for particular AP per slot";
    }
    leaf radio-uptime {
      type uint32;
      description
        "Radio up time for particular AP per slot";
    }
    leaf radio-uptime-cum {
      type uint32;
      description
        "Total cumulative radio up time for particular AP per slot";
    }
    leaf neighbor-list-request-received {
      type uint32;
      description
        "Number of neighbor request received from the clients";
    }
    leaf neighbor-list-report-sent {
      type uint32;
      description
        "Number of neighbor reports sent";
    }
    leaf neighbor-list-broadcast-sent {
      type uint32;
      description
        "Number of neighbor report broadcasts";
    }
    leaf tx-rate {
      type uint32;
      description
        "Tx rate reported by a radio slot";
    }
    leaf rx-rate {
      type uint32;
      description
        "Rx rate reported by a radio slot";
    }
    leaf data-rate {
      type uint32;
      description
        "Aggregate data rate reported by a radio slot";
    }
    leaf rx-error-frame-count {
      type uint32;
      description
        "Total number of frames received with error";
    }
    leaf mac-mic-err-frame-count {
      type uint32;
      description
        "Total Number of frames received with MIC error";
    }
    leaf mac-decrypt-err-frame-count {
      type uint32;
      description
        "Total number of packets received with decrypt error";
    }
    leaf replay-error-frame-count {
      type uint32;
      description
        "Total number of frames received with replay error";
    }
    leaf rx-mgmt-frame-count {
      type uint32;
      description
        "Total number of management frames received";
    }
    leaf rx-ctrl-frame-count {
      type uint32;
      description
        "Total number of control frames received";
    }
    leaf rx-data-frame-count {
      type uint32;
      description
        "Total number of data frames received";
    }
    leaf tx-mgmt-frame-count {
      type uint32;
      description
        "Total number of management frames sent";
    }
    leaf tx-ctrl-frame-count {
      type uint32;
      description
        "Total Number of control frames sent";
    }
    leaf tx-data-frame-count {
      type uint32;
      description
        "Total number of data frames sent";
    }
    leaf rx-data-pkt-count {
      type uint32;
      description
        "Total number of data frame received";
    }
    leaf tx-data-pkt-count {
      type uint32;
      description
        "Total number of data frames sent";
    }
  }

  grouping st-atf-stats {
    description
      "AirTime Fairness Statistics";
    leaf airtime-used-inst {
      type uint32;
      description
        "AirTime used instantaneously on an AP radio by a client or a group of clients";
    }
    leaf airtime-used-cum {
      type uint64;
      description
        "Total AirTime used cumulatively on an AP radio by a client or a group of clients";
    }
    leaf frames-sent-inst {
      type uint32;
      description
        "Number of frames sent instantaneously on an AP radio by a client or a group of clients";
    }
    leaf frames-sent-cum {
      type uint64;
      description
        "Total number of frames sent cumulatively on an AP radio by a client or a group of clients";
    }
    leaf frames-dropped-inst {
      type uint32;
      description
        "Number of frames dropped instantaneously on an AP radio by a client or a group of clients";
    }
    leaf frames-dropped-cum {
      type uint64;
      description
        "Total number of frames dropped cumulatively on an AP radio by a client or a group of clients";
    }
  }

  grouping st-atf-wlan-stats {
    description
      "AirTime Fairness WLAN statistics";
    leaf weight-perc {
      type uint8;
      description
        "AirTime Fairness Policy weight in percentage";
    }
    leaf bytes-sent-inst {
      type uint64;
      description
        "Number of bytes sent instantaneously for particular AP per slot per WlanProfileName";
    }
    leaf bytes-sent-cum {
      type uint64;
      description
        "Total number of bytes sent cumulatively for particular AP per slot per WlanProfileName";
    }
    leaf bytes-dropped-inst {
      type uint64;
      description
        "Number of bytes dropped instantaneously for particular AP per slot per WlanProfileName";
    }
    leaf bytes-dropped-cum {
      type uint64;
      description
        "Total number of bytes dropped cumulatively for particular AP per slot per WlanProfileName";
    }
    container wlan-stats {
      description
        "AirTime Fairness client statistics";
      uses wireless-access-point-oper:st-atf-stats;
    }
  }

  grouping st-atf-client-stats {
    description
      "AirTime Fairness client statistics";
    leaf client-state {
      type wireless-types:enm-atf-client-state;
      description
        "Client usage by a client on its associated AP radio";
    }
    container client-stats {
      description
        "AirTime Fairness client statistics";
      uses wireless-access-point-oper:st-atf-stats;
    }
  }

  grouping st-atf-link-stats {
    description
      "AirTime Fairness mesh statistics";
    leaf link {
      type wireless-types:enm-atf-mesh-link;
      description
        "AirTime Fairness mesh link";
    }
    leaf node-role {
      type wireless-types:enm-atf-mesh-node-role;
      description
        "Node role parent/child";
    }
    leaf link-id {
      type uint8;
      description
        "Mesh AP link index";
    }
    leaf neighbor-ap-name {
      type string;
      description
        "Name of neighbor AP";
    }
    container atf-mesh-stats {
      description
        "AirTime Fairness mesh statistics";
      uses wireless-access-point-oper:st-atf-stats;
    }
  }

  grouping ewlc-vap-operational-config {
    description
      "ewlc_vap_operational_config";
    leaf ap-vap-id {
      type uint16;
      description
        "AP WLAN Identifier";
    }
    leaf bssid-mac {
      type yang:mac-address;
      description
        "Bssid address";
    }
    leaf wtp-mac {
      type yang:mac-address;
      description
        "AP MAC Address";
    }
    leaf wlan-profile-name {
      type string;
      description
        "This object uniquely identifies an entry in
         Policy profile configuration table.";
    }
    leaf ssid {
      type string;
      description
        "WLAN SSID name";
    }
    leaf status {
      type boolean;
      description
        "WLAN status";
    }
  }

  grouping capwap-wtp-predownload-data {
    description
      "Stores information related to predownload operation on AP";
    leaf wtp-mac {
      type yang:mac-address;
      description
        "AP Radio MAC address";
    }
    container predownload-version {
      description
        "This object represents the 
         version to be Predownloaded by AP";
      uses wireless-types:version-info;
    }
    leaf max-retry {
      type uint8;
      description
        "This object represents the 
         predownload retry count";
    }
    leaf delay-time {
      type uint16;
      description
        "This object represents the 
         predownload Next retry time";
    }
    leaf pred-status {
      type wireless-types:enm-predownload-status;
      description
        "This object represents the 
         predownload status of this AP";
    }
  }

  grouping ap-client-trace-site-tag-info {
    description
      "Operational data of AP trace for clients in a site-tag";
    leaf site-tag-name {
      type string;
      description
        "Site-tag name in which AP client traces are enabled";
    }
    leaf all-clients-tracing {
      type boolean;
      description
        "Flag to maintain all client tracing enable on all the APs in a site-tag";
    }
  }

  grouping ap-client-trace-ap-info {
    description
      "Operational data of AP trace for clients on an AP";
    leaf ap-name {
      type string;
      description
        "AP name in which AP client traces are enabled";
    }
    leaf all-clients-tracing {
      type boolean;
      description
        "Flag to maintain all client tracing enable on an AP";
    }
  }

  grouping st-wlmgmt-ipv6 {
    description
      "Wireless management interface IPv6 information";
    leaf addr {
      type inet:ip-prefix;
      description
        "Wireless management interface IPv6 prefix";
    }
  }

  grouping st-wlmgmt-intf {
    description
      "mangement interface information";
    leaf intf-name {
      type string;
      description
        "management interface name";
    }
    leaf intf-type {
      type string;
      description
        "management inteface type";
    }
    leaf intf-id {
      type uint32;
      description
        "management interface id";
    }
    leaf mgmt-ip {
      type inet:ip-address;
      description
        "management IP";
    }
    leaf net-mask {
      type inet:ip-address;
      description
        "management interface netmask";
    }
    leaf mgmt-mac {
      type yang:mac-address;
      description
        "management interface mac";
    }
    list interface-ipv6-list {
      key "addr";
      description
        "Management interface IPv6 information";
      uses wireless-access-point-oper:st-wlmgmt-ipv6;
    }
  }

  grouping st-ap-mac-iteration-key {
    description
      "Combined key of AP mac and iteration number";
    leaf iter-number {
      type uint8;
      description
        "Iteration number in which the AP was upgraded";
    }
    leaf radio-mac {
      type yang:mac-address;
      description
        "Radio mac address of the AP";
    }
  }

  grouping st-ap-staggered-upg-upgraded-ap {
    description
      "All the information related to APs that are upgraded";
    leaf ap-mac {
      type yang:mac-address;
      description
        "Radio mac address of the AP";
    }
    leaf eth-mac {
      type yang:mac-address;
      description
        "Ethernet mac address of the AP";
    }
    leaf wtp-name {
      type string;
      description
        "Name of the AP";
    }
    leaf status {
      type wireless-access-point-oper:enum-ap-upgrade-ap-status;
      description
        "Current status of the AP";
    }
    leaf iteration {
      type uint8;
      description
        "Iteration in which the AP was rebooted";
    }
  }

  grouping st-ap-staggered-upg-remaining-ap {
    description
      "All information related to APs that are pending for reboot";
    leaf ap-mac {
      type yang:mac-address;
      description
        "Radio MAC Address of the AP";
    }
    leaf eth-mac {
      type yang:mac-address;
      description
        "Ethernet MAC Address of the AP";
    }
    leaf wtp-name {
      type string;
      description
        "Name of the AP";
    }
  }

  grouping st-ap-staggered-upg-missing-ap {
    description
      "Details of the APs that went missing during reboot";
    leaf ap-mac {
      type yang:mac-address;
      description
        "Mac address of the AP";
    }
  }

  grouping st-ap-staggered-upg-iter {
    description
      "Information related to each iteration of the AP upgrade algorithm";
    leaf iter-num {
      type uint8;
      description
        "Iteration number";
    }
    leaf number-of-aps {
      type uint32;
      description
        "Number of APs that were initially selected";
    }
    leaf number-of-aps-rebooted {
      type uint32;
      description
        "Number of APs that were rebooted";
    }
    leaf start-time {
      type yang:date-and-time;
      description
        "Start time of the iteration";
    }
    leaf end-time {
      type yang:date-and-time;
      description
        "End time of the iteration";
    }
  }

  grouping st-ap-staggered-upg-report {
    description
      "Information related to Staggered AP Upgrade algorithm";
    leaf report-name {
      type string;
      description
        "Name of the report";
    }
    leaf type {
      type wireless-types:enum-ap-upgrade-type;
      description
        "Type of the upgrade. Based on the required it can be either test or production";
    }
    leaf status {
      type wireless-access-point-oper:enum-ap-upgrade-status;
      description
        "Status of the Algorithm";
    }
    leaf mode {
      type wireless-access-point-oper:enum-ap-upgrade-ap-mode;
      description
        "Indicates the AP upgrade mode";
    }
    container from-version {
      description
        "Current version of the APs";
      uses wireless-types:version-info;
    }
    container to-version {
      description
        "New version of the APs";
      uses wireless-types:version-info;
    }
    leaf upgraded-ap-count {
      type uint32;
      description
        "Total number of APs upgraded";
    }
    leaf current-ap-count {
      type uint32;
      description
        "Total number of APs being upgraded in this iteration";
    }
    leaf remaining-ap-count {
      type uint32;
      description
        "Total number of APs remaining";
    }
    leaf source-ip {
      type inet:ip-address;
      description
        "IP address of the source controller";
    }
    leaf source-name {
      type string;
      description
        "Host name of the source controller";
    }
    leaf destination-ip {
      type inet:ip-address;
      description
        "Destination controller's ip address, required in case of N+1 solution";
    }
    leaf destination-name {
      type string;
      description
        "Destination controller's name, required in case of N+1 solution";
    }
    leaf move-report-name {
      type string;
      description
        "Name of the old report, used to move APs from controller";
    }
    leaf start-time {
      type yang:date-and-time;
      description
        "Start time of the Algorithm";
    }
    leaf cap-percentage {
      type uint8;
      description
        "Percentage of the APs that will be rebooted in each iteration";
    }
    leaf predicted-end-time {
      type yang:date-and-time;
      description
        "Predicted end time of the algorithm";
    }
    leaf progress-percentage {
      type uint8;
      description
        "Algorithm completion in percentage";
    }
    leaf total-aps {
      type uint16;
      description
        "Total number of APs";
    }
    leaf end-time {
      type yang:date-and-time;
      description
        "End time of the algorithm";
    }
    leaf cached-report-name {
      type string;
      description
        "Cached report name";
    }
    list ap-staggered-upgrade-upgraded-ap {
      key "iter-number radio-mac";
      unique "ap-mac";
      description
        "List of APs that are upgraded to the new version";
      uses wireless-access-point-oper:st-ap-staggered-upg-upgraded-ap {
        refine "ap-mac" {
          mandatory true;
        }
      }
      uses wireless-access-point-oper:st-ap-mac-iteration-key;
    }
    list ap-staggered-upgrade-current-ap {
      key "ap-mac";
      description
        "List of APs that are handled in the current iteration";
      uses wireless-access-point-oper:st-ap-staggered-upg-upgraded-ap;
    }
    list ap-staggered-upgrade-remaining-ap {
      key "ap-mac";
      description
        "List of APs that are remaining for upgrade";
      uses wireless-access-point-oper:st-ap-staggered-upg-remaining-ap;
    }
    list ap-staggered-upgrade-missing-ap {
      key "ap-mac";
      description
        "List of APs that went missing after reboot";
      uses wireless-access-point-oper:st-ap-staggered-upg-missing-ap;
    }
    list ap-staggered-upgrade-iteration {
      key "iter-num";
      description
        "List of iterations in this algorithm Run";
      uses wireless-access-point-oper:st-ap-staggered-upg-iter;
    }
  }

  container access-point-oper-data {
    config false;
    description
      "Root container of access point oper";
    list ap-history {
      key "ethernet-mac";
      description
        "Details of all the APs joins and disjoins with reason";
      uses wireless-access-point-oper:all-ap-history;
    }
    container wireless-interface-data {
      presence "ewlcWirelessInterfaceData";
      description
        "Contains wireless interface data";
      uses wireless-access-point-oper:st-wlmgmt-intf;
    }
    list radio-oper-data {
      key "wtp-mac radio-slot-id";
      description
        "Contains the radio operational data corresponding to a radio of the 802.11 LWAPP Access Point";
      uses wireless-access-point-oper:ewlc-radio-operation-config;
      uses wireless-types:radio-slot-key;
    }
    list qos-client-data {
      key "client-mac";
      description
        "This object specify a table for qos client data records in DB";
      uses wireless-access-point-oper:qos-client-data;
    }
    list capwap-data {
      key "wtp-mac";
      description
        "Captures the information about the 802.11 LWAPP Access Point that has joined the controller";
      uses wireless-access-point-oper:capwap-wtp-data;
    }
    list ap-name-mac-map {
      key "wtp-name";
      description
        "Contains the mapping between AP name and radio mac of the AP";
      uses wireless-access-point-oper:ap-name-mac-map;
    }
    list radio-oper-stats {
      key "ap-mac slot-id";
      description
        "Contains the operational statistics for a particular radio";
      uses wireless-access-point-oper:ewlc-radio-operaional-stats;
      uses wireless-access-point-oper:st-mac-slot-id-comp-key;
    }
    list atf-wlan-stats {
      key "radio-mac radio-slot-id wlan-profile-name";
      description
        "AirTime Fairness WLAN statistics";
      uses wireless-access-point-oper:st-atf-wlan-stats;
      uses wireless-types:radio-wlan-key;
    }
    list atf-client-stats {
      key "radio-mac radio-slot-id wlan-profile-name client-mac";
      description
        "AirTime Fairness client statistics";
      uses wireless-access-point-oper:st-atf-client-stats;
      uses wireless-types:radio-client-key;
    }
    list atf-mesh-stats {
      key "radio-mac radio-slot-id neigh-mac";
      description
        "AirTime Fairness mesh statistics";
      uses wireless-access-point-oper:st-atf-link-stats;
      uses wireless-types:radio-neigh-key;
    }
    list join-stats {
      key "wtp-mac";
      description
        "Contains the statistics related to AP join";
      uses wireless-access-point-oper:st-ap-join-info;
    }
    list discovery-stats {
      key "wtp-mac";
      description
        "Contains the statistics related to AP discovery process";
      uses wireless-access-point-oper:st-ap-discovery-info;
    }
    list ethernet-if-stats {
      key "wtp-mac if-index";
      description
        "Contains the Ethernet interface statistics";
      uses wireless-access-point-oper:ap-ethernet-intf-info;
      uses wireless-access-point-oper:ap-ethernet-intf-id;
    }
    list predownload-data {
      key "wtp-mac";
      description
        "Provides the information corresponding to AP Pre image download process";
      uses wireless-access-point-oper:capwap-wtp-predownload-data;
    }
    list qos-radio-data {
      key "radio-slot-id ap-mac";
      description
        "This object specify a table for QoS AP Radio data records in DB";
      uses wireless-access-point-oper:qos-ap-radio-data;
      uses wireless-access-point-oper:qos-ap-radio-key;
    }
    list qos-bssid-data {
      key "ssid-name radio-slot-id wtp-mac";
      description
        "This object specify a table for QoS BSSID data records in DB";
      uses wireless-access-point-oper:qos-bssid-data;
      uses wireless-access-point-oper:qos-bssid-key;
    }
    container qos-global-stats {
      presence "qos-global-stats";
      description
        "This object specify a table for QoS Global statistics data in DB";
      uses wireless-access-point-oper:qos-global-statistics;
    }
    list oper-config {
      key "wtp-mac";
      description
        "Contains the operational data corresponding to an 802.11 LWAPP Access Point";
      uses wireless-access-point-oper:st-ap-oper-config;
    }
    list cdp-cache-data {
      key "mac-addr cdp-cache-device-id";
      description
        "contains the cached neighbor information obtained via receiving CDP messages on APs. Entries are added when a CDP advertisement is received from a neighboring device. Entries get deleted when CDP is disabled on the interface or globally";
      uses wireless-access-point-oper:cdp-cache-data-op;
      uses wireless-access-point-oper:ewlc-cdp-cache-data-key;
      uses wireless-access-point-oper:cdp-cache-data-index-key;
    }
    list ap-client-trace-info {
      key "site-tag-name";
      description
        "AP trace information for clients";
      uses wireless-access-point-oper:ap-client-trace-site-tag-info;
    }
    list ap-client-trace-ap-info {
      key "ap-name";
      description
        "AP trace information for clients on an AP";
      uses wireless-access-point-oper:ap-client-trace-ap-info;
    }
    list ap-staggered-upgrade-report {
      key "report-name";
      unique "start-time";
      description
        "Staggered AP upgrade related information";
      uses wireless-access-point-oper:st-ap-staggered-upg-report {
        refine "start-time" {
          mandatory true;
        }
      }
    }
  }
}
