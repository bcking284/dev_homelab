module cisco-xe-openconfig-platform-deviation {
  // namespace
  namespace "http://openconfig.net/yang/cisco-xe-openconfig-platform-deviation";

  prefix oc-platform-devs;

  import openconfig-platform {
    prefix oc-platform;
  }

  import openconfig-alarms {
    prefix oc-alarms;
  }

  import openconfig-interfaces {
    prefix oc-if;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-platform module.";

  revision 2010-10-09 {
    description
      "Add deviations to remove openconfig-platform features not implemented in 16.10";
 
    reference
      "RFC 6020: YANG - A Data Modeling Language for the
       Network Configuration Protocol (NETCONF)";
  }

 deviation "/oc-platform:components" {
      deviate not-supported; 
      description
        "oc-platform not supported in 16.10.";
  }

 deviation "/oc-platform:components/oc-platform:component/oc-platform:state/oc-alarms:equipment-failure" {
      deviate not-supported; 
      description
        "oc-alarms equipment-failure not supported in 16.10.";
  }

 deviation "/oc-platform:components/oc-platform:component/oc-platform:state/oc-alarms:equipment-mismatch" {
      deviate not-supported; 
      description
        "oc-alarms equipment-mismatch not supported in 16.10.";
  }

 deviation "/oc-if:interfaces/oc-if:interface/oc-if:state/oc-platform:hardware-port" {
      deviate not-supported; 
      description
        "oc-platform hardware-port not supported in 16.10.";
  }

}
