module tailf-xsd-types {
  namespace "http://tail-f.com/yang/xsd-types";
  prefix xs;

  description
    "This module contains useful XML Schema Datatypes that are not
     covered by YANG types directly.";

  revision 2017-11-20 {
    description
      "Released as part of ConfD-6.5.2 / NCS-4.5.2.

       Changed the namespace to make it possible to load the module.";
  }

  revision 2009-03-17 {
    description
      "Initial revision.";
  }

  typedef duration {
    type string;
    reference
      "http://www.w3.org/TR/xmlschema-2/#duration";
  }

  typedef date {
    type string;
    reference
      "http://www.w3.org/TR/xmlschema-2/#date";
  }

  typedef time {
    type string;
    reference
      "http://www.w3.org/TR/xmlschema-2/#time";
  }

  typedef token {
    type string;
    reference
      "http://www.w3.org/TR/xmlschema-2/#token";
  }

  typedef hexBinary {
    type string;
    reference
      "http://www.w3.org/TR/xmlschema-2/#hexBinary";
  }

  typedef QName {
    type string;
    reference
      "http://www.w3.org/TR/xmlschema-2/#QName";
  }

  typedef decimal {
    type string;
    reference
      "http://www.w3.org/TR/xmlschema-2/#decimal";
  }

  typedef float {
    type string;
    reference
      "http://www.w3.org/TR/xmlschema-2/#float";
  }

  typedef double {
    type string;
    reference
      "http://www.w3.org/TR/xmlschema-2/#double";
  }

  extension fraction-digits {
    argument num;
    description
      "To be used as a restriction with type xs:decimal.";
    reference
      "http://www.w3.org/TR/xmlschema-2/#rf-fractionDigits";
  }

  extension total-digits {
    argument num;
    description
      "To be used as a restriction with type xs:decimal.";
    reference
      "http://www.w3.org/TR/xmlschema-2/#rf-totalDigits";
  }
}
