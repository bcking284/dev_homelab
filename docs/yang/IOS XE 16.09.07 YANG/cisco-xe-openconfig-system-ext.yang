module cisco-xe-openconfig-system-ext{

  yang-version "1";

  // namespace
  namespace "http://cisco.com/ns/yang/cisco-xe-openconfig-system-ext";

  prefix "oc-system-cisco";

  import openconfig-system { prefix oc-sys; }


  // import some basic types
  import openconfig-extensions { prefix oc-ext; }
  import tailf-common { prefix tailf; }


  // meta
  organization "Cisco";

  contact
    "www.cisco.com";

  description
    "Cisco augmentation to oc-system model.";

  oc-ext:openconfig-version "1.0.2";

  revision "2018-03-21" {
    description
      "Removed augmented source interface leafs Add optional vrf configuration for the logging source interface";
  }

  revision "2018-01-11" {
    description
      "Moved radius and tacacs source interface leafs to top of servers list";
  }

  revision "2017-12-16" {
    description
      "Added radius and tacacs source interface leafs";
  }

  revision "2017-11-16" {
    description
      "Added support for end user license agreement";
  }
  revision "2017-10-19" {
    description
      "Added support ntp source interface configuration and config state";
  }

  augment "/oc-sys:system/oc-sys:logging/oc-sys:remote-servers/oc-sys:remote-server/oc-sys:config" {
      leaf vrf {
        type string;
      }
      description
        "vrf if used by the interface forwarding logging messages";
  }

  augment "/oc-sys:system/oc-sys:logging/oc-sys:remote-servers/oc-sys:remote-server/oc-sys:state" {
      leaf vrf {
        type string;
      }
      description
        "vrf if used by the interface forwarding logging messages";
  }

  augment "/oc-sys:system/oc-sys:state" {
    container license {
      leaf eula {
        type string;
        description
          "The end user license agreement text";
      }
    }
  }
}
