module cisco-xe-ietf-routing-deviation {
  namespace "http://cisco.com/ns/cisco-xe-ietf-routing-deviation";

  prefix rt-devs;

  import ietf-routing {
    prefix rt;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for ietf-routing
     module.";

  revision 2016-07-09 {
    description
      "Added deviation to last-updated to change the type from
      yang:date-and-time to type string.";
  }

  revision 2015-09-11 {
    description
      "Initial Revision";

    reference
      "RFC 6020: YANG - A Data Modeling Language for the
       Network Configuration Protocol (NETCONF)";

  }

  deviation /rt:routing/rt:routing-instance/rt:type {
    deviate not-supported;
    description  "Not supported in IOS-XE 3.17 release.";
  }

  deviation /rt:routing/rt:routing-instance/rt:enabled {
    deviate not-supported;
    description  "Not supported in IOS-XE 3.17 release.";
  }

  deviation "/rt:routing/rt:routing-instance/rt:routing-protocols" +
            "/rt:routing-protocol/rt:description" {
    deviate not-supported;
    description  "Not supported in IOS-XE 3.17 release.";
  }

  deviation "/rt:routing-state/rt:routing-instance/rt:ribs/rt:rib/rt:routes/rt:route/rt:last-updated" {
        description
            "Modifies the usage of yang:date-and-time in itef-routing
             temporarily to string so that Router's time notation is 
             passed as it is without conversion to yang:date-and-time format.";

        deviate replace {
            type string;
        }

    }
}
