module Cisco-IOS-XE-wireless-rrm-cfg {
  yang-version 1;
  namespace "http://cisco.com/ns/yang/Cisco-IOS-XE-wireless-rrm-cfg";
  prefix wireless-rrm-cfg;

  import Cisco-IOS-XE-wireless-enum-types {
    prefix wireless-enum-types;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing rrm configurations
     Copyright (c) 2016-2018 by Cisco Systems, Inc.
     All rights reserved.";

  revision 2018-08-09 {
    description
      "Added range set and must constraints for Radio band";
    reference "4.0.0";
  }
  revision 2018-03-21 {
    description
      "Leaf removal";
    reference "3.0.0";
  }
  revision 2018-01-24 {
    description
      "The first generally available version";
    reference "2.0.0";
  }
  revision 2017-05-05 {
    description
      "Initial revision";
    reference "1.0.0";
  }

  grouping rrm-rrm-config {
    description
      "This object indicates the general configurations for RRM";
    leaf dca-mode {
      type wireless-enum-types:rrm-control-mode;
      default "rrm-automatic";
      description
        "Dynamic channel assignment(DCA) has three modes. When the mode is auto, the channel assignment will be periodically updated for all Airespace APs that permit this operation. When the DCA is runOnce, channel assignments are updated based on the UPDATE_CMD received from the management. When the DCA is static, no dynamic channel assignments occurs and value are set to their global default. Default is auto.
         Possible values are:
         0 = Automatic Channel selection
         1 = Channel selection is done only once
         2 = Static channel selection";
    }
    leaf dca-update-interval-sec {
      type uint32;
      default "600";
      description
        "When Channel dynamic alogirthm is running, this interval (in secs) specifies how often Channel assignement updates are attempted on an Airespace AP. NOTE: hysteresis is built into the algorithms so we will not have uproductive changes occuring. Default value is 600 secs";
    }
    leaf dca-contribution {
      type uint32;
      default "7";
      description
        "This attribute is a bit mask specifying what to include in DCA optimization";
    }
    leaf dca-contribution-noise {
      type boolean;
      default "true";
      description
        "This object specifies the state of noise on the controller. A value of 'true' indicates that the detection is enabled. A value of 'false' indicates that the detection is disabled";
    }
    leaf dca-contribution-interference {
      type boolean;
      default "true";
      description
        "This object specifies the state of interference on the controller. A value of 'true' indicates that the detection is enabled. A value of 'false' indicates that the detection is disabled.";
    }
    leaf dca-contribution-load {
      type boolean;
      default "false";
      description
        "This object specifies the state of load on the controller. A value of 'true' indicates that the detection is enabled. A value of 'false' indicates that the detection is disabled.";
    }
    leaf dca-contribution-signal {
      type boolean;
      default "true";
      description
        "This object specifies the state of signal on the controller. A value of 'true' indicates that the detection is enabled. A value of 'false' indicates that the detection is disabled.";
    }
    leaf dca-contribution-device {
      type boolean;
      default "false";
      description
        "This object specifies the state of device detection on the controller. A value of 'true' indicates that the detection is enabled. A value of 'false' indicates that the detection is disabled.";
    }
    leaf txpower-mode {
      type wireless-enum-types:rrm-control-mode;
      default "rrm-automatic";
      description
        "Dynamic transmit power (DTP) has three modes. When the mode is auto, the transmit power of each Airespace AP will be periodically updated for all Airespace APs that permit this operation. When the DTP is runOnce,transmit power update will occur based on the UPDATE_CMD received from the management. When the DTP is static, no dynamic transmit power updates occur and their global defaults are used. Default is auto.
         Possible values are:
         0 = Automatic power selection
         1 = Power selection is done only once
         2 = Static power selection";
    }
    leaf txpower-update-interval-sec {
      type uint32;
      default "600";
      description
        "When Tx PowerControl dynamic alogirthm is running, this interval(in secs) specifies how often TxPower control updates are attempted on an Airespace AP. NOTE: hysteresis is build into the algorithms so we will not have uproductive changes occuring. Default value is 600 secs";
    }
    leaf txpower-contribution {
      type uint8;
      default "7";
      description
        "This attribute is a bit mask specifying what to include in DCA optimization";
    }
    leaf txpower-update-cmd-invoke {
      type uint8;
      default "0";
      description
        "When set to activate this starts a DTP calculation regardless of the dynamic update interval. This command should be invoke on Group Leader Airespace Switch.Invoking on a Airespace Switch which is not a Group leader has no effect.";
    }
    leaf monitor-noise-interference-interval {
      type uint32 {
        range "60 .. 3600";
      }
      default "180";
      description
        "This interval( in secs) specifies how often do we get new noise and interference measurements at each Airespace AP. Default is 300 secs";
    }
    leaf monitor-channel-mode {
      type wireless-enum-types:channel-monitor-mode;
      default "rrm-channels-country";
      description
        "This attribute specifies the channels on which the switch monitors noise, interference and rogues. The first option allows monitoring on all channels while the second one on only those that are supported by the country of operation. the option dca implies that the monitor channel list will include those channels that are used by automatic channel assignment.
         Possible values:
         1 = Monitoring on channels that are supported by the country of operation,
         2 = Monitoring on all channels,
         3 = Monitoring on those channels that are used by automatic channel assignment,";
    }
    leaf monitor-rssi-normalization {
      type boolean;
      default "true";
      description
        "The attribute specifies 802.11 configured RRM Neighbor Discovery RSSI Normalization";
    }
    leaf channel-monitor-status {
      type boolean;
      default "true";
      description
        "The attribute is a truth value indicating if the neighbor monitoring is enabled. A truth value of true indicates monitoriing is disabled. Truth value of false indicate monitoring is enabled.";
    }
    leaf monitor-load-interval {
      type uint32 {
        range "60 .. 3600";
      }
      default "60";
      description
        "This interval( in secs) specifies how often do we get new load measurements at each Airespace AP. Default is 300 secs";
    }
    leaf neighbor-interval {
      type uint16 {
        range "60 .. 3600";
      }
      default "180";
      description
        "This interval( in secs) specifies how often do we get new signal strength measurements at each Airespace AP. Default is 300 secs";
    }
    leaf monitor-coverage-interval {
      type uint32 {
        range "60 .. 3600";
      }
      default "180";
      description
        "This interval( in secs) specifies how often do we get new coverage measurements at each Airespace AP. Default is 300 secs";
    }
    leaf sys-log-load {
      type uint8;
      default "0";
      description
        "The attribute is a truth value indicating the logging mode for load profile. A truth value of true indicates logging is enabled. Truth value of false indicate monitoring is disabled.";
    }
    leaf sys-log-noise {
      type uint8;
      default "0";
      description
        "The attribute is a truth value indicating the logging mode for noise profile. A truth value of true indicates logging is enabled. Truth value of false indicate monitoring is disabled.";
    }
    leaf sys-log-foreign {
      type uint8;
      default "0";
      description
        "The attribute is a truth value indicating the logging mode for foreign profile. A truth value of true indicates logging is enabled. Truth value of false indicate monitoring is disabled.";
    }
    leaf sys-log-tx-power {
      type uint8;
      default "0";
      description
        "The attribute is a truth value indicating the logging mode for transmit power change. A truth value of true indicates logging is enabled. Truth value of false indicate monitoring is disabled.";
    }
    leaf sys-log-coverage {
      type uint8;
      default "0";
      description
        "The attribute is a truth value indicating the logging mode for coverage profile. A truth value of true indicates logging is enabled. Truth value of false indicate monitoring is disabled.";
    }
    leaf sys-log-performance {
      type uint8;
      default "0";
      description
        "The attribute is a truth value indicating the logging mode for performance profile. A truth value of true indicates logging is enabled. Truth value of false indicate monitoring is disabled.";
    }
    leaf sys-log-channel {
      type uint8;
      default "0";
      description
        "The attribute is a truth value indicating the logging mode for dynamic channel change. A truth value of true indicates logging is enabled. Truth value of false indicate monitoring is disabled.";
    }
    leaf ndp-type-data {
      type uint32 {
        range "0 .. 1";
      }
      default "0";
      description
        "This attribute indicates the mode of NDP. The possible values are either 0 or 1, where 0 indicates if NDP is transparent and 1 indicates it is protected.";
    }
    leaf roaming-en {
      type boolean;
      default "false";
      description
        "This attribute is truth value indicating if the optimized roaming is enabled. The vlaue true indicates optimized roaming is enabled. The value false indicates optimized roaming is disabled.";
    }
    leaf data-rate-threshold {
      type uint16;
      default "0";
      description
        "This attribute indicates configured data rate threshold for 802.11 Optimized Roaming";
    }
    leaf rrm-meas-req-state {
      type boolean;
      default "false";
      description
        "Indicates configured support of 802.11 CCX Client Location Measurements";
    }
    leaf rrm-meas-req-interval {
      type uint32 {
        range "10 .. 32400";
      }
      default "60";
      description
        "Indicates configured 802.11 CCX Client Location Measurements interval.";
    }
    leaf dca-long-interval {
      type uint8;
      default "0";
      description
        "This attribute indicates configured DCA interval value in hours. Possible values are 1,2,3,4,6,8,12 and 24 hours, 0 = 10 minutes (default).";
    }
    leaf dca-anchor-hour {
      type uint8 {
        range "0 .. 23";
      }
      default "0";
      description
        "This attribute indicates configured anchor time for DCA, hour of the day. Valid value should be in the range 0-23";
    }
    leaf dca-thresh {
      type uint8;
      default "1";
      description
        "This attribute indicates configured dynamic channel assignement sensitivity level to changes in the environment";
    }
    leaf coverage-global-enable {
      type boolean;
      default "true";
      description
        "This object represents the state of CHD (Coverage Hole Detection) on the controller. A value of 'true' indicates that the detection is enabled. A value of 'false' indicates that the detection is disabled.";
    }
    leaf coverage-data-failed-packet-count {
      type uint8 {
        range "1 .. 255";
      }
      default "50";
      description
        "This object represents the minimum threshold on the Data packet count required to trigger the CHD algorithm on the controller.";
    }
    leaf coverage-data-failed-packet-percentage {
      type uint8 {
        range "1 .. 100";
      }
      default "50";
      description
        "This object represents the threshold on the percent of Data packets dropped, that is required to trigger the CHD algorithm on the controller.";
    }
    leaf coverage-data-packet-rssi-threshold {
      type int8 {
        range "-90 .. -60";
      }
      default "-80";
      description
        "This object represents the RSSI threshold value for Data packets, that is required to trigger the CHD algorithm on the controller.";
    }
    leaf coverage-voice-failed-packet-count {
      type uint8 {
        range "1 .. 255";
      }
      default "100";
      description
        "This object represents the minimum threshold on the Voice packet count required to trigger the CHD algorithm on the controller.";
    }
    leaf coverage-voice-failed-packet-percentage {
      type uint8 {
        range "1 .. 100";
      }
      default "50";
      description
        "This object represents the threshold on the percent of Voice packets dropped, that is required to trigger the CHD algorithm on the controller.";
    }
    leaf coverage-voice-packet-rssi-threshold {
      type int8 {
        range "-90 .. -60";
      }
      default "-80";
      description
        "This object represents the RSSI threshold value for Voice packets, that is required to trigger the CHD algorithm on the controller.";
    }
    leaf dca-chan-width {
      type wireless-enum-types:dca-chan-width;
      default "dca-chan-width-20-mhz";
      description
        "This object specifies how the system performs DCA channel width selection: min - Min channel width the radio supports medium - Medium channel width the radio supports max - Max channel width supported by this radio.
         Possible values:
         0 = Channel width will be set to 20Mhz
         1 = Channel width will be set to 40Mhz
         2 = Channel width will be set to 80Mhz
         3 = Best channel width will be selected by DCA algorithm
         4 = Channel width will be set to 160Mhz";
    }
    leaf notification-interval {
      type uint16 {
        range "1 .. 10080";
      }
      default "3";
      description
        "Indicates time interval in minutes between each measurement report.";
    }
    leaf notification-tx-power-enable {
      type boolean;
      default "false";
      description
        "This attribute is a truth value indicating if the txpower change notification needs to enabled. The value of true indicates notification needs to be enabled.";
    }
    leaf notification-min-tx-power-threshold {
      type uint32 {
        range "3 .. 30";
      }
      default "6";
      description
        "Indicates the minimum threshold that the TPC will assign to each radio";
    }
    leaf notification-max-tx-power-threshold {
      type uint32 {
        range "3 .. 30";
      }
      default "6";
      description
        "Indicates the maximum threshold that the TPC will assign to each radio";
    }
    leaf notification-channel-enable {
      type boolean;
      default "false";
      description
        "This boolean indicates if notification are sent after a channel change. The value true indicates that notification will be sent. The value false indicates that notification will not be sent.";
    }
    leaf notification-channel-threshold {
      type uint32 {
        range "1 .. 1000";
      }
      default "1";
      description
        "This object indicates the number of channel changes after which the channel change notification is sent out.";
    }
    leaf dpc-min-tx-power-limit {
      type int32 {
        range "-10 .. 30";
      }
      default "-10";
      description
        "This defines the lower limit of transmit power in dBm. The value of this attribute has to be less than equal to value of clrRrmParametersMaxTxPower.";
    }
    leaf dpc-max-tx-power-limit {
      type int32 {
        range "-10 .. 30";
      }
      default "30";
      description
        "This defines the upper limit of transmit power in dBm. The value of this attribute has to be greater than equal to value of clrRrmParametersMinTxPower";
    }
    leaf dca-min-metric-rssi {
      type int32 {
        range "-100 .. -60";
      }
      default "-95";
      description
        "This defines the minimum RSSI energy metric required for DCA to change the channel";
    }
    leaf chan-width-cap {
      type wireless-enum-types:dca-chan-width-cap;
      default "dca-chan-width-cap-max";
      description
        "The object indicates the max Best Channel Width Allowed for Dynamic Bandwidth Selection. Possible values are 20,40,80 and 180 MHZ";
    }
  }

  grouping rrm-defaultlradcfg-config {
    description
      "This oject indicates the default configs related to radios";
    leaf bytes-per-sec {
      type uint32 {
        range "1000 .. 10000000";
      }
      default "1000000";
      description
        "802.11A throughput threshold between 1000 and 1000000";
    }
    leaf min-perf-snr {
      type int8;
      default "12";
      description
        "802.11A coverage threshold between 3 and 50.";
    }
    leaf exception-level {
      type uint16 {
        range "0 .. 100";
      }
      default "25";
      description
        "This object specifies the minimum percentage of clients in the coverage hole region of the AP, required to trigger a coverage hole exception";
    }
    leaf min-num-clients {
      type int32 {
        range "1 .. 200";
      }
      default "3";
      description
        "This object specifies the minimum number of clients required to trigger coverage hole.";
    }
    leaf automatic-cfg {
      type uint8;
      default "1";
      description
        "This boolean value indicates if the performance profiles enabed.";
    }
  }

  grouping rrm-cfg {
    description
      "This is the base object that holds all the configurations related radio resource management";
    leaf band {
      type uint8 {
        range "1 .. 2";
      }
      description
        "This the key to the st_rrm table and it indicates the band of the configurations.";
    }
    container rrm {
      description
        "This object hold all the basic rrm algorithms configurations.";
      uses wireless-rrm-cfg:rrm-rrm-config;
    }
    container default-radio-cfg {
      description
        "This object holds allthe radio related configs";
      uses wireless-rrm-cfg:rrm-defaultlradcfg-config;
    }
    container rrm-static-member-add-delete-entries {
      description
        "Static member configuration";
      list rrm-static-member-add-delete-entry {
        key "ip";
        description
          "A list of static member configurations";
        uses wireless-rrm-cfg:rrm-staticmember-add-delete;
      }
    }
  }

  grouping rrm-staticmember-add-delete {
    description
      "This object indicates the details about the static member configured";
    leaf ip {
      type inet:ip-address;
      description
        "The attribute indicates the ip address of the static member configured";
    }
    leaf name {
      type string;
      description
        "The attribute indicates the name of the static member configured";
    }
  }

  grouping rrm-mgr-rrm-config {
    description
      "This object holds all the rrm grouping algorithm related configs";
    leaf grouping-mode {
      type wireless-enum-types:rrm-control-mode;
      default "rrm-automatic";
      description
        "RF grouping has three modes. When RF grouping is set to AUTO the controller can be either in Auto leader or Auto member and when the mode is set to static the controller can be either in static meber or static leader.
         Possible values:
         0 = RF leader selected automatically
         1 = RF leader selection process will run only once
         2 = RF leader selection is stoped
         3 = RF leader selection was static
         4 = Restart the RF leader selection process";
    }
    leaf grouping-update-interval-sec {
      type uint32;
      default "600";
      description
        "This object indicates the period used by the grouping algorithm. The grouping algorithm runs when the group contents changes and automatic grouping is enabled. The system administrator can start grouping on demand.";
    }
  }

  grouping rrm-mgr {
    description
      "RRM Manager configuration";
    leaf band {
      type wireless-enum-types:radio-type;
      must
        "../band = 'dot11-2-dot-4-ghz' or
         ../band = 'dot11-5-ghz'" {
        error-message "Band must be dot11-2-dot-4-ghz or dot11-5-ghz";
        error-app-tag "must-violation";
      }
      description
        "This the key to the st_rrm_mgr table and it indicates the band of the configurations.
         Possible values:
         1 = 802.11bg
         2 = 802.11a";
    }
    container rrm {
      description
        "RRM Grouping Attributes";
      uses wireless-rrm-cfg:rrm-mgr-rrm-config;
    }
  }

  container rrm-cfg-data {
    description
      "This yang file contains all the fields related rrm feature";
    container rrms {
      description
        "RRM configuration";
      list rrm {
        key "band";
        description
          "This object holds all the rrm grouping algorithm related configs";
        uses wireless-rrm-cfg:rrm-cfg;
      }
    }
    container rrm-mgr-cfg-entries {
      description
        "Configuration related to RRM Algorithms";
      list rrm-mgr-cfg-entry {
        key "band";
        description
          "A list of entries related to RRM Algorithms";
        uses wireless-rrm-cfg:rrm-mgr;
      }
    }
  }
}
