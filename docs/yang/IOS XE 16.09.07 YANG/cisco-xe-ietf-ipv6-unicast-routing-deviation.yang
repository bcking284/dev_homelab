module cisco-xe-ietf-ipv6-unicast-routing-deviation {
  namespace "http://cisco.com/ns/cisco-xe-ietf-ipv6-unicast-routing-deviation";

  prefix v6ur-devs;

  import ietf-routing {
    prefix rt;
  }

  import ietf-ipv6-unicast-routing {
    prefix v6ur;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for ietf-ipv6-unicast-routing
     module.";

  revision 2015-09-11 {
    description
      "Initial Revision";

    reference
      "RFC 6020: YANG - A Data Modeling Language for the
       Network Configuration Protocol (NETCONF)";
  }

  deviation "/rt:routing/rt:routing-instance/rt:routing-protocols" +
            "/rt:routing-protocol/rt:static-routes/v6ur:ipv6" +
            "/v6ur:route/v6ur:description" {
    deviate not-supported;
    description  "Not supported in IOS-XE 3.17 release.";
  }
}
