module Cisco-IOS-XE-bfd-oper {
  yang-version 1;
  namespace "http://cisco.com/ns/yang/Cisco-IOS-XE-bfd-oper";
  prefix bfd-ios-xe-oper;

  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for BFD neighbor monitoring.
     Copyright (c) 2016-2018 by Cisco Systems, Inc.
     All rights reserved.";

  revision 2017-09-10 {
    description
      "Enum renames";
    reference "2.0.0";
  }
  revision 2017-02-07 {
    description
      "Initial revision";
    reference "1.0.0";
  }

  typedef bfd-oper-session-type {
    type enumeration {
      enum "ipv4" {
        value 0;
      }
      enum "ipv6" {
        value 1;
      }
      enum "vccv" {
        value 2;
      }
      enum "mpls-tp" {
        value 3;
      }
      enum "ipv4-multihop" {
        value 4;
      }
      enum "ipv6-multihop" {
        value 5;
      }
    }
    description
      "BFD session type";
  }

  typedef bfd-remote-state-type {
    type enumeration {
      enum "remote-up" {
        value 0;
      }
      enum "remote-down" {
        value 1;
      }
      enum "remote-init" {
        value 2;
      }
      enum "remote-admindown" {
        value 3;
      }
      enum "remote-invalid" {
        value 4;
      }
    }
    description
      "BFD remote state type";
  }

  typedef bfd-state-type {
    type enumeration {
      enum "admindown" {
        value 0;
      }
      enum "down" {
        value 1;
      }
      enum "fail" {
        value 2;
      }
      enum "init" {
        value 3;
      }
      enum "up" {
        value 4;
      }
      enum "invalid" {
        value 5;
      }
    }
    description
      "BFD state type";
  }

  typedef bfd-lsp-type {
    type enumeration {
      enum "working" {
        value 0;
      }
      enum "protect" {
        value 1;
      }
      enum "unknown" {
        value 2;
      }
    }
    description
      "BFD LSP type";
  }

  grouping bfd-neighbor-params {
    description
      "BFD neighbour parameters";
    leaf ld {
      type uint32;
      description
        "Local discriminator";
    }
    leaf rd {
      type uint32;
      description
        "Remote discriminator";
    }
    leaf remote-state {
      type bfd-ios-xe-oper:bfd-remote-state-type;
      description
        "Remote Heard. RH state of BFD version '0' 
         is also mapped to up/down";
    }
    leaf state {
      type bfd-ios-xe-oper:bfd-state-type;
      description
        "BFD state";
    }
  }

  grouping bfd-tunnel-path-key {
    description
      "BFD tunnel Path Key";
    leaf interface {
      type string;
      description
        "Associated interface";
    }
    leaf lsp-type {
      type bfd-ios-xe-oper:bfd-lsp-type;
      description
        "LSP type";
    }
  }

  grouping bfd-circuit-key {
    description
      "BFD circuit key";
    leaf interface {
      type string;
      description
        "Associated interface";
    }
    leaf vcid {
      type uint32;
      description
        "Virtual circuit identifier";
    }
  }

  grouping bfd-nbr-key {
    description
      "BFD Neighbor key";
    leaf ip {
      type inet:ip-address;
      description
        "Neighbor IP address";
    }
    leaf interface {
      type string;
      description
        "Interface";
    }
  }

  grouping mhop-nbr-key {
    description
      "BFD MHOP Neighbor key";
    leaf ip {
      type inet:ip-address;
      description
        "Neighbor IP address";
    }
    leaf src-ip {
      type inet:ip-address;
      description
        "Source IP address";
    }
  }

  grouping mhop-vrf-nbr-key {
    description
      "BFD MHOP VRF Neighbor key";
    leaf ip {
      type inet:ip-address;
      description
        "Neighbor IP address";
    }
    leaf vrf {
      type string;
      description
        "Neighbor VFR";
    }
    leaf src-ip {
      type inet:ip-address;
      description
        "Source IP address";
    }
  }

  grouping bfd-session-v2 {
    description
      "BFD session data";
    leaf type {
      type bfd-ios-xe-oper:bfd-oper-session-type;
      description
        "Session type";
    }
    container bfd-tunnel-paths {
      description
        "BFD tunnel path information";
      list bfd-tunnel-path {
        when "../../type='mpls-tp'";
        key "interface lsp-type";
        description
          "List of BFD tunnel paths";
        uses bfd-ios-xe-oper:bfd-tunnel-path-key;
        uses bfd-ios-xe-oper:bfd-neighbor-params;
      }
    }
    container bfd-circuits {
      description
        "BFD circuit information";
      list bfd-circuit {
        when "../../type='vccv'";
        key "interface vcid";
        description
          "List of BFD circuits";
        uses bfd-ios-xe-oper:bfd-circuit-key;
        uses bfd-ios-xe-oper:bfd-neighbor-params;
      }
    }
    container bfd-nbrs {
      description
        "BFD neighbor information";
      list bfd-nbr {
        when "../../type!='mpls-tp' and ../../type!='vccv'";
        key "ip interface";
        description
          "List of BFD neighbors";
        uses bfd-ios-xe-oper:bfd-nbr-key;
        uses bfd-ios-xe-oper:bfd-neighbor-params;
      }
    }
    container bfd-mhop-nbrs {
      description
        "Multi hop neighbors for multi hop neighbor scenario 
         for global VRF (no VRF)";
      list bfd-mhop-nbr {
        when "../../type='ipv4-multihop' or ../../type='ipv6-multihop'";
        key "ip src-ip";
        description
          "List of MHOP neighbors";
        uses bfd-ios-xe-oper:mhop-nbr-key;
        uses bfd-ios-xe-oper:bfd-neighbor-params;
      }
    }
    container bfd-mhop-vrf-nbrs {
      description
        "Multi hop neighbors for multi hop neighbor scenario
         with non-global VRF";
      list bfd-mhop-vrf-nbr {
        when "../../type='ipv4-multihop' or ../../type='ipv6-multihop'";
        key "ip vrf src-ip";
        description
          "List of multi hop neighbors";
        uses bfd-ios-xe-oper:mhop-vrf-nbr-key;
        uses bfd-ios-xe-oper:bfd-neighbor-params;
      }
    }
  }

  container bfd-state {
    config false;
    description
      "BFD neighbor information";
    container sessions {
      description
        "BFD neighbor session information";
      list session {
        key "type";
        description
          "List of BFD sessions";
        uses bfd-ios-xe-oper:bfd-session-v2;
      }
    }
  }
}
