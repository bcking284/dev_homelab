/*
 * Generated by confdc --mib2yang-std
 * Source: mgmt/dmi/model/mib/src/patched/CISCO-SIP-UA-MIB.mib
 */
/*
 * This YANG module has been generated by smidump 0.5.0:
 *
 *      smidump -f yang CISCO-SIP-UA-MIB
 *
 * Do not edit. Edit the source file instead!
 */

module CISCO-SIP-UA-MIB {

  namespace "urn:ietf:params:xml:ns:yang:smiv2:CISCO-SIP-UA-MIB";
  prefix CISCO-SIP-UA-MIB;

  import IF-MIB {
    prefix "if-mib";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "       Cisco Systems
    Customer Service
    
    Postal: 170 W. Tasman Drive
    San Jose, CA  95134
    USA
    
    Tel: +1 800 553-NETS
    
    E-mail: cs-sip@cisco.com";

  description
   "Cisco User Agent Session Initiation Protocol (SIP) 
    MIB module.  SIP is an application-layer signalling
    protocol for creating, modifying and terminating
    multimedia sessions with one or more participants.
    These sessions include Internet multimedia conferences
    and Internet telephone calls.  SIP is defined in 
    RFC 2543 (March 1999).  
    
    This MIB is defined for the management of SIP User 
    Agents (UAs).  A User Agent is an application which 
    contains both a User Agent Client (UAC) and a User 
    Agent Server (UAS).   A UAC is an application that 
    initiates a SIP request.  A UAS is an application that 
    contacts the user when a SIP request is received and 
    that returns a response on behalf of the user.  The 
    response accepts, rejects, or redirects the request.
    
    A SIP transaction occurs between a client and a server 
    and comprises all messages from the first request sent
    from the client to the server up to a final (non-1xx) 
    response sent from the server to the client.";

  revision 2004-02-19 {
    description
     " Addition of the following objects:
      cSipCfgSuspendResumeEnabled
      cSipCfgTimerHold
      cSipCfgTimerInfo
      cSipCfgTimerConnectionAging
      cSipCfgTimerBufferInvite
      cSipCfgRetryInfo
      cSipCfgRetrySubscribe
      cSipCfgOfferCallHold
      cSipCfgPeerSwitchTransEnabled
      cSipCfgSwitchTransportEnabled
      cSipCfgMaximumForwards
      cSipCfgReasonHeaderOveride
      
      cSipCfgBindSourceAddrTable ->
          cSipCfgBindSourceAddrEntry 
          cSipCfgBindSourceAddrScope 
          cSipCfgBindSourceAddrInterface 
      cSipCfgVoiceServiceVoip ->
          cSipCfgHeaderPassingEnabled
          cSipCfgMaxSubscriptionAccept 
          cSipCfgMaxSubscriptionOriginate
      
      cSipStatsRedirMovedTempsIns
      cSipStatsRedirMovedTempsOuts
      cSipStatsRetryInfo
      cSipStatsRetrySubscribe
      cSipStatsClientReqPendingIns
      cSipStatsClientReqPendingOuts
      cSipStatsTrafficUpdateIns
      cSipStatsTrafficUpdateOuts
      cSipStatsConnTCPSendFailures
      cSipStatsConnUDPSendFailures
      cSipStatsConnTCPRemoteClosures
      cSipStatsConnUDPCreateFailures
      cSipStatsConnTCPCreateFailures
      cSipStatsConnUDPInactiveTimeouts
      cSipStatsConnTCPInactiveTimeouts
      cSipStatsActiveUDPConnections
      cSipStatsActiveTCPConnections
      
      Deprecated the following objects:
      cSipCfgMaxForwards
      cSipStatsRedirMovedTemps
      cSipCfgBindSrcAddrScope
      cSipCfgBindSrcAddrInterface
      
      Addition of the following Conformance objects:
      ciscoSipTrafficStatsGroupRev3
      ciscoSipStatsRedirStatusCodesGroupRev2
      ciscoSipTimerConfigGroupRev4
      ciscoSipRetryStatsGroupRev4
      ciscoSipBaseIOSConfigGroupRev1
      ciscoSipStatsClientStatusCodesGroupRev4
      ciscoSipRetryConfigGroupRev4
      ciscoSipCfgPeerGroupRev1
      ciscoSipCfgVoiceServiceVoipGroup
      ciscoSipStatsConnectionGroup
      
      Deprecated the following Conformance objects:
      ciscoSipTrafficStatsGroupRev2
      ciscoSipStatsRedirStatusCodesGroupRev1
      ciscoSipTimerConfigGroupRev3
      ciscoSipRetryStatsGroupRev3
      ciscoSipBaseIOSConfigGroup
      ciscoSipStatsClientStatusCodesGroupRev3
      ciscoSipRetryConfigGroupRev3
      ciscoSipCfgPeerGroup
      
      Addition of the following Compliance object:
      ciscoSipComplianceRev5
      
      Deprecated the following Compliance object:
      ciscoSipComplianceRev4";
  }

  revision 2002-05-08 {
    description
     " Addition of the following textual conventions:
      CSipStatusCode
      CSipMethodStr
      
      Addition of the following objects:
      cSipCfgRedirectionDisabled
      cSipCfgTimerSessionTimer
      cSipCfgEarlyMediaTable
          cSipCfgEarlyMediaStatusCodeIndex
          cSipCfgEarlyMediaCutThruDisabled
      cSipStatsClientSTTooSmallIns
      cSipStatsClientSTTooSmallOuts
      cSipStatsMisc3xxMappedTo4xxRsps
      cSipStatsSuccessOkTable
          cSipStatsSuccessOkMethod
          cSipStatsSuccessOkInbounds
          cSipStatsSuccessOkOutbounds
      cSipCfgSymNatEnabled
      cSipCfgSymNatDirectionRole";
  }

  revision 2001-10-05 {
    description
     "Obsoleting  cSipStatsRedirSeeOthers, 
      cSipStatsClientLengthRequiredIns and
      cSipStatsClientLengthRequiredOuts.
      Add cSipCfgTimerRefer, cSipCfgRetryRefer,
      and cSipStatsRetryRefers.
      Deprecated old-style ciscoSipUaMIBNotificationPrefix.";
  }

  revision 2001-09-07 {
    description
     "Neglected to deprecate 
      ciscoSipStatsClientStatusCodesGroupRev1 
      in the previous revision where 
      ciscoSipStatsClientStatusCodesGroupRev2 
      was made current.";
  }

  revision 2001-08-21 {
    description
     "Deprecating cSipStatsRedirSeeOthers, 
      cSipStatsClientLengthRequiredIns and
      cSipStatsClientLengthRequiredOuts.
      The SIP status codes related to these
      counters have been removed from 
      RFC2543bis03 version of the standard.";
  }

  revision 2001-08-02 {
    description
     "Addition of the following objects:
      cSipCfgAaaUsername
      cSipStatsTrafficInfoIns
      cSipStatsTrafficInfoOuts
      cSipStatsTrafficSubscribeIns
      cSipStatsTrafficSubscribeOuts
      cSipStatsClientBadEventIns
      cSipStatsClientBadEventOuts";
  }

  revision 2001-06-07 {
    description
     "Addition of the following objects:
      cSipCfgBindSrcAddrInterface
      cSipCfgBindSrcAddrScope
      cSipCfgDnsSrvQueryStringFormat
      cSipStatsTrafficReferIns
      cSipStatsTrafficReferOuts
      cSipStatsTrafficNotifyIns
      cSipStatsTrafficNotifyOuts
      cSipStatsSuccessAcceptedIns
      cSipStatsSuccessAcceptedOuts
      cSipCfgTimerNotify 
      cSipCfgRetryNotify
      cSipCfgStatusCodeIndex   
      cSipCfgPstnCause
      cSipCfgStatusCauseStoreStatus
      cSipCfgPstnCauseIndex
      cSipCfgStatusCode   
      cSipCfgCauseStatusStoreStatus
      cSipStatsRetryNotifys";
  }

  revision 2001-03-02 {
    description
     "Addition of the following objects:
      cSipCfgMaxForwards
      cSipCfgTimerPrack
      cSipCfgTimerComet
      cSipCfgTimerReliableRsp
      cSipCfgRetryPrack
      cSipCfgRetryComet
      cSipCfgRetryReliableRsp
      cSipCfgOutSessionTransport
      cSipCfgReliable1xxRspStr
      cSipCfgReliable1xxRspHdr
      cSipCfgUrlType
      cSipCfgPeerTable
          cSipCfgPeerIndex
          cSipCfgPeerOutSessionTransport
          cSipCfgPeerReliable1xxRspStr
          cSipCfgPeerReliable1xxRspHdr
          cSipCfgPeerUrlType
      cSipStatsClientReqTermIns
      cSipStatsClientReqTermOuts
      cSipStatsClientNoAcceptHereIns
      cSipStatsClientNoAcceptHereOuts
      cSipStatsServerPrecondFailureIns
      cSipStatsServerPrecondFailureOuts
      cSipStatsTrafficCometIns
      cSipStatsTrafficCometOuts
      cSipStatsTrafficPrackIns
      cSipStatsTrafficPrackOuts
      cSipStatsRetryPrack
      cSipStatsRetryComets
      cSipStatsRetryReliable1xxRsps";
  }

  typedef CSipStatusCode {
    type int32 {
      range "1..2147483647";
    }
    description
     "A textual convention reflecting a SIP 
      response status code value.";
  }

  typedef CSipMethodStr {
    type binary {
      length "1..32";
    }
    description
     "A textual convention reflecting SIP methods 
      supported by this user agent.  SIP methods 
      are case-sensitive.  Therefore, objects using 
      this textual convention must also have values
      that are case-sensitive.  All SIP methods must
      be represented as all upper case ASCII strings.  
      For example, 'INVITE'.";
  }

  identity ciscoSipUaMIBNotificationPrefix {
    base smiv2:object-identity;
    status deprecated;
    description
     "Old style notification prefixing.  Being replaced by
      ciscoSipUaMIBNotifs.";
    smiv2:oid "1.3.6.1.4.1.9.9.152.2";
  }

  identity ciscoSipUaMIBNotifications {
    base smiv2:object-identity;
    status deprecated;
    description
     "Old style notification prefixing.  Being replaced by
      ciscoSipUaMIBNotifs.";
    smiv2:oid "1.3.6.1.4.1.9.9.152.2.0";
  }


  container CISCO-SIP-UA-MIB {
    config false;

    container cSipCfgBase {
      smiv2:oid "1.3.6.1.4.1.9.9.152.1.1.1";

      leaf cSipCfgVersion {
        type snmp-framework:SnmpAdminString;
        description
         "This object will reflect the version of SIP supported by this 
          user agent.  It will follow the same format as SIP version 
          information contained in the SIP messages generated by this
          user agent.  For example, user agents supporting SIP version 2
          will return 'SIP/2.0' as dictated by RFC 2543.";
        smiv2:max-access "read-only";
        smiv2:oid "1.3.6.1.4.1.9.9.152.1.1.1.1";
      }

      leaf cSipCfgTransport {
        type enumeration {
          enum "udp" {
            value "1";
          }
          enum "tcp" {
            value "2";
          }
          enum "udpAndTcp" {
            value "3";
          }
          enum "disabled" {
            value "4";
          }
        }
        description
         "This object specifies the transport protocol the SIP user 
          agent will use to receive SIP messages.  A value of 'disabled'
          indicates that the UA will not receive any SIP messages.";
        smiv2:max-access "read-write";
        smiv2:oid "1.3.6.1.4.1.9.9.152.1.1.1.2";
      }

      leaf cSipCfgUserLocationServerAddr {
        type snmp-framework:SnmpAdminString;
        description
         "This object specifies address of the User Location 
          Server (ULS) being used to resolve the location of end 
          points.  This could be a Domain Name Server (DNS) or a 
          SIP proxy/redirect server.
          
          The format of the address follows the IETF service location 
          protocol. The syntax is as follows:
          
             mapping-type:type-specific-syntax
          
          the mapping-type specifies a scheme for mapping the matching 
          dial string to a target server. The type-specific-syntax is 
          exactly that, something that the particular mapping scheme can
          understand.  For example,
             Session target           Meaning
             ipv4:171.68.13.55:1006   The session target is the IP 
                                      version 4 address of 171.68.13.55 
                                      and port 1006.
             dns:pots.cisco.com       The session target is the IP host 
                                      with dns name pots.cisco.com.
          
          The valid Mapping type definitions for the peer follow:
             ipv4  - Syntax: ipv4:w.x.y.z:port or  ipv4:w.x.y.z 
             dns   - Syntax: dns:host.domain.";
        smiv2:max-access "read-write";
        smiv2:oid "1.3.6.1.4.1.9.9.152.1.1.1.3";
      }

      leaf cSipCfgMaxForwards {
        type int32 {
          range "1..70";
        }
        status deprecated;
        description
         "This object may be used with any SIP method to limit the 
          number of proxies that can forward the request to the next 
          downstream server.";
        smiv2:max-access "read-write";
        smiv2:oid "1.3.6.1.4.1.9.9.152.1.1.1.4";
      }

      leaf cSipCfgBindSrcAddrInterface {
        type if-mib:InterfaceIndexOrZero;
        status deprecated;
        description
         "This object may specify the interface where the
          source IP address used in SIP signalling or media
          packets is configured.  A value of 0 means that 
          there is no specific source address configured and 
          in this case the best local IP address will be chosen 
          by the system.";
        smiv2:defval "0";
        smiv2:max-access "read-write";
        smiv2:oid "1.3.6.1.4.1.9.9.152.1.1.1.5";
      }

      leaf cSipCfgBindSrcAddrScope {
        type enumeration {
          enum "none" {
            value "0";
          }
          enum "all" {
            value "1";
          }
          enum "control" {
            value "2";
          }
        }
        status deprecated;
        description
         "This object specifies the scope of packets to
          which the source IP address of the interface 
          designated by cSipCfgBindSrcAddrInterface
          will be bound.  A value of 'all' means the IP address 
          will be bound to both SIP signalling and media packets.
          A value of 'control' means the IP address will only
          be bound to SIP signalling packets.  
          If cSipCfgBindSrcAddrInterface is set to 0,
          the value of this object has no meaning.";
        smiv2:defval "all";
        smiv2:max-access "read-write";
        smiv2:oid "1.3.6.1.4.1.9.9.152.1.1.1.6";
      }

      leaf cSipCfgDnsSrvQueryStringFormat {
        type enumeration {
          enum "v1" {
            value "1";
          }
          enum "v2" {
            value "2";
          }
        }
        description
         "This object specifies the format of the prefix used 
          by the system for DNS SRV queries.
          
          v1  :  RFC 2052 format - 'protocol.transport.'
          v2  :  RFC 2782 format - '_protocol._transport.'
          
          This object allows backward compatibility with systems
          only supporting RFC 2052 format.";
        smiv2:defval "v2";
        smiv2:max-access "read-write";
        smiv2:oid "1.3.6.1.4.1.9.9.152.1.1.1.7";
      }

      leaf cSipCfgRedirectionDisabled {
        type boolean;
        description
         "This object specifies how call redirection (3xx)
          is handled by the user agent.  
          
          If 'false', the user agent's treatment of incoming 
          3xx class response messages is as defined in RFC 2543.  
          That is, the user agent uses the Contact header(s)
          from the 3xx response to reinitiate another INVITE
          transaction to the user's new location.  The call 
          is redirected.
          
          If 'true', the user agent treats incoming 3xx 
          response messages as 4xx (client error) class 
          response messages.  In this case, the call is not
          redirected, instead it is released with the 
          appropriate PSTN cause code.
          
          The mapping of SIP 3xx response status codes to
          4xx response status codes is as follows:
           300 Multiple Choices -> 410 Gone
           301 Moved Permanently -> 410 Gone
           302 Moved Temporarily -> 480 Temporarily Unavailable
           305 User Proxy        -> 410 Gone
           380 Alternative Service -> 410 Gone
           Any other 3xx -> 410 Gone";
        smiv2:defval "false";
        smiv2:max-access "read-write";
        smiv2:oid "1.3.6.1.4.1.9.9.152.1.1.1.8";
      }

      leaf cSipCfgSymNatEnabled {
        type boolean;
        description
         "This object specifies whether remote media checks
          for Symmetric Network Address Translation (NAT) 
          is enabled or disabled.
          
          If 'true', remote media checks are enabled.  The
          gateway will have the ability to open a Real Time 
          Transport Protocol (RTP) session with the remote
          end and then update (modify) the existing RTP
          session's remote address/port (raddr:rport) with
          the source address and port of the actual media
          packet received.  This would be triggered for only
          those calls where the Session Description Protocol
          (SDP) received by the gateway has an indication to
          do so.
          
          If 'false', remote media checks are disabled.";
        smiv2:defval "false";
        smiv2:max-access "read-write";
        smiv2:oid "1.3.6.1.4.1.9.9.152.1.1.1.10";
      }

      leaf cSipCfgSymNatDirectionRole {
        type enumeration {
          enum "none" {
            value "1";
          }
          enum "passive" {
            value "2";
          }
          enum "active" {
            value "3";
          }
        }
        description
         "This object specifies the value of the
          'a=direction:<role>' SDP attribute supported by 
          the user agent.  The direction attribute is used 
          to describe the role of the user agent (as an 
          endpoint for a connection-oriented media stream) 
          in the connection setup procedure.
          
          none    :  No role is specified.
          passive :  The user agent will advertise itself
                     as a 'passive' entity (inside the NAT)
                     in the SDP.
          active  :  The user agent will advertise itself
                     as a 'active' entity (outside the NAT)
                     in the SDP.";
        smiv2:defval "none";
        smiv2:max-access "read-write";
        smiv2:oid "1.3.6.1.4.1.9.9.152.1.1.1.11";
      }

      leaf cSipCfgSuspendResumeEnabled {
        type boolean;
        description
         "This object specifies if support for handling 
          Suspend/Resume events from the switch is enabled or not.
          
          If 'true', the user agent on getting a Suspend will
          notify the remote agent by sending it a re-invite with
          a hold SDP. Similarly, when the Gateway receives a Resume, it
          will initiate a re-invite with the original SDP and unhold the
          call.
          
          If 'false', the user agent will not initiate any re-invites
          on receiving Suspend/Resume events, basically it won't be
          putting the call on hold or off hold.";
        smiv2:defval "true";
        smiv2:max-access "read-write";
        smiv2:oid "1.3.6.1.4.1.9.9.152.1.1.1.13";
      }

      leaf cSipCfgOfferCallHold {
        type enumeration {
          enum "directionAttr" {
            value "1";
          }
          enum "connAddr" {
            value "2";
          }
        }
        description
         "This object specifies how the SIP gateway would initiate call
          hold requests.
          
          directionAttr: The user agent will use the direction
                          attribute such as a=sendonly or a=inactive in
                          the sdp to initiate call hold requests.
                            
          connAddr: The user agent will use 0.0.0.0 connection address
                     to specify Call Hold.";
        smiv2:defval "directionAttr";
        smiv2:max-access "read-write";
        smiv2:oid "1.3.6.1.4.1.9.9.152.1.1.1.14";
      }

      leaf cSipCfgReasonHeaderOveride {
        type boolean;
        description
         "This object specifies that the Reason header overrides SIP 
          status code mapping table.";
        smiv2:defval "false";
        smiv2:max-access "read-write";
        smiv2:oid "1.3.6.1.4.1.9.9.152.1.1.1.15";
      }

      leaf cSipCfgMaximumForwards {
        type int32 {
          range "1..70";
        }
        description
         "This object may be used with any SIP method to limit the 
          number of proxies that can forward the request to the next 
          downstream server.";
        smiv2:defval "70";
        smiv2:max-access "read-write";
        smiv2:oid "1.3.6.1.4.1.9.9.152.1.1.1.16";
      }
    }

    container cSipCfgTimer {
      smiv2:oid "1.3.6.1.4.1.9.9.152.1.1.2";

      leaf cSipCfgTimerTrying {
        type int32 {
          range "100..1000";
        }
        units "milliseconds";
        description
         "This object specifies the time a user agent will wait to 
          receive a provisional response to a INVITE before resending 
          the INVITE.";
        smiv2:max-access "read-write";
        smiv2:oid "1.3.6.1.4.1.9.9.152.1.1.2.1";
      }

      leaf cSipCfgTimerExpires {
        type int32 {
          range "60000..300000";
        }
        units "milliseconds";
        description
         "This object specifies the time a user agent will wait to 
          receive a final response to a INVITE before cancelling the 
          transaction.";
        smiv2:max-access "read-write";
        smiv2:oid "1.3.6.1.4.1.9.9.152.1.1.2.2";
      }

      leaf cSipCfgTimerConnect {
        type int32 {
          range "100..1000";
        }
        units "milliseconds";
        description
         "This object specifies the time a user agent will wait to 
          receive an ACK confirmation a session is established.";
        smiv2:max-access "read-write";
        smiv2:oid "1.3.6.1.4.1.9.9.152.1.1.2.3";
      }

      leaf cSipCfgTimerDisconnect {
        type int32 {
          range "100..1000";
        }
        units "milliseconds";
        description
         "This object specifies the time a user agent will wait to 
          receive an BYE confirmation a session is disconnected.";
        smiv2:max-access "read-write";
        smiv2:oid "1.3.6.1.4.1.9.9.152.1.1.2.4";
      }

      leaf cSipCfgTimerPrack {
        type int32 {
          range "100..1000";
        }
        units "milliseconds";
        description
         "This object specifies the time a user agent will wait for 
          a final response before retransmitting the PRACK (PRovisional
          ACKnowledgment).";
        smiv2:max-access "read-write";
        smiv2:oid "1.3.6.1.4.1.9.9.152.1.1.2.5";
      }

      leaf cSipCfgTimerComet {
        type int32 {
          range "100..1000";
        }
        units "milliseconds";
        description
         "This object specifies the time a user agent will wait 
          for a final response before retransmitting the COMET 
          (COndition MET).";
        smiv2:max-access "read-write";
        smiv2:oid "1.3.6.1.4.1.9.9.152.1.1.2.6";
      }

      leaf cSipCfgTimerReliableRsp {
        type int32 {
          range "100..1000";
        }
        units "milliseconds";
        description
         "This object specifies the amount of time to wait for a
          PRACK before retransmitting the reliable 1xx response.";
        smiv2:max-access "read-write";
        smiv2:oid "1.3.6.1.4.1.9.9.152.1.1.2.7";
      }

      leaf cSipCfgTimerNotify {
        type int32 {
          range "100..1000";
        }
        units "milliseconds";
        description
         "This object specifies the amount of time to wait for a
          final response before retransmitting the Notify.";
        smiv2:max-access "read-write";
        smiv2:oid "1.3.6.1.4.1.9.9.152.1.1.2.8";
      }

      leaf cSipCfgTimerRefer {
        type int32 {
          range "100..1000";
        }
        units "milliseconds";
        description
         "This object specifies the amount of time to wait for a
          final response before retransmitting the Refer.";
        smiv2:max-access "read-write";
        smiv2:oid "1.3.6.1.4.1.9.9.152.1.1.2.9";
      }

      leaf cSipCfgTimerSessionTimer {
        type int32 {
          range "60..86400";
        }
        units "seconds";
        description
         "This object specifies the value of the Min-SE 
          header for INVITE messages originated by this 
          user agent and the minimum value of the 
          Session-Expires headers for INVITE messages 
          received by this user agent.
          
          Any Session-Expires headers received with a 
          value below this object's value will be rejected
          with a 422 client error response message.
          
          Setting this object to a value less than 600 is
          valid, but the possibly of excessive re-INVITES 
          and the impact of those messages should be fully 
          understood and considered an acceptable risk.";
        smiv2:defval "1800";
        smiv2:max-access "read-write";
        smiv2:oid "1.3.6.1.4.1.9.9.152.1.1.2.10";
      }

      leaf cSipCfgTimerHold {
        type int32 {
          range "0|15..2880";
        }
        units "minutes";
        description
         "This object specifies the amount of time to wait before 
          disconnecting a call already on hold. A value of 0 specifies
          that this functionality is disabled.";
        smiv2:defval "2880";
        smiv2:max-access "read-write";
        smiv2:oid "1.3.6.1.4.1.9.9.152.1.1.2.11";
      }

      leaf cSipCfgTimerInfo {
        type int32 {
          range "100..1000";
        }
        units "milliseconds";
        description
         "This object specifies the amount of time to wait for a
          200ok response before retransmitting the Info.";
        smiv2:defval "500";
        smiv2:max-access "read-write";
        smiv2:oid "1.3.6.1.4.1.9.9.152.1.1.2.12";
      }

      leaf cSipCfgTimerConnectionAging {
        type int32 {
          range "5..30";
        }
        units "minutes";
        description
         "This object specifies the amount of time to wait before 
          aging out a TCP/UDP connection.";
        smiv2:defval "5";
        smiv2:max-access "read-write";
        smiv2:oid "1.3.6.1.4.1.9.9.152.1.1.2.13";
      }

      leaf cSipCfgTimerBufferInvite {
        type int32 {
          range "0|50..5000";
        }
        units "milliseconds";
        description
         "This object specifies the amount of time to buffer the INVITE 
          while waiting for display name info in the Facility.
          
          A value of 0 means that the INVITE wouldn't be buffered
          waiting for the display name info in the Facility.";
        smiv2:defval "0";
        smiv2:max-access "read-write";
        smiv2:oid "1.3.6.1.4.1.9.9.152.1.1.2.14";
      }
    }

    container cSipCfgRetry {
      smiv2:oid "1.3.6.1.4.1.9.9.152.1.1.3";

      leaf cSipCfgRetryInvite {
        type int32 {
          range "1..10";
        }
        description
         "This object specifies the number of times a user agent 
          will retry sending a INVITE request.";
        smiv2:max-access "read-write";
        smiv2:oid "1.3.6.1.4.1.9.9.152.1.1.3.1";
      }

      leaf cSipCfgRetryBye {
        type int32 {
          range "1..10";
        }
        description
         "This object specifies the number of times a user agent 
          will retry sending a BYE request.";
        smiv2:max-access "read-write";
        smiv2:oid "1.3.6.1.4.1.9.9.152.1.1.3.2";
      }

      leaf cSipCfgRetryCancel {
        type int32 {
          range "1..10";
        }
        description
         "This object specifies the number of times a user agent 
          will retry sending a CANCEL request.";
        smiv2:max-access "read-write";
        smiv2:oid "1.3.6.1.4.1.9.9.152.1.1.3.3";
      }

      leaf cSipCfgRetryRegister {
        type int32 {
          range "1..10";
        }
        description
         "This object specifies the number of times a user agent 
          will retry sending a REGISTER request.";
        smiv2:max-access "read-write";
        smiv2:oid "1.3.6.1.4.1.9.9.152.1.1.3.4";
      }

      leaf cSipCfgRetryResponse {
        type int32 {
          range "1..10";
        }
        description
         "This object specifies the number of times a user agent 
          will retry sending a Response and expecting a ACK.";
        smiv2:max-access "read-write";
        smiv2:oid "1.3.6.1.4.1.9.9.152.1.1.3.5";
      }

      leaf cSipCfgRetryPrack {
        type int32 {
          range "1..10";
        }
        description
         "This object specifies the number of times a user agent 
          will retry sending a PRACK (PRovisional ACKnowledgement).";
        smiv2:max-access "read-write";
        smiv2:oid "1.3.6.1.4.1.9.9.152.1.1.3.6";
      }

      leaf cSipCfgRetryComet {
        type int32 {
          range "1..10";
        }
        description
         "This object specifies the number of times a user agent 
          will retry sending a COMET (COndition MET).";
        smiv2:max-access "read-write";
        smiv2:oid "1.3.6.1.4.1.9.9.152.1.1.3.7";
      }

      leaf cSipCfgRetryReliableRsp {
        type int32 {
          range "1..10";
        }
        description
         "This object specifies the number of times a user agent 
          will retry sending a reliable response.";
        smiv2:max-access "read-write";
        smiv2:oid "1.3.6.1.4.1.9.9.152.1.1.3.8";
      }

      leaf cSipCfgRetryNotify {
        type int32 {
          range "1..10";
        }
        description
         "This object specifies the number of times a user agent 
          will retry sending a Notify request.";
        smiv2:max-access "read-write";
        smiv2:oid "1.3.6.1.4.1.9.9.152.1.1.3.9";
      }

      leaf cSipCfgRetryRefer {
        type int32 {
          range "1..10";
        }
        description
         "This object specifies the number of times a user agent 
          will retry sending a Refer request.";
        smiv2:max-access "read-write";
        smiv2:oid "1.3.6.1.4.1.9.9.152.1.1.3.10";
      }

      leaf cSipCfgRetryInfo {
        type int32 {
          range "1..10";
        }
        description
         "This object specifies the number of times a user agent
          will retry sending a Info request.";
        smiv2:defval "6";
        smiv2:max-access "read-write";
        smiv2:oid "1.3.6.1.4.1.9.9.152.1.1.3.11";
      }

      leaf cSipCfgRetrySubscribe {
        type int32 {
          range "1..10";
        }
        description
         "This object specifies the number of times a user agent
          will retry sending a Subscribe request.";
        smiv2:defval "6";
        smiv2:max-access "read-write";
        smiv2:oid "1.3.6.1.4.1.9.9.152.1.1.3.12";
      }
    }

    container cSipCfgPeer {
      smiv2:oid "1.3.6.1.4.1.9.9.152.1.1.4";

      leaf cSipCfgOutSessionTransport {
        type enumeration {
          enum "udp" {
            value "1";
          }
          enum "tcp" {
            value "2";
          }
        }
        description
         "This object specifies the session transport 
          protocol that will be used for outbound SIP 
          messages.  This configuration is applicable
          to all dial-peers in the system having 
          cSipCfgPeerOutSessionTransport set to 'system'.";
        smiv2:defval "udp";
        smiv2:max-access "read-write";
        smiv2:oid "1.3.6.1.4.1.9.9.152.1.1.4.2";
      }

      leaf cSipCfgReliable1xxRspStr {
        type snmp-framework:SnmpAdminString;
        description
         "This object specifies the string that will be 
          placed in either the Supported or Require SIP 
          header, as specified by cSipCfgReliable1xxRspHdr.";
        smiv2:defval "100rel";
        smiv2:max-access "read-write";
        smiv2:oid "1.3.6.1.4.1.9.9.152.1.1.4.3";
      }

      leaf cSipCfgReliable1xxRspHdr {
        type enumeration {
          enum "supported" {
            value "1";
          }
          enum "require" {
            value "2";
          }
          enum "disabled" {
            value "3";
          }
        }
        description
         "This object specifies behavior with respect to
          Supported or Require headers in SIP messages sent
          and received via this dial-peer.
          
          If the originating gateway is configured for 'require',
          the Require header is added to the outgoing INVITEs
          with the value of cSipCfgReliable1xxStr.  This
          requires the use of reliable provisional responses by
          the terminating gateway.  Sessions will be torn down
          if this use cannot be supported by that gateway.
          
          If the originating gateway is configured for 'supported',
          the Supported header is added to the outgoing INVITEs
          with the value of cSipCfgReliable1xxStr.  This 
          requires that an attempt to use reliable provisional
          responses be made, but sessions can continue without them.
          
          If the originating gateway is configured for 'disabled',
          the value of cSipCfgReliable1xxStr will NOT be added to
          either the Require or Supported headers of outgoing INVITEs.";
        smiv2:defval "supported";
        smiv2:max-access "read-write";
        smiv2:oid "1.3.6.1.4.1.9.9.152.1.1.4.4";
      }

      leaf cSipCfgUrlType {
        type enumeration {
          enum "sip" {
            value "1";
          }
          enum "tel" {
            value "2";
          }
        }
        description
         "This object specifies the URL type sent in outbound
          INVITES generated by this device.";
        smiv2:defval "sip";
        smiv2:max-access "read-write";
        smiv2:oid "1.3.6.1.4.1.9.9.152.1.1.4.5";
      }
    }

    container cSipCfgAaa {
      smiv2:oid "1.3.6.1.4.1.9.9.152.1.1.6";

      leaf cSipCfgAaaUsername {
        type enumeration {
          enum "callingNumber" {
            value "1";
          }
          enum "proxyAuth" {
            value "2";
          }
        }
        description
         "This object specifies the source of the information used to
          populate the username attribute of AAA billing records.";
        smiv2:defval "callingNumber";
        smiv2:max-access "read-write";
        smiv2:oid "1.3.6.1.4.1.9.9.152.1.1.6.1";
      }
    }

    container cSipCfgVoiceServiceVoip {
      smiv2:oid "1.3.6.1.4.1.9.9.152.1.1.7";

      leaf cSipCfgHeaderPassingEnabled {
        type boolean;
        description
         "This object specifies if support for passing
          SIP headers from Invite, Subscribe, Notify Request to the
          application is enabled.
          
          If 'true', the headers received in a message will be passed
          to the application.
          
          If 'false', the headers received in a message will not be
          passed to the application.";
        smiv2:defval "false";
        smiv2:max-access "read-write";
        smiv2:oid "1.3.6.1.4.1.9.9.152.1.1.7.1";
      }

      leaf cSipCfgMaxSubscriptionAccept {
        type uint32 {
          range "0..4294967295";
        }
        description
         "This object specifies the maximum number of concurrent SIP
          subscriptions a SIP Gateway can accept.";
        smiv2:max-access "read-write";
        smiv2:oid "1.3.6.1.4.1.9.9.152.1.1.7.2";
      }

      leaf cSipCfgMaxSubscriptionOriginate {
        type uint32 {
          range "0..4294967295";
        }
        description
         "This object specifies the maximum number of concurrent SIP
          subscriptions that a SIP Gateway can originate. Default is Max
          Dialpeers on platform. Maximum is 2*Max Dialpeers on
          Platform.";
        smiv2:max-access "read-write";
        smiv2:oid "1.3.6.1.4.1.9.9.152.1.1.7.3";
      }

      leaf cSipCfgSwitchTransportEnabled {
        type boolean;
        description
         "This object specifies if the functionality of switching
          between transports from udp to tcp if the message size of a
          Request is greater than 1300 bytes is enabled or not.
          
          This configuration is at the global level, and will only be 
          considered if there exists no voip dial-peer.";
        smiv2:defval "false";
        smiv2:max-access "read-write";
        smiv2:oid "1.3.6.1.4.1.9.9.152.1.1.7.4";
      }
    }

    container cSipStatsInfo {
      smiv2:oid "1.3.6.1.4.1.9.9.152.1.2.1";

      leaf cSipStatsInfoTryingIns {
        type yang:counter32;
        description
         "This object reflects the total number of Trying
          (100) responses received by the user agent since system startup.  
          Trying responses indicate that some unspecified
          action is being taken on behalf of this call, but
          the user has not yet been located.  Inbound Trying
          responses indicate that outbound INVITE request 
          sent out by this system have been received and
          are processed.";
        reference
         "RFC 2543, Sections 5.1.1 & 7.1.1";
        smiv2:max-access "read-only";
        smiv2:oid "1.3.6.1.4.1.9.9.152.1.2.1.1";
      }

      leaf cSipStatsInfoTryingOuts {
        type yang:counter32;
        description
         "This object reflects the total number of Trying
          (100) responses sent by the user agent since system startup.
          Trying responses indicate that some unspecified
          action is being taken on behalf of this call, but
          the user has not yet been located.  Outbound Trying
          responses indicate this system is successfully 
          receiving INVITE requests and processing them on 
          behalf of the system initiating the INVITE.";
        reference
         "RFC 2543, Sections 5.1.1 & 7.1.1";
        smiv2:max-access "read-only";
        smiv2:oid "1.3.6.1.4.1.9.9.152.1.2.1.2";
      }

      leaf cSipStatsInfoRingingIns {
        type yang:counter32;
        description
         "This object reflects the total number of Ringing
          (180) responses received by the user agent since system startup.
          A inbound Ringing response indicates that the UAS
          processing a INVITE initiated by this system has 
          found a possible location where the desired end user 
          has registered recently and is trying to alert the user.";
        reference
         "RFC 2543, Sections 5.1.1 & 7.1.2";
        smiv2:max-access "read-only";
        smiv2:oid "1.3.6.1.4.1.9.9.152.1.2.1.3";
      }

      leaf cSipStatsInfoRingingOuts {
        type yang:counter32;
        description
         "This object reflects the total number of Ringing
          (180) responses sent by the user agent since system startup.
          A outbound Ringing response indicates that this
          system has processed an INVITE for a particular
          end user and found a possible location where that
          user has registered recently.  The system is trying
          to alert the end user and is conveying that status
          to the system that originated the INVITE.";
        reference
         "RFC 2543, Sections 5.1.1 & 7.1.2";
        smiv2:max-access "read-only";
        smiv2:oid "1.3.6.1.4.1.9.9.152.1.2.1.4";
      }

      leaf cSipStatsInfoForwardedIns {
        type yang:counter32;
        description
         "This object reflects the total number of Call Is Being
          Forwarded (181) responses received by the user agent since system startup.
          A proxy server may use a Forwarded status code to
          indicate that the call is being forwarded to a different
          set of destinations.  Inbound Forwarded responses indicate 
          to this system that forwarding actions are taking place 
          with regard to calls initiated by this system.";
        reference
         "RFC 2543, Sections 5.1.1 & 7.1.3";
        smiv2:max-access "read-only";
        smiv2:oid "1.3.6.1.4.1.9.9.152.1.2.1.5";
      }

      leaf cSipStatsInfoForwardedOuts {
        type yang:counter32;
        description
         "This object reflects the total number of Call Is Being
          Forwarded (181) responses sent by the user agent since system startup.
          A proxy server may use a Forwarded status code to
          indicate that the call is being forwarded to a different
          set of destinations.  Outbound Forwarded responses
          indicate this system is taking some forwarding action
          for calls and conveying that status to the system that
          initiated the calls.";
        reference
         "RFC 2543, Sections 5.1.1 & 7.1.3";
        smiv2:max-access "read-only";
        smiv2:oid "1.3.6.1.4.1.9.9.152.1.2.1.6";
      }

      leaf cSipStatsInfoQueuedIns {
        type yang:counter32;
        description
         "This object reflects the total number of Queued
          (182) responses received by the user agent since system startup.
          Inbound Queued responses indicate that the users
          this system is attempting to call are temporarily
          unavailable but the SIP agents operating on behalf
          of those users wish to queue the calls rather than
          reject them.  When the called parties become available,
          this system can expect to receive the appropriate
          final status response.  The Reason-Phrase from the
          Queued response messages Status-Line may give further
          details about the status of the call.  Multiple 
          Queued responses to update this system about the status
          of the queued call my be received.";
        reference
         "RFC 2543, Sections 5.1.1 & 7.1.4";
        smiv2:max-access "read-only";
        smiv2:oid "1.3.6.1.4.1.9.9.152.1.2.1.7";
      }

      leaf cSipStatsInfoQueuedOuts {
        type yang:counter32;
        description
         "This object reflects the total number of Queued
          (182) responses sent by the user agent since system startup.
          Outbound Queued responses indicate this system
          has determined that the called party is temporarily
          unavailable but the call is not rejected.  Rather 
          the call is queued until the called party becomes
          available.  Queued responses messages are sent to
          the system originating the call request to convey
          the current status of a queued call.";
        reference
         "RFC 2543, Sections 5.1.1 & 7.1.4";
        smiv2:max-access "read-only";
        smiv2:oid "1.3.6.1.4.1.9.9.152.1.2.1.8";
      }

      leaf cSipStatsInfoSessionProgIns {
        type yang:counter32;
        description
         "This object reflects the total number of Session
          Progress (183) responses received by the user agent since system startup.";
        smiv2:max-access "read-only";
        smiv2:oid "1.3.6.1.4.1.9.9.152.1.2.1.9";
      }

      leaf cSipStatsInfoSessionProgOuts {
        type yang:counter32;
        description
         "This object reflects the total number of Session
          Progress (183) responses sent by the user agent since system startup.";
        smiv2:max-access "read-only";
        smiv2:oid "1.3.6.1.4.1.9.9.152.1.2.1.10";
      }
    }

    container cSipStatsSuccess {
      smiv2:oid "1.3.6.1.4.1.9.9.152.1.2.2";

      leaf cSipStatsSuccessOkIns {
        type yang:counter32;
        status deprecated;
        description
         "This object reflects the total number of Ok
          (200) responses received by the user agent since system startup.
          The meaning of inbound Ok responses depends
          on the method used in the associated request.
          
          BYE      : The Ok response means the call has 
                     been terminated.
          
          CANCEL   : The Ok response means the search for 
                     the end user has been cancelled.
          
          INVITE   : The Ok response means the called party 
                     has agreed to participate in the call.
          
          OPTIONS  : The Ok response means the called party 
                     has agreed to share its capabilities.
          
          REGISTER : The Ok response means the registration
                     has succeeded.";
        reference
         "RFC 2543, Sections 5.1.1 & 7.2.1";
        smiv2:max-access "read-only";
        smiv2:oid "1.3.6.1.4.1.9.9.152.1.2.2.1";
      }

      leaf cSipStatsSuccessOkOuts {
        type yang:counter32;
        status deprecated;
        description
         "This object reflects the total number of Ok
          (200) responses sent by the user agent since system startup.
          The meaning of outbound Ok responses depends
          on the method used in the associated request.
          
          BYE      : The Ok response means the call has 
                     been terminated.
          
          CANCEL   : The Ok response means the search for 
                     the end user has been cancelled.
          
          INVITE   : The Ok response means the called party 
                     has agreed to participate in the call.
          
          OPTIONS  : The Ok response means the called party 
                     has agreed to share its capabilities.
          
          REGISTER : The Ok response means the registration
                     has succeeded.";
        reference
         "RFC 2543, Sections 5.1.1 & 7.2.1";
        smiv2:max-access "read-only";
        smiv2:oid "1.3.6.1.4.1.9.9.152.1.2.2.2";
      }

      leaf cSipStatsSuccessAcceptedIns {
        type yang:counter32;
        description
         "This object reflects the total number of Accepted
          (202) responses received by the user agent since system startup.
          The meaning of outbound 202 Ok responses depends
          on the method used in the associated request.";
        reference
         "draft-ietf-sip-cc-transfer-04.txt";
        smiv2:max-access "read-only";
        smiv2:oid "1.3.6.1.4.1.9.9.152.1.2.2.3";
      }

      leaf cSipStatsSuccessAcceptedOuts {
        type yang:counter32;
        description
         "This object reflects the total number of Accepted
          (202) responses sent by the user agent since system startup.
          The meaning of outbound 202 Ok responses depends
          on the method used in the associated request.";
        reference
         "draft-ietf-sip-cc-transfer-04.txt";
        smiv2:max-access "read-only";
        smiv2:oid "1.3.6.1.4.1.9.9.152.1.2.2.4";
      }
    }

    container cSipStatsRedirect {
      smiv2:oid "1.3.6.1.4.1.9.9.152.1.2.3";

      leaf cSipStatsRedirMultipleChoices {
        type yang:counter32;
        description
         "This object reflects the total number of Multiple
          Choices (300) responses received by the user agent since system startup.
          Multiple Choices responses indicate that the called
          party can be reached at several different locations
          and the server cannot or prefers not to proxy the request.";
        reference
         "RFC 2543, Section 5.1.1 & 7.3.1";
        smiv2:max-access "read-only";
        smiv2:oid "1.3.6.1.4.1.9.9.152.1.2.3.1";
      }

      leaf cSipStatsRedirMovedPerms {
        type yang:counter32;
        description
         "This object reflects the total number of Moved 
          Permanently (301) responses received by the user agent since system startup.
          Moved Permanently responses indicate that the called party 
          can no longer be found at the address offered in the request 
          and the requesting UAC should retry at the new address given 
          by the Contact header field of the response.";
        reference
         "RFC 2543, Sections 5.1.1 & 7.3.2";
        smiv2:max-access "read-only";
        smiv2:oid "1.3.6.1.4.1.9.9.152.1.2.3.2";
      }

      leaf cSipStatsRedirMovedTemps {
        type yang:counter32;
        status deprecated;
        description
         "This object reflects the total number of Moved 
          Temporarily (302) responses received by the user agent since system startup.
          Moved Temporarily responses indicate the UAC should
          retry the request directed at the new address(es)
          given by the Contact header field of the response.
          The duration of this redirection can be indicated
          through the Expires header.  If no explicit expiration
          time is given, the new address(es) are only valid
          for this call.";
        reference
         "RFC 2543, Sections 5.1.1 & 7.3.3";
        smiv2:max-access "read-only";
        smiv2:oid "1.3.6.1.4.1.9.9.152.1.2.3.3";
      }

      leaf cSipStatsRedirSeeOthers {
        type yang:counter32;
        status obsolete;
        description
         "This object reflects the total number of See Other 
          (303) responses received by the user agent since system startup.";
        reference
         "RFC 2543, Sections 5.1.1";
        smiv2:max-access "read-only";
        smiv2:oid "1.3.6.1.4.1.9.9.152.1.2.3.4";
      }

      leaf cSipStatsRedirUseProxys {
        type yang:counter32;
        description
         "This object reflects the total number of Use Proxy 
          (305) responses received by the user agent since system startup.
          See Other responses indicate that requested resources
          must be accessed through the proxy given by the 
          Contact header field of the response.  The recipient
          of this response is expected to repeat this single
          request via the proxy.";
        reference
         "RFC 2543, Sections 5.1.1 & 7.3.4";
        smiv2:max-access "read-only";
        smiv2:oid "1.3.6.1.4.1.9.9.152.1.2.3.5";
      }

      leaf cSipStatsRedirAltServices {
        type yang:counter32;
        description
         "This object reflects the total number of Alternative
          Service (380) responses received by the user agent since system startup.
          Alternative Service responses indicate that the call
          was not successful, but alternative services are
          possible.  Those alternative services are described
          in the message body of the response.";
        reference
         "RFC 2543, Sections 5.1.1 & 7.3.5";
        smiv2:max-access "read-only";
        smiv2:oid "1.3.6.1.4.1.9.9.152.1.2.3.6";
      }

      leaf cSipStatsRedirMovedTempsIns {
        type yang:counter32;
        description
         "This object reflects the total number of Moved
          Temporarily (302) responses received by the user agent since
          system startup. 
          Moved Temporarily responses indicate the UAC should
          retry the request directed at the new address(es) 
          given by the Contact header field of the response.
          The duration of this redirection can be indicated
          through the Expires header.  If no explicit expiration
          time is given, the new address(es) are only valid
          for this call.";
        reference
         "RFC 3261 Section 21.3.3";
        smiv2:max-access "read-only";
        smiv2:oid "1.3.6.1.4.1.9.9.152.1.2.3.7";
      }

      leaf cSipStatsRedirMovedTempsOuts {
        type yang:counter32;
        description
         "This object reflects the total number of Moved
          Temporarily (302) responses sent by the user agent since
          system startup.";
        reference
         "RFC 3261, Section 21.3.3";
        smiv2:max-access "read-only";
        smiv2:oid "1.3.6.1.4.1.9.9.152.1.2.3.8";
      }
    }

    container cSipStatsErrClient {
      smiv2:oid "1.3.6.1.4.1.9.9.152.1.2.4";

      leaf cSipStatsClientBadRequestIns {
        type yang:counter32;
        description
         "This object reflects the total number of Bad Request (400) 
          responses received by the user agent since system startup.
          Inbound Bad Request responses indicate that requests issued 
          by this system could not be understood due to malformed 
          syntax.";
        reference
         "RFC 2543, Sections 5.1.1 & 7.4.1";
        smiv2:max-access "read-only";
        smiv2:oid "1.3.6.1.4.1.9.9.152.1.2.4.1";
      }

      leaf cSipStatsClientBadRequestOuts {
        type yang:counter32;
        description
         "This object reflects the total number of Bad Request (400) 
          responses sent by the user agent since system startup.
          Outbound Bad Request responses indicate that requests 
          received by this system could not be understood due to 
          malformed syntax.";
        reference
         "RFC 2543, Sections 5.1.1 & 7.4.1";
        smiv2:max-access "read-only";
        smiv2:oid "1.3.6.1.4.1.9.9.152.1.2.4.2";
      }

      leaf cSipStatsClientUnauthorizedIns {
        type yang:counter32;
        description
         "This object reflects the total number of Unauthorized (401) 
          responses received by the user agent since system startup.  
          Inbound Unauthorized responses indicate that requests issued 
          by this system require user authentication.";
        reference
         "RFC 2543, Sections 5.1.1 & 7.4.2";
        smiv2:max-access "read-only";
        smiv2:oid "1.3.6.1.4.1.9.9.152.1.2.4.3";
      }

      leaf cSipStatsClientUnauthorizedOuts {
        type yang:counter32;
        description
         "This object reflects the total number of Unauthorized (401) 
          responses sent by the user agent since system startup.
          Outbound Unauthorized responses indicate that requests 
          received by this system require user authentication.";
        reference
         "RFC 2543, Sections 5.1.1 & 7.4.2";
        smiv2:max-access "read-only";
        smiv2:oid "1.3.6.1.4.1.9.9.152.1.2.4.4";
      }

      leaf cSipStatsClientPaymentReqdIns {
        type yang:counter32;
        description
         "This object reflects the total number of Payment Required 
          (402) responses received by the user agent since system startup.";
        reference
         "RFC 2543, Sections 5.1.1 & 7.4.3";
        smiv2:max-access "read-only";
        smiv2:oid "1.3.6.1.4.1.9.9.152.1.2.4.5";
      }

      leaf cSipStatsClientPaymentReqdOuts {
        type yang:counter32;
        description
         "This object reflects the total number of Payment Required 
          (402) responses sent by the user agent since system startup.";
        reference
         "RFC 2543, Sections 5.1.1 & 7.4.3";
        smiv2:max-access "read-only";
        smiv2:oid "1.3.6.1.4.1.9.9.152.1.2.4.6";
      }

      leaf cSipStatsClientForbiddenIns {
        type yang:counter32;
        description
         "This object reflects the total number of Forbidden (403) 
          responses received by the user agent since system startup.
          Inbound Forbidden responses indicate that requests issued
          by this system are understood by the server but the server
          refuses to fulfill the request.  Authorization will not help
          and the requests should not be repeated.";
        reference
         "RFC 2543, Sections 5.1.1 & 7.4.4";
        smiv2:max-access "read-only";
        smiv2:oid "1.3.6.1.4.1.9.9.152.1.2.4.7";
      }

      leaf cSipStatsClientForbiddenOuts {
        type yang:counter32;
        description
         "This object reflects the total number of Forbidden (403) 
          responses sent by the user agent since system startup.
          Outbound Forbidden responses indicate that requests received
          by this system are understood but this system is refusing to
          fulfill the requests.";
        reference
         "RFC 2543, Sections 5.1.1 & 7.4.4";
        smiv2:max-access "read-only";
        smiv2:oid "1.3.6.1.4.1.9.9.152.1.2.4.8";
      }

      leaf cSipStatsClientNotFoundIns {
        type yang:counter32;
        description
         "This object reflects the total number of Not Found (404) 
          responses received by the user agent since system startup.
          Inbound Not Found responses indicate that the called party 
          does not exist at the domain specified in the Request-URI 
          or the domain is not handled by the recipient of the request.";
        reference
         "RFC 2543, Sections 5.1.1 & 7.4.5";
        smiv2:max-access "read-only";
        smiv2:oid "1.3.6.1.4.1.9.9.152.1.2.4.9";
      }

      leaf cSipStatsClientNotFoundOuts {
        type yang:counter32;
        description
         "This object reflects the total number of Not Found (404) 
          responses sent by the user agent since system startup.
          Outbound Not Found responses indicate that this system
          knows that the called party does not exist at the domain
          specified in the Request-URI or the domain is not handled
          by this system.";
        reference
         "RFC 2543, Sections 5.1.1 & 7.4.5";
        smiv2:max-access "read-only";
        smiv2:oid "1.3.6.1.4.1.9.9.152.1.2.4.10";
      }

      leaf cSipStatsClientMethNotAllowedIns {
        type yang:counter32;
        description
         "This object reflects the total number of Method Not Allowed 
          (405) received responses by the user agent.
          Inbound Method Not Allowed responses indicate that requests 
          issued by this system have specified a SIP method in the 
          Request-Line that is not allowed for the address identified 
          by the Request-URI.";
        reference
         "RFC 2543, Sections 5.1.1 & 7.4.6";
        smiv2:max-access "read-only";
        smiv2:oid "1.3.6.1.4.1.9.9.152.1.2.4.11";
      }

      leaf cSipStatsClientMethNotAllowedOuts {
        type yang:counter32;
        description
         "This object reflects the total number of Method Not Allowed 
          (405) received sent by the user agent since system startup.
          Outbound Method Not Allowed responses indicate that requests 
          received by this system have SIP methods specified in the 
          Request-Line that are not allowed for the address identified 
          by the Request-URI.";
        reference
         "RFC 2543, Sections 5.1.1 & 7.4.6";
        smiv2:max-access "read-only";
        smiv2:oid "1.3.6.1.4.1.9.9.152.1.2.4.12";
      }

      leaf cSipStatsClientNotAcceptableIns {
        type yang:counter32;
        description
         "This object reflects the total number of Not Acceptable 
          (406) responses received by the user agent since system startup.
          Inbound Not Acceptable responses indicate the resources 
          identified by requests issued by this system cannot generate 
          responses with content characteristics acceptable to this 
          system according to the accept headers sent in the requests.";
        reference
         "RFC 2543, Sections 5.1.1 & 7.4.7";
        smiv2:max-access "read-only";
        smiv2:oid "1.3.6.1.4.1.9.9.152.1.2.4.13";
      }

      leaf cSipStatsClientNotAcceptableOuts {
        type yang:counter32;
        description
         "This object reflects the total number of Not Acceptable (406) 
          responses sent by the user agent since system startup.
          Outbound Not Acceptable responses indicate that the resources
          identified by requests received by this system cannot generate
          responses with content characteristics acceptable to the 
          system sending the requests.";
        reference
         "RFC 2543, Sections 5.1.1 & 7.4.7";
        smiv2:max-access "read-only";
        smiv2:oid "1.3.6.1.4.1.9.9.152.1.2.4.14";
      }

      leaf cSipStatsClientProxyAuthReqdIns {
        type yang:counter32;
        description
         "This object reflects the total number of Proxy Authentication 
          Required (407) responses received by the user agent since system startup.
          Inbound Proxy Authentication Required responses indicate that 
          this system must authenticate itself with the proxy before 
          gaining access to the requested resource.";
        reference
         "RFC 2543, Sections 5.1.1 & 7.4.8";
        smiv2:max-access "read-only";
        smiv2:oid "1.3.6.1.4.1.9.9.152.1.2.4.15";
      }

      leaf cSipStatsClientProxyAuthReqdOuts {
        type yang:counter32;
        description
         "This object reflects the total number of Proxy Authentication 
          Required (407) responses sent by the user agent since system startup.
          Outbound Proxy Authentication Required responses indicate that
          the systems issuing requests being processed by this system 
          must authenticate themselves with this system before gaining 
          access to requested resources.";
        reference
         "RFC 2543, Sections 5.1.1 & 7.4.8";
        smiv2:max-access "read-only";
        smiv2:oid "1.3.6.1.4.1.9.9.152.1.2.4.16";
      }

      leaf cSipStatsClientReqTimeoutIns {
        type yang:counter32;
        description
         "This object reflects the total number of Request Timeout 
          (408) responses received by the user agent since system startup.
          Inbound Request Timeout responses indicate that requests 
          issued by this system are not being processed by the server 
          within the time indicated in the Expires header of the 
          request.";
        reference
         "RFC 2543, Sections 5.1.1 & 7.4.9";
        smiv2:max-access "read-only";
        smiv2:oid "1.3.6.1.4.1.9.9.152.1.2.4.17";
      }

      leaf cSipStatsClientReqTimeoutOuts {
        type yang:counter32;
        description
         "This object reflects the total number of Request Timeout 
          (408) responses sent by the user agent since system startup.
          Outbound Request Timeout responses indicate that this 
          system is not able to produce an appropriate response within 
          the time indicated in the Expires header of the request.";
        reference
         "RFC 2543, Sections 5.1.1 & 7.4.9";
        smiv2:max-access "read-only";
        smiv2:oid "1.3.6.1.4.1.9.9.152.1.2.4.18";
      }

      leaf cSipStatsClientConflictIns {
        type yang:counter32;
        description
         "This object reflects the total number of Conflict (409) 
          responses received by the user agent since system startup.
          Inbound Conflict responses indicate that requests issued
          by this system could not be completed due to a conflict
          with the current state of a requested resource.";
        reference
         "RFC 2543, Sections 5.1.1 & 7.4.10";
        smiv2:max-access "read-only";
        smiv2:oid "1.3.6.1.4.1.9.9.152.1.2.4.19";
      }

      leaf cSipStatsClientConflictOuts {
        type yang:counter32;
        description
         "This object reflects the total number of Conflict (409) 
          responses sent by the user agent since system startup.
          Outbound Conflict responses indicate that requests received
          by this system could not be completed due to a conflict
          with the current state of a requested resource.";
        reference
         "RFC 2543, Sections 5.1.1 & 7.4.10";
        smiv2:max-access "read-only";
        smiv2:oid "1.3.6.1.4.1.9.9.152.1.2.4.20";
      }

      leaf cSipStatsClientGoneIns {
        type yang:counter32;
        description
         "This object reflects the total number of Gone (410) 
          responses received by the user agent since system startup.
          Inbound Gone responses indicate that resources requested
          by this system are no longer available at the recipient server
          and no forwarding address is known.";
        reference
         "RFC 2543, Sections 5.1.1 & 7.4.11";
        smiv2:max-access "read-only";
        smiv2:oid "1.3.6.1.4.1.9.9.152.1.2.4.21";
      }

      leaf cSipStatsClientGoneOuts {
        type yang:counter32;
        description
         "This object reflects the total number of Gone (410) 
          responses sent by the user agent since system startup.
          Outbound Gone responses indicate that the requested
          resources are no longer available at this system and
          no forwarding address is known.";
        reference
         "RFC 2543, Sections 5.1.1 & 7.4.11";
        smiv2:max-access "read-only";
        smiv2:oid "1.3.6.1.4.1.9.9.152.1.2.4.22";
      }

      leaf cSipStatsClientLengthRequiredIns {
        type yang:counter32;
        status obsolete;
        description
         "This object reflects the total number of Length Required 
          (411) responses received by the user agent since system startup.
          Inbound Length Required responses indicate that requests 
          issued by this system are being refused by servers because 
          of no defined Content-Length header field.";
        reference
         "RFC 2543, Sections 5.1.1 & 7.4.12";
        smiv2:max-access "read-only";
        smiv2:oid "1.3.6.1.4.1.9.9.152.1.2.4.23";
      }

      leaf cSipStatsClientLengthRequiredOuts {
        type yang:counter32;
        status obsolete;
        description
         "This object reflects the total number of Length Required 
          (411) responses sent by the user agent since system startup.
          Outbound Length Required responses indicate that requests 
          received by this system are being refused because of no 
          defined Content-Length header field.";
        reference
         "RFC 2543, Sections 5.1.1 & 7.4.12";
        smiv2:max-access "read-only";
        smiv2:oid "1.3.6.1.4.1.9.9.152.1.2.4.24";
      }

      leaf cSipStatsClientReqEntTooLargeIns {
        type yang:counter32;
        description
         "This object reflects the total number of Request Entity Too 
          Large (413) responses received by the user agent since system startup.
          Inbound Request Entity Too Large responses indicate that 
          requests issued by this system are being refused because 
          the request is larger than the server is willing or able to 
          process.";
        reference
         "RFC 2543, Sections 5.1.1 & 7.4.13";
        smiv2:max-access "read-only";
        smiv2:oid "1.3.6.1.4.1.9.9.152.1.2.4.25";
      }

      leaf cSipStatsClientReqEntTooLargeOuts {
        type yang:counter32;
        description
         "This object reflects the total number of Request Entity Too 
          Large (413) responses sent by the user agent since system startup.
          Outbound Request Entity Too Large responses indicate that 
          requests received by this system are larger than this system 
          is willing or able to process.";
        reference
         "RFC 2543, Sections 5.1.1 & 7.4.13";
        smiv2:max-access "read-only";
        smiv2:oid "1.3.6.1.4.1.9.9.152.1.2.4.26";
      }

      leaf cSipStatsClientReqURITooLargeIns {
        type yang:counter32;
        description
         "This object reflects the total number of Request-URI Too 
          Large (414) responses received by the user agent since system startup.
          Inbound Request-URI Too Large responses indicate that 
          requests issued by this system are being refused because the 
          Request-URI is longer than the server is willing or able to 
          interpret.";
        reference
         "RFC 2543, Sections 5.1.1 & 7.4.14";
        smiv2:max-access "read-only";
        smiv2:oid "1.3.6.1.4.1.9.9.152.1.2.4.27";
      }

      leaf cSipStatsClientReqURITooLargeOuts {
        type yang:counter32;
        description
         "This object reflects the total number of Request-URI Too 
          Large (414) responses sent by the user agent since system startup.
          Outbound Request-URI Too Large responses indicate that 
          Request-URIs received by this system are longer than this 
          system is willing or able to interpret.";
        reference
         "RFC 2543, Sections 5.1.1 & 7.4.14";
        smiv2:max-access "read-only";
        smiv2:oid "1.3.6.1.4.1.9.9.152.1.2.4.28";
      }

      leaf cSipStatsClientNoSupMediaTypeIns {
        type yang:counter32;
        description
         "This object reflects the total number of Unsupported Media 
          Type (415) responses received by the user agent since system startup.
          Inbound Unsupported Media Type responses indicate that 
          requests issued by this system are being refused because the 
          message body of the request is in a format not supported by 
          the requested resource for the requested method.";
        reference
         "RFC 2543, Sections 5.1.1 & 7.4.15";
        smiv2:max-access "read-only";
        smiv2:oid "1.3.6.1.4.1.9.9.152.1.2.4.29";
      }

      leaf cSipStatsClientNoSupMediaTypeOuts {
        type yang:counter32;
        description
         "This object reflects the total number of Unsupported Media 
          Type (415) responses sent by the user agent since system startup.
          Outbound Unsupported Media Type responses indicate that the 
          body of requests received by this system are in a format not 
          supported by the requested resource for the requested method.";
        reference
         "RFC 2543, Sections 5.1.1 & 7.4.15";
        smiv2:max-access "read-only";
        smiv2:oid "1.3.6.1.4.1.9.9.152.1.2.4.30";
      }

      leaf cSipStatsClientBadExtensionIns {
        type yang:counter32;
        description
         "This object reflects the total number of Bad Extension (420) 
          responses received by the user agent since system startup.
          Inbound Bad Extension responses indicate that the recipient 
          did not understand the protocol extension specified in a 
          Require header field.";
        reference
         "RFC 2543, Sections 5.1.1 & 7.5.16";
        smiv2:max-access "read-only";
        smiv2:oid "1.3.6.1.4.1.9.9.152.1.2.4.31";
      }

      leaf cSipStatsClientBadExtensionOuts {
        type yang:counter32;
        description
         "This object reflects the total number of Bad Extension (420) 
          responses sent by the user agent since system startup.
          Outbound Bad Extension responses indicate that this system
          did not understand the protocol extension specified in a
          Require header field of requests.";
        reference
         "RFC 2543, Sections 5.1.1 & 7.4.16";
        smiv2:max-access "read-only";
        smiv2:oid "1.3.6.1.4.1.9.9.152.1.2.4.32";
      }

      leaf cSipStatsClientTempNotAvailIns {
        type yang:counter32;
        description
         "This object reflects the total number of Temporarily Not 
          Available (480) responses received by the user agent since system startup.
          Inbound Temporarily Not Available responses indicate that 
          the called party is currently unavailable.";
        reference
         "RFC 2543, Sections 5.1.1 & 7.4.17";
        smiv2:max-access "read-only";
        smiv2:oid "1.3.6.1.4.1.9.9.152.1.2.4.33";
      }

      leaf cSipStatsClientTempNotAvailOuts {
        type yang:counter32;
        description
         "This object reflects the total number of Temporarily Not 
          Available (480) responses sent by the user agent since system startup.
          Outbound Temporarily Not Available responses indicate that 
          the called party's end system was contacted successfully but 
          the called party is currently unavailable.";
        reference
         "RFC 2543, Sections 5.1.1 & 7.4.17";
        smiv2:max-access "read-only";
        smiv2:oid "1.3.6.1.4.1.9.9.152.1.2.4.34";
      }

      leaf cSipStatsClientCallLegNoExistIns {
        type yang:counter32;
        description
         "This object reflects the total number of Call Leg/Transaction 
          Does Not Exist (481) responses received by the user agent since system startup.
          Inbound Call Leg/Transaction Does Not Exist responses indicate
          that either BYE or CANCEL requests issued by this system were 
          received by a server and not matching call leg or transaction 
          existed.";
        reference
         "RFC 2543, Sections 5.1.1 & 7.4.18";
        smiv2:max-access "read-only";
        smiv2:oid "1.3.6.1.4.1.9.9.152.1.2.4.35";
      }

      leaf cSipStatsClientCallLegNoExistOuts {
        type yang:counter32;
        description
         "This object reflects the total number of Call Leg/Transaction 
          Does Not Exist (481) responses sent by the user agent since system startup.
          Outbound Call Leg/Transaction Does Not Exist responses 
          indicate that BYE or CANCEL requests have been received by 
          this system and not call leg or transaction matching that 
          request exists.";
        reference
         "RFC 2543, Sections 5.1.1 & 7.4.18";
        smiv2:max-access "read-only";
        smiv2:oid "1.3.6.1.4.1.9.9.152.1.2.4.36";
      }

      leaf cSipStatsClientLoopDetectedIns {
        type yang:counter32;
        description
         "This object reflects the total number of Loop Detected (482) 
          responses received by the user agent since system startup.
          Inbound Loop Detected responses indicate that requests issued
          by this system were received at servers and the server found 
          itself in the Via path more than once.";
        reference
         "RFC 2543, Sections 5.1.1 & 7.4.19";
        smiv2:max-access "read-only";
        smiv2:oid "1.3.6.1.4.1.9.9.152.1.2.4.37";
      }

      leaf cSipStatsClientLoopDetectedOuts {
        type yang:counter32;
        description
         "This object reflects the total number of Loop Detected (482) 
          responses sent by the user agent since system startup.
          Outbound Loop Detected responses indicate that requests 
          received by this system contain a Via path with this system 
          appearing more than once.";
        reference
         "RFC 2543, Sections 5.1.1 & 7.4.19";
        smiv2:max-access "read-only";
        smiv2:oid "1.3.6.1.4.1.9.9.152.1.2.4.38";
      }

      leaf cSipStatsClientTooManyHopsIns {
        type yang:counter32;
        description
         "This object reflects the total number of Too Many Hops (483) 
          responses received by the user agent since system startup.
          Inbound Too Many Hops responses indicate that requests issued
          by this system contain more Via entries (hops) than allowed by
          the Max-Forwards header field of the requests.";
        reference
         "RFC 2543, Sections 5.1.1 & 7.4.20";
        smiv2:max-access "read-only";
        smiv2:oid "1.3.6.1.4.1.9.9.152.1.2.4.39";
      }

      leaf cSipStatsClientTooManyHopsOuts {
        type yang:counter32;
        description
         "This object reflects the total number of Too Many Hops (483) 
          responses sent by the user agent since system startup.
          Outbound Too Many Hops responses indicate that requests
          received by this system contain more Via entries (hops) than
          are allowed by the Max-Forwards header field of the requests.";
        reference
         "RFC 2543, Sections 5.1.1 & 7.4.20";
        smiv2:max-access "read-only";
        smiv2:oid "1.3.6.1.4.1.9.9.152.1.2.4.40";
      }

      leaf cSipStatsClientAddrIncompleteIns {
        type yang:counter32;
        description
         "This object reflects the total number of Address Incomplete 
          (484) responses received by the user agent since system startup.
          Inbound Address Incomplete responses indicate that requests 
          issued by this system had To addresses or Request-URIs that 
          were incomplete.";
        reference
         "RFC 2543, Sections 5.1.1 & 7.4.21";
        smiv2:max-access "read-only";
        smiv2:oid "1.3.6.1.4.1.9.9.152.1.2.4.41";
      }

      leaf cSipStatsClientAddrIncompleteOuts {
        type yang:counter32;
        description
         "This object reflects the total number of Address Incomplete 
          (484) responses sent by the user agent since system startup.
          Outbound Address Incomplete responses indicate that requests 
          received by this system had To addresses or Request-URIs that 
          were incomplete.";
        reference
         "RFC 2543, Sections 5.1.1 & 7.4.21";
        smiv2:max-access "read-only";
        smiv2:oid "1.3.6.1.4.1.9.9.152.1.2.4.42";
      }

      leaf cSipStatsClientAmbiguousIns {
        type yang:counter32;
        description
         "This object reflects the total number of Ambiguous (485) 
          responses received by the user agent since system startup.
          Inbound Ambiguous responses indicate that requests issued
          by this system provided ambiguous address information.";
        reference
         "RFC 2543, Sections 5.1.1 & 7.4.22";
        smiv2:max-access "read-only";
        smiv2:oid "1.3.6.1.4.1.9.9.152.1.2.4.43";
      }

      leaf cSipStatsClientAmbiguousOuts {
        type yang:counter32;
        description
         "This object reflects the total number of Ambiguous (485) 
          responses sent by the user agent since system startup.
          Outbound Ambiguous responses indicate that requests received
          by this system contained ambiguous address information.";
        reference
         "RFC 2543, Sections 5.1.1 & 7.4.22";
        smiv2:max-access "read-only";
        smiv2:oid "1.3.6.1.4.1.9.9.152.1.2.4.44";
      }

      leaf cSipStatsClientBusyHereIns {
        type yang:counter32;
        description
         "This object reflects the total number of Busy Here (486) 
          responses received by the user agent since system startup.
          Inbound Busy Here responses indicate that the
          called party is currently not willing or not able to
          take additional calls.";
        reference
         "RFC 2543, Section 5.1.1 & 7.4.23";
        smiv2:max-access "read-only";
        smiv2:oid "1.3.6.1.4.1.9.9.152.1.2.4.45";
      }

      leaf cSipStatsClientBusyHereOuts {
        type yang:counter32;
        description
         "This object reflects the total number of Busy Here (486) 
          responses sent by the user agent since system startup.
          Outbound Busy Here responses indicate that the
          called party's end system was contacted successfully but the
          called party is currently not willing or able to take 
          additional calls.";
        reference
         "RFC 2543, Sections 5.1.1 & 7.4.23";
        smiv2:max-access "read-only";
        smiv2:oid "1.3.6.1.4.1.9.9.152.1.2.4.46";
      }

      leaf cSipStatsClientReqTermIns {
        type yang:counter32;
        description
         "This object reflects the total number of Request Terminated 
          (487) responses received by the user agent since system startup.
          Request Terminated responses are issued if the original 
          request was terminated via CANCEL or BYE.";
        reference
         "draft-ietf-sip-rfc2543bis-01.txt, Section 7.4.24.487";
        smiv2:max-access "read-only";
        smiv2:oid "1.3.6.1.4.1.9.9.152.1.2.4.47";
      }

      leaf cSipStatsClientReqTermOuts {
        type yang:counter32;
        description
         "This object reflects the total number of Request Terminated 
          (487) responses sent by the user agent since system startup.
          Request Terminated responses are issued if the original 
          request was terminated via CANCEL or BYE.";
        reference
         "draft-ietf-sip-rfc2543bis-01.txt, Section 7.4.24.487";
        smiv2:max-access "read-only";
        smiv2:oid "1.3.6.1.4.1.9.9.152.1.2.4.48";
      }

      leaf cSipStatsClientNoAcceptHereIns {
        type yang:counter32;
        description
         "This object reflects the total number of Not Acceptable Here
          (488) responses received by the user agent since system startup.
          The response has the same meaning as 606 (Not Acceptable), 
          but only applies to the specific entity addressed by the 
          Request-URI and the request may succeed elsewhere.";
        reference
         "draft-ietf-sip-rfc2543bis-01.txt, Section 7.4.24.488";
        smiv2:max-access "read-only";
        smiv2:oid "1.3.6.1.4.1.9.9.152.1.2.4.49";
      }

      leaf cSipStatsClientNoAcceptHereOuts {
        type yang:counter32;
        description
         "This object reflects the total number of Not Acceptable Here
          (488) responses sent by the user agent since system startup.
          The response has the same meaning as 606 (Not Acceptable), 
          but only applies to the specific entity addressed by the 
          Request-URI and the request may succeed elsewhere.";
        reference
         "draft-ietf-sip-rfc2543bis-01.txt, Section 7.4.24.488";
        smiv2:max-access "read-only";
        smiv2:oid "1.3.6.1.4.1.9.9.152.1.2.4.50";
      }

      leaf cSipStatsClientBadEventIns {
        type yang:counter32;
        description
         "This object reflects the total number of BadEvent (489) 
          responses received by the user agent since system startup.";
        smiv2:max-access "read-only";
        smiv2:oid "1.3.6.1.4.1.9.9.152.1.2.4.51";
      }

      leaf cSipStatsClientBadEventOuts {
        type yang:counter32;
        description
         "This object reflects the total number of BadEvent (489) 
          responses sent by the user agent since system startup.";
        smiv2:max-access "read-only";
        smiv2:oid "1.3.6.1.4.1.9.9.152.1.2.4.52";
      }

      leaf cSipStatsClientSTTooSmallIns {
        type yang:counter32;
        description
         "This object reflects the total number of SessionTimerTooSmall
          (422) responses received by the user agent since system 
          startup.";
        smiv2:max-access "read-only";
        smiv2:oid "1.3.6.1.4.1.9.9.152.1.2.4.53";
      }

      leaf cSipStatsClientSTTooSmallOuts {
        type yang:counter32;
        description
         "This object reflects the total number of SessionTimerTooSmall
          (422) responses sent by the user agent since system startup.";
        smiv2:max-access "read-only";
        smiv2:oid "1.3.6.1.4.1.9.9.152.1.2.4.54";
      }

      leaf cSipStatsClientReqPendingIns {
        type yang:counter32;
        description
         "This object reflects the total number of RequestPending
          (491) responses received by the user agent since system
          startup.";
        smiv2:max-access "read-only";
        smiv2:oid "1.3.6.1.4.1.9.9.152.1.2.4.55";
      }

      leaf cSipStatsClientReqPendingOuts {
        type yang:counter32;
        description
         "This object reflects the total number of RequestPending
          (491) responses sent by the user agent since system startup.";
        smiv2:max-access "read-only";
        smiv2:oid "1.3.6.1.4.1.9.9.152.1.2.4.56";
      }
    }

    container cSipStatsErrServer {
      smiv2:oid "1.3.6.1.4.1.9.9.152.1.2.5";

      leaf cSipStatsServerIntErrorIns {
        type yang:counter32;
        description
         "This object reflects the total number of Internal Server Error
          (500) responses received by the user agent since system startup.
          Inbound Internal Server Error responses indicate that servers 
          to which this system is sending requests have encountered 
          unexpected conditions that prevent them from fulfilling the 
          requests.";
        reference
         "RFC 2543, Sections 5.1.1 & 7.5.1";
        smiv2:max-access "read-only";
        smiv2:oid "1.3.6.1.4.1.9.9.152.1.2.5.1";
      }

      leaf cSipStatsServerIntErrorOuts {
        type yang:counter32;
        description
         "This object reflects the total number of Internal Server Error
          (500) responses sent by the user agent since system startup.
          Outbound Internal Server Error responses indicate that this 
          system has encountered unexpected conditions that prevent it 
          from fulfilling received requests.";
        reference
         "RFC 2543, Sections 5.1.1 & 7.5.1";
        smiv2:max-access "read-only";
        smiv2:oid "1.3.6.1.4.1.9.9.152.1.2.5.2";
      }

      leaf cSipStatsServerNotImplementedIns {
        type yang:counter32;
        description
         "This object reflects the total number of Not Implemented 
          (501) responses received by the user agent since system startup.
          Inbound Not Implemented responses indicate that servers to 
          which this system is sending requests do not support the 
          functionality required to fulfill the requests.";
        reference
         "RFC 2543, Sections 5.1.1 & 7.5.2";
        smiv2:max-access "read-only";
        smiv2:oid "1.3.6.1.4.1.9.9.152.1.2.5.3";
      }

      leaf cSipStatsServerNotImplementedOuts {
        type yang:counter32;
        description
         "This object reflects the total number of Not Implemented 
          (501) responses sent by the user agent since system startup.
          Outbound Not Implemented responses indicate that this system
          does not support the functionality required to fulfill the 
          requests.";
        reference
         "RFC 2543, Sections 5.1.1 & 7.5.2";
        smiv2:max-access "read-only";
        smiv2:oid "1.3.6.1.4.1.9.9.152.1.2.5.4";
      }

      leaf cSipStatsServerBadGatewayIns {
        type yang:counter32;
        description
         "This object reflects the total number of Bad Gateway (502) 
          responses received by the user agent since system startup.";
        reference
         "RFC 2543, Sections 5.1.1 & 7.5.3";
        smiv2:max-access "read-only";
        smiv2:oid "1.3.6.1.4.1.9.9.152.1.2.5.5";
      }

      leaf cSipStatsServerBadGatewayOuts {
        type yang:counter32;
        description
         "This object reflects the total number of Bad Gateway (502) 
          responses sent by the user agent since system startup.";
        reference
         "RFC 2543, Sections 5.1.1 & 7.5.3";
        smiv2:max-access "read-only";
        smiv2:oid "1.3.6.1.4.1.9.9.152.1.2.5.6";
      }

      leaf cSipStatsServerServiceUnavailIns {
        type yang:counter32;
        description
         "This object reflects the total number of Service Unavailable 
          (503) responses received by the user agent since system startup.
          Inbound Service Unavailable responses indicate that the server
          servicing this system's request is temporarily unavailable to
          handle the request.";
        reference
         "RFC 2543, Sections 5.1.1 & 7.5.4";
        smiv2:max-access "read-only";
        smiv2:oid "1.3.6.1.4.1.9.9.152.1.2.5.7";
      }

      leaf cSipStatsServerServiceUnavailOuts {
        type yang:counter32;
        description
         "This object reflects the total number of Service Unavailable 
          (503) responses sent by the user agent since system startup.
          Outbound Service Unavailable responses indicate that this
          system is temporarily unable to handle received requests.";
        reference
         "RFC 2543, Sections 5.1.1 & 7.5.4";
        smiv2:max-access "read-only";
        smiv2:oid "1.3.6.1.4.1.9.9.152.1.2.5.8";
      }

      leaf cSipStatsServerGatewayTimeoutIns {
        type yang:counter32;
        description
         "This object reflects the total number of Gateway Time-out 
          (504) responses received by the user agent since system startup.
          Inbound Gateway Time-out responses indicate that the server
          attempting to complete this system's request did not receive
          a timely response from yet another system it was accessing to
          complete the request.";
        reference
         "RFC 2543, Sections 5.1.1 & 7.5.5";
        smiv2:max-access "read-only";
        smiv2:oid "1.3.6.1.4.1.9.9.152.1.2.5.9";
      }

      leaf cSipStatsServerGatewayTimeoutOuts {
        type yang:counter32;
        description
         "This object reflects the total number of Gateway Time-out 
          (504) responses sent by the user agent since system startup.
          Outbound Gateway Time-out responses indicate that this system
          did not receive a timely response from the system it had
          accessed to assist in completing a received request.";
        reference
         "RFC 2543, Sections 5.1.1 & 7.5.5";
        smiv2:max-access "read-only";
        smiv2:oid "1.3.6.1.4.1.9.9.152.1.2.5.10";
      }

      leaf cSipStatsServerBadSipVersionIns {
        type yang:counter32;
        description
         "This object reflects the total number of SIP Version Not 
          Supported (505) responses received by the user agent since system startup.
          Inbound SIP Version Not Supported responses indicate that 
          the server does not support, or refuses to support, the SIP 
          protocol version that was used in the request message.";
        reference
         "RFC 2543, Sections 5.1.1 & 7.5.6";
        smiv2:max-access "read-only";
        smiv2:oid "1.3.6.1.4.1.9.9.152.1.2.5.11";
      }

      leaf cSipStatsServerBadSipVersionOuts {
        type yang:counter32;
        description
         "This object reflects the total number of SIP Version Not 
          Supported (505) responses sent by the user agent since system startup.
          Outbound SIP Version Not Supported responses indicate that 
          this system does not support, or refuses to support, the SIP 
          protocol version used in received requests.";
        reference
         "RFC 2543, Sections 5.1.1 & 7.5.6";
        smiv2:max-access "read-only";
        smiv2:oid "1.3.6.1.4.1.9.9.152.1.2.5.12";
      }

      leaf cSipStatsServerPrecondFailureIns {
        type yang:counter32;
        description
         "This object reflects the total number of Precondition 
          Failure (580) responses received by the user agent since system startup.
          This response is returned by a UAS if it is unable to
          perform the mandatory preconditions for the session.";
        reference
         "draft-manyfolks-sip-resource-01.txt, Section 6";
        smiv2:max-access "read-only";
        smiv2:oid "1.3.6.1.4.1.9.9.152.1.2.5.13";
      }

      leaf cSipStatsServerPrecondFailureOuts {
        type yang:counter32;
        description
         "This object reflects the total number of Precondition 
          Failure (580) responses sent by the user agent since system startup.
          This response is returned by a UAS if it is unable to
          perform the mandatory preconditions for the session.";
        reference
         "draft-manyfolks-sip-resource-01.txt, Section 6";
        smiv2:max-access "read-only";
        smiv2:oid "1.3.6.1.4.1.9.9.152.1.2.5.14";
      }
    }

    container cSipStatsGlobalFail {
      smiv2:oid "1.3.6.1.4.1.9.9.152.1.2.6";

      leaf cSipStatsGlobalBusyEverywhereIns {
        type yang:counter32;
        description
         "This object reflects the total number of Busy
          Everywhere (600) responses received by the user agent since system startup.
          Inbound Busy Everywhere responses indicate that the 
          called party's end system was contacted successfully
          but the called party is busy and does not wish to take
          the call at this time.";
        reference
         "RFC 2543, Sections 5.1.1 & 7.6.1";
        smiv2:max-access "read-only";
        smiv2:oid "1.3.6.1.4.1.9.9.152.1.2.6.1";
      }

      leaf cSipStatsGlobalBusyEverywhereOuts {
        type yang:counter32;
        description
         "This object reflects the total number of Busy
          Everywhere (600) responses sent by the user agent since system startup.
          Outbound Busy Everywhere responses indicate that 
          this system has successfully contacted a called party's
          end system and the called party does not wish to take
          the call at this time.";
        reference
         "RFC 2543, Sections 5.1.1 & 7.6.1";
        smiv2:max-access "read-only";
        smiv2:oid "1.3.6.1.4.1.9.9.152.1.2.6.2";
      }

      leaf cSipStatsGlobalDeclineIns {
        type yang:counter32;
        description
         "This object reflects the total number of Decline
          (603) responses received by the user agent since system startup.
          Decline responses indicate that the called party's end 
          system was contacted successfully but the called party 
          explicitly does not wish to, or cannot, participate.";
        reference
         "RFC 2543, Sections 5.1.1 & 7.6.2";
        smiv2:max-access "read-only";
        smiv2:oid "1.3.6.1.4.1.9.9.152.1.2.6.3";
      }

      leaf cSipStatsGlobalDeclineOuts {
        type yang:counter32;
        description
         "This object reflects the total number of Decline
          (603) responses sent by the user agent since system startup.
          Outbound Decline responses indicate that this system
          has successfully contacted a called party's end system
          and the called party explicitly does not wish to, or
          cannot, participate.";
        reference
         "RFC 2543, Sections 5.1.1 & 7.6.2";
        smiv2:max-access "read-only";
        smiv2:oid "1.3.6.1.4.1.9.9.152.1.2.6.4";
      }

      leaf cSipStatsGlobalNotAnywhereIns {
        type yang:counter32;
        description
         "This object reflects the total number of Does Not
          Exist Anywhere (604) responses received by the user agent since system startup.
          Inbound Does Not Exist Anywhere responses indicate that
          the server handling this system's request has authoritative
          information that the called party indicated in the To
          request field does not exist anywhere.";
        reference
         "RFC 2543, Sections 5.1.1 & 7.6.3";
        smiv2:max-access "read-only";
        smiv2:oid "1.3.6.1.4.1.9.9.152.1.2.6.5";
      }

      leaf cSipStatsGlobalNotAnywhereOuts {
        type yang:counter32;
        description
         "This object reflects the total number of Does Not
          Exist Anywhere (604) responses sent by the user agent since system startup.
          Outbound Does Not Exist Anywhere responses indicate that
          this system has authoritative information that the called
          party in the To field of received requests does not exist
          anywhere.";
        reference
         "RFC 2543, Sections 5.1.1 & 7.6.3";
        smiv2:max-access "read-only";
        smiv2:oid "1.3.6.1.4.1.9.9.152.1.2.6.6";
      }

      leaf cSipStatsGlobalNotAcceptableIns {
        type yang:counter32;
        description
         "This object reflects the total number of Not Acceptable
          (606) responses received by the user agent since system startup.
          Inbound Not Acceptable responses indicate that the called
          party's end system was contacted successfully but some
          aspect of the session description is not acceptable.";
        reference
         "RFC 2543, Sections 5.1.1 & 7.6.4";
        smiv2:max-access "read-only";
        smiv2:oid "1.3.6.1.4.1.9.9.152.1.2.6.7";
      }

      leaf cSipStatsGlobalNotAcceptableOuts {
        type yang:counter32;
        description
         "This object reflects the total number of Not Acceptable
          (606) responses sent by the user agent since system startup.
          Outbound Not Acceptable responses indicate that the called
          party wishes to communicate, but cannot adequately support
          the session described in the request.";
        reference
         "RFC 2543, Sections 5.1.1 & 7.6.4";
        smiv2:max-access "read-only";
        smiv2:oid "1.3.6.1.4.1.9.9.152.1.2.6.8";
      }
    }

    container cSipStatsTraffic {
      smiv2:oid "1.3.6.1.4.1.9.9.152.1.2.7";

      leaf cSipStatsTrafficInviteIns {
        type yang:counter32;
        description
         "This object reflects the total number of INVITE requests 
          received by the user agent since system startup.";
        reference
         "RFC 2543, Section 4.2.1";
        smiv2:max-access "read-only";
        smiv2:oid "1.3.6.1.4.1.9.9.152.1.2.7.1";
      }

      leaf cSipStatsTrafficInviteOuts {
        type yang:counter32;
        description
         "This object reflects the total number of INVITE requests sent
          by the user agent.";
        reference
         "RFC 2543, Section 4.2.1";
        smiv2:max-access "read-only";
        smiv2:oid "1.3.6.1.4.1.9.9.152.1.2.7.2";
      }

      leaf cSipStatsTrafficAckIns {
        type yang:counter32;
        description
         "This object reflects the total number of ACK requests 
          received by the user agent since system startup.";
        reference
         "RFC 2543, Section 4.2.2";
        smiv2:max-access "read-only";
        smiv2:oid "1.3.6.1.4.1.9.9.152.1.2.7.3";
      }

      leaf cSipStatsTrafficAckOuts {
        type yang:counter32;
        description
         "This object reflects the total number of ACK requests sent
          by the user agent.";
        reference
         "RFC 2543, Section 4.2.2";
        smiv2:max-access "read-only";
        smiv2:oid "1.3.6.1.4.1.9.9.152.1.2.7.4";
      }

      leaf cSipStatsTrafficByeIns {
        type yang:counter32;
        description
         "This object reflects the total number of BYE requests 
          received by the user agent since system startup.";
        reference
         "RFC 2543, Section 4.2.4";
        smiv2:max-access "read-only";
        smiv2:oid "1.3.6.1.4.1.9.9.152.1.2.7.5";
      }

      leaf cSipStatsTrafficByeOuts {
        type yang:counter32;
        description
         "This object reflects the total number of BYE requests sent
          by the user agent.";
        reference
         "RFC 2543, Section 4.2.4";
        smiv2:max-access "read-only";
        smiv2:oid "1.3.6.1.4.1.9.9.152.1.2.7.6";
      }

      leaf cSipStatsTrafficCancelIns {
        type yang:counter32;
        description
         "This object reflects the total number of CANCEL requests 
          received by the user agent since system startup.";
        reference
         "RFC 2543, Section 4.2.5";
        smiv2:max-access "read-only";
        smiv2:oid "1.3.6.1.4.1.9.9.152.1.2.7.7";
      }

      leaf cSipStatsTrafficCancelOuts {
        type yang:counter32;
        description
         "This object reflects the total number of CANCEL requests sent
          by the user agent.";
        reference
         "RFC 2543, Section 4.2.5";
        smiv2:max-access "read-only";
        smiv2:oid "1.3.6.1.4.1.9.9.152.1.2.7.8";
      }

      leaf cSipStatsTrafficOptionsIns {
        type yang:counter32;
        description
         "This object reflects the total number of OPTIONS requests 
          received by the user agent since system startup.";
        reference
         "RFC 2543, Section 4.2.3";
        smiv2:max-access "read-only";
        smiv2:oid "1.3.6.1.4.1.9.9.152.1.2.7.9";
      }

      leaf cSipStatsTrafficOptionsOuts {
        type yang:counter32;
        description
         "This object reflects the total number of OPTIONS requests sent
          by the user agent.";
        reference
         "RFC 2543, Section 4.2.3";
        smiv2:max-access "read-only";
        smiv2:oid "1.3.6.1.4.1.9.9.152.1.2.7.10";
      }

      leaf cSipStatsTrafficRegisterIns {
        type yang:counter32;
        description
         "This object reflects the total number of REGISTER requests 
          received by the user agent since system startup.";
        reference
         "RFC 2543, Section 4.2.6";
        smiv2:max-access "read-only";
        smiv2:oid "1.3.6.1.4.1.9.9.152.1.2.7.11";
      }

      leaf cSipStatsTrafficRegisterOuts {
        type yang:counter32;
        description
         "This object reflects the total number of REGISTER requests 
          sent by the user agent since system startup.";
        reference
         "RFC 2543, Section 4.2.6";
        smiv2:max-access "read-only";
        smiv2:oid "1.3.6.1.4.1.9.9.152.1.2.7.12";
      }

      leaf cSipStatsTrafficCometIns {
        type yang:counter32;
        description
         "This object reflects the total number of COndition MET 
          requests received by the user agent since system startup.";
        reference
         "draft-manyfolks-sip-resource-01.txt, Section 5";
        smiv2:max-access "read-only";
        smiv2:oid "1.3.6.1.4.1.9.9.152.1.2.7.13";
      }

      leaf cSipStatsTrafficCometOuts {
        type yang:counter32;
        description
         "This object reflects the total number of COndition MET 
          requests sent by the user agent since system startup.";
        reference
         "draft-manyfolks-sip-resource-01.txt, Section 5";
        smiv2:max-access "read-only";
        smiv2:oid "1.3.6.1.4.1.9.9.152.1.2.7.14";
      }

      leaf cSipStatsTrafficPrackIns {
        type yang:counter32;
        description
         "This object reflects the total number of PRovisonal 
          ACKnowledgement requests received by the user agent since system startup.";
        reference
         "draft-ietf-sip-100rel-02.txt";
        smiv2:max-access "read-only";
        smiv2:oid "1.3.6.1.4.1.9.9.152.1.2.7.15";
      }

      leaf cSipStatsTrafficPrackOuts {
        type yang:counter32;
        description
         "This object reflects the total number of PRovisonal 
          ACKnowledgement requests sent by the user agent since system startup.";
        reference
         "draft-ietf-sip-100rel-02.txt";
        smiv2:max-access "read-only";
        smiv2:oid "1.3.6.1.4.1.9.9.152.1.2.7.16";
      }

      leaf cSipStatsTrafficReferIns {
        type yang:counter32;
        description
         "This object reflects the total number of Refer
          requests received by the user agent since system startup.";
        smiv2:max-access "read-only";
        smiv2:oid "1.3.6.1.4.1.9.9.152.1.2.7.17";
      }

      leaf cSipStatsTrafficReferOuts {
        type yang:counter32;
        description
         "This object reflects the total number of Refer
          requests sent by the user agent since system startup.";
        smiv2:max-access "read-only";
        smiv2:oid "1.3.6.1.4.1.9.9.152.1.2.7.18";
      }

      leaf cSipStatsTrafficNotifyIns {
        type yang:counter32;
        description
         "This object reflects the total number of Notify 
          requests received by the user agent since system startup.";
        smiv2:max-access "read-only";
        smiv2:oid "1.3.6.1.4.1.9.9.152.1.2.7.19";
      }

      leaf cSipStatsTrafficNotifyOuts {
        type yang:counter32;
        description
         "This object reflects the total number of Notify 
          requests sent by the user agent since system startup.";
        smiv2:max-access "read-only";
        smiv2:oid "1.3.6.1.4.1.9.9.152.1.2.7.20";
      }

      leaf cSipStatsTrafficInfoIns {
        type yang:counter32;
        description
         "This object reflects the total number of Info 
          requests received by the user agent since system startup.";
        smiv2:max-access "read-only";
        smiv2:oid "1.3.6.1.4.1.9.9.152.1.2.7.21";
      }

      leaf cSipStatsTrafficInfoOuts {
        type yang:counter32;
        description
         "This object reflects the total number of Info 
          requests sent by the user agent since system startup.";
        smiv2:max-access "read-only";
        smiv2:oid "1.3.6.1.4.1.9.9.152.1.2.7.22";
      }

      leaf cSipStatsTrafficSubscribeIns {
        type yang:counter32;
        description
         "This object reflects the total number of Subscribe
          requests received by the user agent since system startup.";
        smiv2:max-access "read-only";
        smiv2:oid "1.3.6.1.4.1.9.9.152.1.2.7.23";
      }

      leaf cSipStatsTrafficSubscribeOuts {
        type yang:counter32;
        description
         "This object reflects the total number of Subscribe
          requests sent by the user agent since system startup.";
        smiv2:max-access "read-only";
        smiv2:oid "1.3.6.1.4.1.9.9.152.1.2.7.24";
      }

      leaf cSipStatsTrafficUpdateIns {
        type yang:counter32;
        description
         "This object reflects the total number of Update
          requests received by the user agent since system startup.";
        smiv2:max-access "read-only";
        smiv2:oid "1.3.6.1.4.1.9.9.152.1.2.7.25";
      }

      leaf cSipStatsTrafficUpdateOuts {
        type yang:counter32;
        description
         "This object reflects the total number of Update
          requests sent by the user agent since system startup.";
        smiv2:max-access "read-only";
        smiv2:oid "1.3.6.1.4.1.9.9.152.1.2.7.26";
      }
    }

    container cSipStatsRetry {
      smiv2:oid "1.3.6.1.4.1.9.9.152.1.2.8";

      leaf cSipStatsRetryInvites {
        type yang:counter32;
        description
         "This object reflects the total number of INVITE retries that 
          have been sent by the user agent since system startup.   If the number of 'first 
          attempt' INVITES is of interest, subtract the value of this 
          object from cSipStatsTrafficInviteOut.";
        smiv2:max-access "read-only";
        smiv2:oid "1.3.6.1.4.1.9.9.152.1.2.8.1";
      }

      leaf cSipStatsRetryByes {
        type yang:counter32;
        description
         "This object reflects the total number of BYE retries that have
          been sent by the user agent since system startup.";
        smiv2:max-access "read-only";
        smiv2:oid "1.3.6.1.4.1.9.9.152.1.2.8.2";
      }

      leaf cSipStatsRetryCancels {
        type yang:counter32;
        description
         "This object reflects the total number of CANCEL retries that 
          have been sent by the user agent since system startup.";
        smiv2:max-access "read-only";
        smiv2:oid "1.3.6.1.4.1.9.9.152.1.2.8.3";
      }

      leaf cSipStatsRetryRegisters {
        type yang:counter32;
        description
         "This object reflects the total number of REGISTER retries that
          have been sent by the user agent since system startup.";
        smiv2:max-access "read-only";
        smiv2:oid "1.3.6.1.4.1.9.9.152.1.2.8.4";
      }

      leaf cSipStatsRetryResponses {
        type yang:counter32;
        description
         "This object reflects the total number of Response (while 
          expecting a ACK) retries that have been sent by the user
          agent.";
        smiv2:max-access "read-only";
        smiv2:oid "1.3.6.1.4.1.9.9.152.1.2.8.5";
      }

      leaf cSipStatsRetryPracks {
        type yang:counter32;
        description
         "This object reflects the total number of PRovisional
          ACKnowledgement retries sent by the user agent since system startup.";
        smiv2:max-access "read-only";
        smiv2:oid "1.3.6.1.4.1.9.9.152.1.2.8.6";
      }

      leaf cSipStatsRetryComets {
        type yang:counter32;
        description
         "This object reflects the total number of COndition
          MET retries sent by the user agent since system startup.";
        smiv2:max-access "read-only";
        smiv2:oid "1.3.6.1.4.1.9.9.152.1.2.8.7";
      }

      leaf cSipStatsRetryReliable1xxRsps {
        type yang:counter32;
        description
         "This object reflects the total number of Reliable
          1xx Response retries sent by the user agent since system startup.";
        smiv2:max-access "read-only";
        smiv2:oid "1.3.6.1.4.1.9.9.152.1.2.8.8";
      }

      leaf cSipStatsRetryNotifys {
        type yang:counter32;
        description
         "This object reflects the total number of Notify 
          retries that have been sent by the user agent since system startup.";
        smiv2:max-access "read-only";
        smiv2:oid "1.3.6.1.4.1.9.9.152.1.2.8.9";
      }

      leaf cSipStatsRetryRefers {
        type yang:counter32;
        description
         "This object reflects the total number of Refer
          retries that have been sent by the user agent since system startup.";
        smiv2:max-access "read-only";
        smiv2:oid "1.3.6.1.4.1.9.9.152.1.2.8.10";
      }

      leaf cSipStatsRetryInfo {
        type yang:counter32;
        description
         "This object reflects the total number of Info
          retries that have been sent by the user agent since system
          startup.";
        smiv2:max-access "read-only";
        smiv2:oid "1.3.6.1.4.1.9.9.152.1.2.8.11";
      }

      leaf cSipStatsRetrySubscribe {
        type yang:counter32;
        description
         "This object reflects the total number of Subscribe
          retries that have been sent by the user agent since system
          startup.";
        smiv2:max-access "read-only";
        smiv2:oid "1.3.6.1.4.1.9.9.152.1.2.8.12";
      }
    }

    container cSipStatsMisc {
      smiv2:oid "1.3.6.1.4.1.9.9.152.1.2.9";

      leaf cSipStatsMisc3xxMappedTo4xxRsps {
        type yang:counter32;
        description
         "This object reflects the total number of incoming Redirect 
          (3xx) response messages that have been mapped to Client 
          Error (4xx) response messages.";
        smiv2:max-access "read-only";
        smiv2:oid "1.3.6.1.4.1.9.9.152.1.2.9.1";
      }
    }

    container cSipStatsConnection {
      smiv2:oid "1.3.6.1.4.1.9.9.152.1.2.10";

      leaf cSipStatsConnTCPSendFailures {
        type yang:counter32;
        description
         "This object reflects the total number of TCP send failures
          since system startup.";
        smiv2:max-access "read-only";
        smiv2:oid "1.3.6.1.4.1.9.9.152.1.2.10.1";
      }

      leaf cSipStatsConnUDPSendFailures {
        type yang:counter32;
        description
         "This object reflects the total number of UDP send failures
          since system startup.";
        smiv2:max-access "read-only";
        smiv2:oid "1.3.6.1.4.1.9.9.152.1.2.10.2";
      }

      leaf cSipStatsConnTCPRemoteClosures {
        type yang:counter32;
        description
         "This object reflects the total number of Remote Closures 
          for TCP since system startup.";
        smiv2:max-access "read-only";
        smiv2:oid "1.3.6.1.4.1.9.9.152.1.2.10.3";
      }

      leaf cSipStatsConnUDPCreateFailures {
        type yang:counter32;
        description
         "This object reflects the total number of connection create
          failures for UDP since system startup.";
        smiv2:max-access "read-only";
        smiv2:oid "1.3.6.1.4.1.9.9.152.1.2.10.4";
      }

      leaf cSipStatsConnTCPCreateFailures {
        type yang:counter32;
        description
         "This object reflects the total number of connection create
          failures for TCP since system startup.";
        smiv2:max-access "read-only";
        smiv2:oid "1.3.6.1.4.1.9.9.152.1.2.10.5";
      }

      leaf cSipStatsConnUDPInactiveTimeouts {
        type yang:counter32;
        description
         "This object reflects the total number of UDP connections that 
          timed out due to inactivity since system startup.";
        smiv2:max-access "read-only";
        smiv2:oid "1.3.6.1.4.1.9.9.152.1.2.10.6";
      }

      leaf cSipStatsConnTCPInactiveTimeouts {
        type yang:counter32;
        description
         "This object reflects the total number of TCP connections that
          timed out due to inactivity since system startup.";
        smiv2:max-access "read-only";
        smiv2:oid "1.3.6.1.4.1.9.9.152.1.2.10.7";
      }

      leaf cSipStatsActiveUDPConnections {
        type yang:gauge32;
        description
         "This object reflects the total number of active UDP
          connections since system startup.";
        smiv2:max-access "read-only";
        smiv2:oid "1.3.6.1.4.1.9.9.152.1.2.10.8";
      }

      leaf cSipStatsActiveTCPConnections {
        type yang:gauge32;
        description
         "This object reflects the total number of active TCP
          connections since system startup.";
        smiv2:max-access "read-only";
        smiv2:oid "1.3.6.1.4.1.9.9.152.1.2.10.9";
      }
    }

    container cSipCfgEarlyMediaTable {
      description
       "This table contains configuration for Early
        Media Cut Through.  The configuration controls
        how the SIP user agent will process 1xx
        (Provisional) SIP response messages that contain 
        Session Definition Protocol (SDP) payloads.";
      smiv2:oid "1.3.6.1.4.1.9.9.152.1.1.1.9";

      list cSipCfgEarlyMediaEntry {
        key "cSipCfgEarlyMediaStatusCodeIndex";
        description
         "A row in the cSipCfgEarlyMediaTable.
          A row is accessible with a Provisional (1xx)
          status code value (eg, 180) and provides
          an object for the enabling or disabling of
          the Early Media Cut Through functionality.";
        smiv2:oid "1.3.6.1.4.1.9.9.152.1.1.1.9.1";

        leaf cSipCfgEarlyMediaStatusCodeIndex {
          type CISCO-SIP-UA-MIB:CSipStatusCode;
          description
           "A unique identifier of a row in this table and
            a valid SIP status code.";
          smiv2:max-access "not-accessible";
          smiv2:oid "1.3.6.1.4.1.9.9.152.1.1.1.9.1.1";
        }

        leaf cSipCfgEarlyMediaCutThruDisabled {
          type boolean;
          description
           "This object specifies whether Early Media 
            Cut Through is enabled or disabled for the 
            SIP response messages with status codes that 
            match cSipCfgEarlyMediaStatusCodeIndex.
            
            If 'true', early media cut through is disabled,
            and the user agent will process the message as
            though it did not contain any SDP payload.
            
            If 'false', early media cut through is enabled,
            and the user agent will process the message
            similar to a 183 (Session Progress) and cut
            through for early media.  The assumption being
            that the SDP is an indication that the far end
            is going to send early media.";
          smiv2:defval "false";
          smiv2:max-access "read-write";
          smiv2:oid "1.3.6.1.4.1.9.9.152.1.1.1.9.1.2";
        }
      }
    }

    container cSipCfgBindSourceAddrTable {
      description
       "This table contains configuration for binding
        the scope of packets to the particular ethernet
        interface. The scope for the packets can be
        specified as either 'signalling' or 'media'
        packets. The ethernet interface shall be
        specified by the interface index. The table
        shall be indexed based on the scope.";
      smiv2:oid "1.3.6.1.4.1.9.9.152.1.1.1.12";

      list cSipCfgBindSourceAddrEntry {
        key "cSipCfgBindSourceAddrScope";
        description
         "A row in the cSipCfgBindSourceAddrTable.
          A row is accessible with the scope of packets
          to which the source IP address of the interface
          designated by cSipCfgBindSourceAddrInterface
          will be bound.";
        smiv2:oid "1.3.6.1.4.1.9.9.152.1.1.1.12.1";

        leaf cSipCfgBindSourceAddrScope {
          type enumeration {
            enum "media" {
              value "1";
            }
            enum "control" {
              value "2";
            }
          }
          description
           "A unique identifier of a row in this table and
            specifies the scope of packets to which the
            source IP address of the interface
            designated by cSipCfgBindSourceAddrInterface
            will be bound.";
          smiv2:max-access "not-accessible";
          smiv2:oid "1.3.6.1.4.1.9.9.152.1.1.1.12.1.1";
        }

        leaf cSipCfgBindSourceAddrInterface {
          type if-mib:InterfaceIndexOrZero;
          description
           "This object may specify the interface where the
            source IP address used in SIP signalling or media
            packets is configured.  A value of 0 means that
            there is no specific source address configured and
            in this case the best local IP address will be chosen
            by the system.";
          smiv2:defval "0";
          smiv2:max-access "read-write";
          smiv2:oid "1.3.6.1.4.1.9.9.152.1.1.1.12.1.2";
        }
      }
    }

    container cSipCfgPeerTable {
      description
       "This table contains per dial-peer SIP related 
        configuration.   
        
        The table is a sparse table of dial-peer information.
        This means, it only reflects dial-peers being used 
        for SIP.  A dial-peer is being used for SIP if the 
        value of cvVoIPPeerCfgSessionProtocol 
        (CISCO-VOICE-DIAL-CONTROL-MIB) is 'sip'.
        
        Dial-peers are not created or destroyed via this
        table.  Only SIP related configuration can be 
        performed via this table once the dial-peer exists
        in the system and is visible in this table.";
      smiv2:oid "1.3.6.1.4.1.9.9.152.1.1.4.1";

      list cSipCfgPeerEntry {
        key "cSipCfgPeerIndex";
        description
         "A row in the cSipCfgPeerTable.";
        smiv2:oid "1.3.6.1.4.1.9.9.152.1.1.4.1.1";

        leaf cSipCfgPeerIndex {
          type int32 {
            range "1..2147483647";
          }
          description
           "An arbitrary index that uniquely identifies a 
            dial-peer configured for SIP.";
          smiv2:max-access "not-accessible";
          smiv2:oid "1.3.6.1.4.1.9.9.152.1.1.4.1.1.1";
        }

        leaf cSipCfgPeerOutSessionTransport {
          type enumeration {
            enum "system" {
              value "1";
            }
            enum "udp" {
              value "2";
            }
            enum "tcp" {
              value "3";
            }
          }
          description
           "This object specifies the session transport 
            protocol that will be used by this dial-peer
            for outbound SIP messages.  
            
            The value 'system' is the default and indicates 
            that this dial-peer should use the value set by 
            cSipCfgOutSessionTransport instead.";
          smiv2:defval "system";
          smiv2:max-access "read-write";
          smiv2:oid "1.3.6.1.4.1.9.9.152.1.1.4.1.1.2";
        }

        leaf cSipCfgPeerReliable1xxRspStr {
          type snmp-framework:SnmpAdminString;
          description
           "This object specifies the string that will be 
            placed in either the Supported or Require SIP 
            header, as specified by cSipCfgPeerReliable1xxRspHdr.";
          smiv2:defval "100rel";
          smiv2:max-access "read-write";
          smiv2:oid "1.3.6.1.4.1.9.9.152.1.1.4.1.1.3";
        }

        leaf cSipCfgPeerReliable1xxRspHdr {
          type enumeration {
            enum "system" {
              value "1";
            }
            enum "supported" {
              value "2";
            }
            enum "require" {
              value "3";
            }
            enum "disabled" {
              value "4";
            }
          }
          description
           "This object specifies behavior with respect to
            Support or Require headers in SIP messages sent
            and received via this dial-peer.
            
            If the originating gateway is configured for 'require',
            the Require header is added to the outgoing INVITEs
            with the value of cSipCfgPeerReliable1xxStr.  This
            requires the use of reliable provisional responses by
            the terminating gateway.  Sessions will be torn down
            if this use cannot be supported by that gateway.
            
            If the originating gateway is configured for 'supported',
            the Supported header is added to the outgoing INVITEs
            with the value of cSipCfgPeerReliable1xxStr.  This 
            requires that an attempt to use reliable provisional
            responses be made, but sessions can continue without them.
            
            If the originating gateway is configured for 'disabled',
            the value of cSipCfgReliable1xxStr will NOT be added to
            either the Require or Supported headers of outgoing INVITEs.
            
            The value 'system' is the default and indicates that this 
            dial-peer should use the value of  cSipCfgReliable1xxRspHdr
            instead.";
          smiv2:defval "system";
          smiv2:max-access "read-write";
          smiv2:oid "1.3.6.1.4.1.9.9.152.1.1.4.1.1.4";
        }

        leaf cSipCfgPeerUrlType {
          type enumeration {
            enum "system" {
              value "1";
            }
            enum "sip" {
              value "2";
            }
            enum "tel" {
              value "3";
            }
          }
          description
           "This object specifies the URL type sent in outbound
            INVITES generated by this device.
            
            The value 'system' is the default and indicates that this 
            dial-peer should use the value of cSipCfgUrlType instead.";
          smiv2:defval "system";
          smiv2:max-access "read-write";
          smiv2:oid "1.3.6.1.4.1.9.9.152.1.1.4.1.1.5";
        }

        leaf cSipCfgPeerSwitchTransEnabled {
          type boolean;
          description
           "This object specifies if the functionality of switching
            between transports from UDP to TCP if the message size of a
            Request is greater than 1300 bytes is enabled or not.";
          smiv2:defval "false";
          smiv2:max-access "read-write";
          smiv2:oid "1.3.6.1.4.1.9.9.152.1.1.4.1.1.6";
        }
      }
    }

    container cSipCfgStatusCauseTable {
      description
       "This table contains SIP status code to PSTN cause code
        mapping configuration.  Inbound SIP response messages 
        that will result in outbound PSTN signalling messages
        will have the SIP status codes transposed into the
        PSTN cause codes as prescribed by the contents of this 
        table.";
      smiv2:oid "1.3.6.1.4.1.9.9.152.1.1.5.1";

      list cSipCfgStatusCauseEntry {
        key "cSipCfgStatusCodeIndex";
        description
         "A row in the cSipCfgStatusCauseTable.  Entries cannot be
          created or destroyed by the actions of any NMS.";
        smiv2:oid "1.3.6.1.4.1.9.9.152.1.1.5.1.1";

        leaf cSipCfgStatusCodeIndex {
          type CISCO-SIP-UA-MIB:CSipStatusCode;
          description
           "A unique identifier of a row in this table and
            a valid SIP status code.";
          smiv2:max-access "not-accessible";
          smiv2:oid "1.3.6.1.4.1.9.9.152.1.1.5.1.1.1";
        }

        leaf cSipCfgPstnCause {
          type int32 {
            range "1..2147483647";
          }
          description
           "The PSTN cause code to which the SIP status code
            given by cSipCfgStatusCodeIndex is to be mapped
            for outbound PSTN signalling messages.";
          smiv2:max-access "read-write";
          smiv2:oid "1.3.6.1.4.1.9.9.152.1.1.5.1.1.2";
        }

        leaf cSipCfgStatusCauseStoreStatus {
          type snmpv2-tc:StorageType;
          description
           "This object reflects the storage status of this
            table entry.  If the value is 'volatile', then
            this entry only exists in RAM and the information
            would be lost (reverting to defaults) on system reload.  
            If the value is 'nonVolatile' then this entry has been 
            written to NVRAM and will persist across system reloads.";
          smiv2:max-access "read-only";
          smiv2:oid "1.3.6.1.4.1.9.9.152.1.1.5.1.1.3";
        }
      }
    }

    container cSipCfgCauseStatusTable {
      description
       "This table contains PSTN cause code to SIP status code
        mapping configuration.   Inbound PSTN signalling messages
        that will result in outbound SIP response messages 
        will have the PSTN cause codes transposed into the
        SIP status codes as prescribed by the contents of this 
        table.";
      smiv2:oid "1.3.6.1.4.1.9.9.152.1.1.5.2";

      list cSipCfgCauseStatusEntry {
        key "cSipCfgPstnCauseIndex";
        description
         "A row in the cSipCfgCauseStatusTable. Entries cannot be
          created or destroyed by the actions of any NMS.";
        smiv2:oid "1.3.6.1.4.1.9.9.152.1.1.5.2.1";

        leaf cSipCfgPstnCauseIndex {
          type int32 {
            range "1..2147483647";
          }
          description
           "A unique identifier of a row in this table and
            a valid PSTN cause code.";
          smiv2:max-access "not-accessible";
          smiv2:oid "1.3.6.1.4.1.9.9.152.1.1.5.2.1.1";
        }

        leaf cSipCfgStatusCode {
          type CISCO-SIP-UA-MIB:CSipStatusCode;
          description
           "The SIP status code to which the PSTN cause code
            given by cSipCfgPstnCauseIndex is to be mapped
            for outbound SIP response messages.";
          smiv2:max-access "read-write";
          smiv2:oid "1.3.6.1.4.1.9.9.152.1.1.5.2.1.2";
        }

        leaf cSipCfgCauseStatusStoreStatus {
          type snmpv2-tc:StorageType;
          description
           "This object reflects the storage status of this
            table entry.  If the value is 'volatile', then
            this entry only exists in RAM and the information
            would be lost (reverting to defaults) on system reload.  
            If the value is 'nonVolatile' then this entry has been 
            written to NVRAM and will persist across system reloads.";
          smiv2:max-access "read-only";
          smiv2:oid "1.3.6.1.4.1.9.9.152.1.1.5.2.1.3";
        }
      }
    }

    container cSipStatsSuccessOkTable {
      description
       "This table contains statistics for sent and
        received 200 Ok response messages.  The 
        statistics are kept on per SIP method basis.";
      smiv2:oid "1.3.6.1.4.1.9.9.152.1.2.2.5";

      list cSipStatsSuccessOkEntry {
        key "cSipStatsSuccessOkMethod";
        description
         "A row in the cSipStatsSuccessOkTable.  There is 
          an entry for each SIP method for which 200 Ok 
          inbound and/or outbound statistics are kept.";
        smiv2:oid "1.3.6.1.4.1.9.9.152.1.2.2.5.1";

        leaf cSipStatsSuccessOkMethod {
          type CISCO-SIP-UA-MIB:CSipMethodStr;
          description
           "This object is used for instance identification
            of objects in this table.  The value reflects a
            SIP method.";
          smiv2:max-access "not-accessible";
          smiv2:oid "1.3.6.1.4.1.9.9.152.1.2.2.5.1.1";
        }

        leaf cSipStatsSuccessOkInbounds {
          type yang:counter32;
          description
           "This object reflects the total number of Ok
            (200) responses sent by the user agent, since
            system startup, that were associated with the
            SIP method as specified by cSipStatsSuccessOkMethod.";
          smiv2:max-access "read-only";
          smiv2:oid "1.3.6.1.4.1.9.9.152.1.2.2.5.1.2";
        }

        leaf cSipStatsSuccessOkOutbounds {
          type yang:counter32;
          description
           "This object reflects the total number of Ok
            (200) responses received by the user agent, since
            system startup, that were associated with the
            SIP method as specified by cSipStatsSuccessOkMethod.";
          smiv2:max-access "read-only";
          smiv2:oid "1.3.6.1.4.1.9.9.152.1.2.2.5.1.3";
        }
      }
    }
  }

  smiv2:alias "ciscoSipUaMIB" {
    smiv2:oid "1.3.6.1.4.1.9.9.152";
  }

  smiv2:alias "ciscoSipUaMIBNotifs" {
    smiv2:oid "1.3.6.1.4.1.9.9.152.0";
  }

  smiv2:alias "ciscoSipUaMIBObjects" {
    smiv2:oid "1.3.6.1.4.1.9.9.152.1";
  }

  smiv2:alias "cSipCfg" {
    smiv2:oid "1.3.6.1.4.1.9.9.152.1.1";
  }

  smiv2:alias "cSipCfgBase" {
    smiv2:oid "1.3.6.1.4.1.9.9.152.1.1.1";
  }

  smiv2:alias "cSipCfgTimer" {
    smiv2:oid "1.3.6.1.4.1.9.9.152.1.1.2";
  }

  smiv2:alias "cSipCfgRetry" {
    smiv2:oid "1.3.6.1.4.1.9.9.152.1.1.3";
  }

  smiv2:alias "cSipCfgPeer" {
    smiv2:oid "1.3.6.1.4.1.9.9.152.1.1.4";
  }

  smiv2:alias "cSipCfgStatusCauseMap" {
    smiv2:oid "1.3.6.1.4.1.9.9.152.1.1.5";
  }

  smiv2:alias "cSipCfgAaa" {
    smiv2:oid "1.3.6.1.4.1.9.9.152.1.1.6";
  }

  smiv2:alias "cSipCfgVoiceServiceVoip" {
    smiv2:oid "1.3.6.1.4.1.9.9.152.1.1.7";
  }

  smiv2:alias "cSipStats" {
    smiv2:oid "1.3.6.1.4.1.9.9.152.1.2";
  }

  smiv2:alias "cSipStatsInfo" {
    smiv2:oid "1.3.6.1.4.1.9.9.152.1.2.1";
  }

  smiv2:alias "cSipStatsSuccess" {
    smiv2:oid "1.3.6.1.4.1.9.9.152.1.2.2";
  }

  smiv2:alias "cSipStatsRedirect" {
    smiv2:oid "1.3.6.1.4.1.9.9.152.1.2.3";
  }

  smiv2:alias "cSipStatsErrClient" {
    smiv2:oid "1.3.6.1.4.1.9.9.152.1.2.4";
  }

  smiv2:alias "cSipStatsErrServer" {
    smiv2:oid "1.3.6.1.4.1.9.9.152.1.2.5";
  }

  smiv2:alias "cSipStatsGlobalFail" {
    smiv2:oid "1.3.6.1.4.1.9.9.152.1.2.6";
  }

  smiv2:alias "cSipStatsTraffic" {
    smiv2:oid "1.3.6.1.4.1.9.9.152.1.2.7";
  }

  smiv2:alias "cSipStatsRetry" {
    smiv2:oid "1.3.6.1.4.1.9.9.152.1.2.8";
  }

  smiv2:alias "cSipStatsMisc" {
    smiv2:oid "1.3.6.1.4.1.9.9.152.1.2.9";
  }

  smiv2:alias "cSipStatsConnection" {
    smiv2:oid "1.3.6.1.4.1.9.9.152.1.2.10";
  }

  smiv2:alias "ciscoSipUaMIBNotificationPrefix" {
    status deprecated;
    description
     "Old style notification prefixing.  Being replaced by
      ciscoSipUaMIBNotifs.";
    smiv2:oid "1.3.6.1.4.1.9.9.152.2";
  }

  smiv2:alias "ciscoSipUaMIBNotifications" {
    status deprecated;
    description
     "Old style notification prefixing.  Being replaced by
      ciscoSipUaMIBNotifs.";
    smiv2:oid "1.3.6.1.4.1.9.9.152.2.0";
  }

  smiv2:alias "ciscoSipUaMIBConformance" {
    smiv2:oid "1.3.6.1.4.1.9.9.152.3";
  }

  smiv2:alias "ciscoSipUaMIBCompliances" {
    smiv2:oid "1.3.6.1.4.1.9.9.152.3.1";
  }

  smiv2:alias "ciscoSipUaMIBGroups" {
    smiv2:oid "1.3.6.1.4.1.9.9.152.3.2";
  }

}
