/*
 * Generated by confdc --mib2yang-std
 * Source: mgmt/dmi/model/mib/src/CISCO-IETF-MPLS-ID-STD-03-MIB.mib
 */
/*
 * This YANG module has been generated by smidump 0.5.0:
 *
 *      smidump -f yang CISCO-IETF-MPLS-ID-STD-03-MIB
 *
 * Do not edit. Edit the source file instead!
 */

module CISCO-IETF-MPLS-ID-STD-03-MIB {

  namespace "urn:ietf:params:xml:ns:yang:smiv2:CISCO-IETF-MPLS-ID-STD-03-MIB";
  prefix CISCO-IETF-MPLS-ID-STD-03-MIB;

  import CISCO-MPLS-TC-EXT-STD-MIB {
    prefix "cisco-mpls";
  }

  import ietf-yang-smiv2 {
    prefix "smiv2";
  }

  organization
   "Multiprotocol Label Switching (MPLS) Working Group";

  contact
   "Venkatesan Mahalingam
    Dell Inc,
    350 Holger way, San Jose, CA, USA
    Email: venkat.mahalingams@gmail.com
    
    Kannan KV Sampath
    Aricent,
    India
    Email: Kannan.Sampath@aricent.com
    
    Sam Aldrin
    Huawei Technologies
    2330 Central Express Way,
    Santa Clara, CA 95051, USA
    Email:  aldrin.ietf@gmail.com
    
    Thomas D. Nadeau
    Juniper Networks
    10 Technology Park Drive, Westford, MA 01886
    Email: tnadeau@juniper.net";

  description
   "Copyright (c) 2012 IETF Trust and the persons identified
    as the document authors.  All rights reserved.
    
    This MIB module contains generic object definitions for
    MPLS Traffic Engineering in transport networks. This module is a
    cisco-ized version of the IETF draft:
    draft-ietf-mpls-tp-te-mib-03.";

  revision 2012-06-07 {
    description
     "[Revision added by libsmi due to a LAST-UPDATED clause.]";
  }

  revision 2012-04-08 {
    description
     "MPLS identifiers mib object extension";
  }


  container CISCO-IETF-MPLS-ID-STD-03-MIB {
    config false;

    container cmplsIdObjects {
      smiv2:oid "1.3.6.1.4.1.9.10.147.1";

      leaf cmplsGlobalId {
        type cisco-mpls:CMplsGlobalId;
        description
         "This object allows the administrator to assign a unique
          operator identifier also called MPLS-TP Global_ID.";
        reference
         "MPLS-TP Identifiers [RFC6370].";
        smiv2:max-access "read-write";
        smiv2:oid "1.3.6.1.4.1.9.10.147.1.1";
      }

      leaf cmplsIcc {
        type cisco-mpls:CMplsIccId;
        description
         "This object allows the operator or service provider to
          assign a unique MPLS-TP ITU-T Carrier Code (ICC) to a
          network.";
        reference
         "MPLS-TP Identifiers [RFC6370].";
        smiv2:max-access "read-write";
        smiv2:oid "1.3.6.1.4.1.9.10.147.1.2";
      }

      leaf cmplsNodeId {
        type cisco-mpls:CMplsNodeId;
        description
         "This object allows the operator or service provider to
          assign a unique MPLS-TP Node_ID.
          
          The Node_ID is assigned within the scope of
          the Global_ID.";
        reference
         "MPLS-TP Identifiers [RFC6370].";
        smiv2:max-access "read-write";
        smiv2:oid "1.3.6.1.4.1.9.10.147.1.3";
      }
    }
  }

  smiv2:alias "cmplsIdStdMIB" {
    smiv2:oid "1.3.6.1.4.1.9.10.147";
  }

  smiv2:alias "cmplsIdNotifications" {
    smiv2:oid "1.3.6.1.4.1.9.10.147.0";
  }

  smiv2:alias "cmplsIdObjects" {
    smiv2:oid "1.3.6.1.4.1.9.10.147.1";
  }

  smiv2:alias "cmplsIdConformance" {
    smiv2:oid "1.3.6.1.4.1.9.10.147.2";
  }

  smiv2:alias "cmplsIdGroups" {
    smiv2:oid "1.3.6.1.4.1.9.10.147.2.1";
  }

  smiv2:alias "cmplsIdCompliances" {
    smiv2:oid "1.3.6.1.4.1.9.10.147.2.2";
  }

}
