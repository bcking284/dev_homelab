/*
 * Generated by confdc --mib2yang-std
 * Source: mgmt/dmi/model/mib/src/CISCO-ENTITY-FRU-CONTROL-MIB.mib
 */
/*
 * This YANG module has been generated by smidump 0.5.0:
 *
 *      smidump -f yang CISCO-ENTITY-FRU-CONTROL-MIB
 *
 * Do not edit. Edit the source file instead!
 */

module CISCO-ENTITY-FRU-CONTROL-MIB {

  namespace "urn:ietf:params:xml:ns:yang:smiv2:CISCO-ENTITY-FRU-CONTROL-MIB";
  prefix CISCO-ENTITY-FRU-CONTROL-MIB;

  import ENTITY-MIB {
    prefix "entity-mib";
  }

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Postal: Cisco Systems, Inc.
    170 West Tasman Drive
    San Jose, CA 95134-1706
    USA
    
    Tel: +1 408 526 4000
    
    E-mail: cs-snmp@cisco.com";

  description
   "The CISCO-ENTITY-FRU-CONTROL-MIB is used to monitor
    and configure operational status of 
    Field Replaceable Units (FRUs) and other managable 
    physical entities of the system listed in the 
    Entity-MIB (RFC 2737) entPhysicalTable. 
    
    FRUs include assemblies such as power supplies, fans, 
    processor modules, interface modules, etc.";

  revision 2013-08-19 {
    description
     "Added fwMismatchFound(25), fwDownloadSuccess(26)
      and fwDownloadFailure(27) to the
      Textual Convention ModuleOperType";
  }

  revision 2011-12-22 {
    description
     "Added new enumeration value mdr(24) to
      ModuleOperType Textual Convention.";
  }

  revision 2011-03-18 {
    description
     "Added FRUCoolingUnit Textual Convention.
      Added psRedundantSingleInput(7) to Textual
      Convention PowerRedundancyType.
      
      Added the following groups:
          cefcFRUPowerRealTimeStatusGroup
          cefcFRUPowerCapabilityGroup
          cefcFRUCoolingUnitGroup
          cefcFRUFanCoolingUnitGroup
      
      Deprecated cefcCoolingGroup and replaced with
      cefcCoolingGroup2 and cefcFanCoolingGroup.";
  }

  revision 2010-12-10 {
    description
     "Added cefcMIBModuleLocalSwitchingGroup.";
  }

  revision 2008-10-08 {
    description
     "Added two new enumeration values
      upgrading(22) and okButAuthFailed(23) to
      ModuleOperType Textual Convention.";
  }

  revision 2007-06-21 {
    description
     "* Added two new enumeration values :
      psRedundant(5) and inPwrSrcRedundant(6) to 
      PowerRedundancyType Textual Convention.";
  }

  revision 2007-03-14 {
    description
     "* Added cefcTotalDrawnInlineCurrent and
      cefcMIBInLinePowerCurrentGroup.
      * Added cefcPowerNonRedundantReason and 
      cefcMIBPowerRedundancyInfoGroup. 
      * Added cefcFanCoolingCapTable and 
      cefcFanCoolingCapGroup.
      * Added cefcMIBPowerCompliance8.";
  }

  revision 2006-06-23 {
    description
     "* Added new value 'onButInlinePowerFail(12)' to PowerOperType.";
  }

  revision 2005-09-06 {
    description
     "* Added cefcPowerCapacityGroup,
      cefcCoolingGroup and cefcConnectorRatingGroup.
      * Added new enumerator 'powerCycle' to the TC 
      PowerAdminType. 
      * Added two new enumerators 'offCooling'
      and 'offConnectorRating' to the TC PowerOperType.
      * Added cefcMIBNotificationEnablesGroup2 
      and cefcMgmtNotificationsGroup3.";
  }

  revision 2004-12-09 {
    description
     "Removed the additional varbind 'entPhysicalDescr' added
      in 'cefcFRUInserted' & 'cefcFRURemoved' notifications.";
  }

  revision 2004-10-19 {
    description
     "* Added the enumeration 'syncInProgress' to
      ModuleOperType Textual Convention.
      Added an additional varbind 'entPhysicalDescr' in
      'cefcFRUInserted' & 'cefcFRURemoved' notifications.";
  }

  revision 2003-11-24 {
    description
     "* Added the enumerations okButPowerOverWarning
      and okButPowerOverCritical to ModuleOperType
      Textual Convention.";
  }

  revision 2003-10-27 {
    description
     "Added poweredDown,poweredUp, powerDenied,powerCycled
      to ModuleOperType.";
  }

  revision 2003-10-23 {
    description
     "* Added cefcModuleStateChangeReasonDescr and
      cefcModuleUpTime in the cefcModuleTable.
      * Added cefcIntelliModuleTable to provide the
      IP address information for intelligent
      modules.";
  }

  revision 2003-07-22 {
    description
     "* Modified the description for cefcPowerRedudancyMode to
      indicate that this object reflects the administrative
      power supply redundancy mode.
      * Added cefcPowerRedundancyOperMode to reflect the 
      operational status of the power supply redundancy mode.
      * Deprecated cefcMaxDefaultInLinePower and added
      cefcMaxDefaultHighInLinePower to replace it.
      * Modified the DESCRIPTION for cefcFanTrayStatusTable
      and cefcFanTrayStatusEntry to reflect the right 
      situation.";
  }

  revision 2002-10-16 {
    description
     "Added:
      * Added cefcFanTrayStatusChange notification
      * Added cefcFanTrayStatusChange to 
        cefcMgmtNotificationsGroup2";
  }

  revision 2002-10-03 {
    description
     "Added:
      * cefcFanTrayStatus table containing fan tray status 
        information.
      * added cefcPhysical table containing status information
        of the physical entity.
      * added cefcUnrecognizedFRU notification.
      * added cefcMIBFanTrayStatusGroup.
      * added cefcMIBPhysicalGroup.";
  }

  revision 2002-09-15 {
    description
     "Added:
      * powerSupplyValue table containing information such 
        as, total and used inline and data power, for variable 
        power supplies.
      
      * added following object group
        cefcMIBPowerFRUValueGroup";
  }

  revision 2002-07-12 {
    description
     "Added:
      cefcModuleLastClearConfigTime  
      cefcModuleResetReasonDescription
      cefcModuleGroupRev1
      Modified:
      Added enumerations watchDogTimeoutReset,
      resourceOverflowReset, missingTaskReset,
      lowVoltageReset, controllerReset, systemReset,
      switchoverReset, upgradeReset, downgradeReset,
      cacheErrorReset, deviceDriverReset, 
      softwareExceptionReset, restoreConfigReset,
      abortRevReset, burnBootReset,
      standbyCdHealthierReset, nonNativeConfigClearReset,
      and memoryProtectionErrorReset to 
      ModuleResetReasonType TC.";
  }

  revision 2001-05-22 {
    description
     "Modified the description for cefcTotalAvailableCurrent.
      Changed 'cefcPowerRedundancy' in the description to
      'cefcPowerRedundancyMode'
      Also made the file conform to the 72 char line limit.
      Imported NOTIFICATION-GROUP
      Added cefcMgmtNotificationsGroup.";
  }

  revision 2000-01-13 {
    description
     "Following changes are made in this revision
      
      * added following enumerations to ModuleOperType TC:
        dormant, outOfServiceAdmin, outOfServiceEnvTemp
      
      * added outOfServiceAdmin to ModuleAdminType TC
      
      * added following notifications:
        cefcMIBNotificationEnables
        cefcMIBEnableStatusNotification
        cefcPowerStatusChange
        cefcFRUInserted
        cefcFRURemoved
      
      * added following object groups:
        cefcMIBInLinePowerControlGroup
        cefcMIBNotificationEnablesGroup";
  }

  revision 1999-04-05 {
    description
     "Added module table containing the status information.";
  }

  typedef PowerRedundancyType {
    type enumeration {
      enum "notsupported" {
        value "1";
      }
      enum "redundant" {
        value "2";
      }
      enum "combined" {
        value "3";
      }
      enum "nonRedundant" {
        value "4";
      }
      enum "psRedundant" {
        value "5";
      }
      enum "inPwrSrcRedundant" {
        value "6";
      }
      enum "psRedundantSingleInput" {
        value "7";
      }
    }
    description
     "power supply redundancy modes.  valid values are:
      
      notsupported(1): Read-only operational state, indicates
          that the requested administrative state (redundant(2),
          combined(3), psRedundant(5), inPwrSrcRedundant(6)
          or psRedundantSingleInput(7)) is not supported
          by the system.
      
      redundant(2): A single power supply output can power
          the entire system, although there are more than
          one matched supply in the system.
      
          In the systems which support multiple level of
          redundancy, such as input power redundancy, this
          state indicates that redundancy is enabled on
          all levels.
      
      combined(3): The combined output of the power supplies
          are available to operate the system when there are
          more than one matched power supply in the system.
      
          In the platforms which support multiple level of
          redundancy, such as input redundancy, this state
          indicates that no redundancy on all levels.
      
      nonRedundant(4): Read-only operational state, indicates
          that there is only one power supply or there are
          unmatched power supplies in the system.
      
      psRedundant(5): Only the power output redundancy
          is enabled in the systems which support multiple
          levels of redundancy.  All other types of redundancy,
          such as input power redundancy, are disabled.
      
          This value is only supported by the systems which
          support multiple levels of redundancy.
      
      inPwrSrcRedundant(6): Only the input power redundancy
          is enabled in the systems which support multiple
          levels of redundancy.  All other types of redundancy,
          such as output power redundancy, are disabled.
      
          This value is only supported by the systems which
          support input power redundancy.
      
       psRedundantSingleInput(7): Only the power redundancy with
          single input is enabled in the systems which support
          multiple levels of redundancy.  All other types of
          redundancy, such as output power redundancy, are disabled.
      
          This value is only supported by the systems which
          support power redundancy with single input.";
  }

  typedef PowerAdminType {
    type enumeration {
      enum "on" {
        value "1";
      }
      enum "off" {
        value "2";
      }
      enum "inlineAuto" {
        value "3";
      }
      enum "inlineOn" {
        value "4";
      }
      enum "powerCycle" {
        value "5";
      }
    }
    description
     "Administratively desired FRU power state types.  valid values
      are:
      on(1):  Turn FRU on.
      off(2): Turn FRU off.
      
      The inline power means that the FRU itself won't cost any power,
      but the external device connecting to the FRU will drain the
      power from FRU.  For example, the IP phone device.  The FRU is a
      port of a switch with voice ability and IP phone will cost power
      from the port once it connects to the port.
      
      inlineAuto(3): Turn FRU inline power to auto mode. It means that
      the FRU will try to detect whether the connecting device needs
      power or not.  If it needs power, the FRU will supply power.  If
      it doesn't, the FRU will treat the device as a regular network
      device.
      
      inlineOn(4): Turn FRU inline power to on mode.  It means that
      once the device connects to the FRU, the FRU will always supply
      power to the device no matter the device needs the power or not.
      
      powerCycle(5): Power cycle the FRU.  This value may be specified
      in a management protocol set operation, it will not be returned 
      in response to a management protocol retrieval operation.";
  }

  typedef PowerOperType {
    type enumeration {
      enum "offEnvOther" {
        value "1";
      }
      enum "on" {
        value "2";
      }
      enum "offAdmin" {
        value "3";
      }
      enum "offDenied" {
        value "4";
      }
      enum "offEnvPower" {
        value "5";
      }
      enum "offEnvTemp" {
        value "6";
      }
      enum "offEnvFan" {
        value "7";
      }
      enum "failed" {
        value "8";
      }
      enum "onButFanFail" {
        value "9";
      }
      enum "offCooling" {
        value "10";
      }
      enum "offConnectorRating" {
        value "11";
      }
      enum "onButInlinePowerFail" {
        value "12";
      }
    }
    description
     "Operational FRU Status types.  valid values are:
      
      offEnvOther(1)   FRU is powered off because of a problem not
                       listed below.
      
      on(2):           FRU is powered on.
      
      offAdmin(3):     Administratively off.
      
      offDenied(4):    FRU is powered off because available
                       system power is insufficient.
      
      offEnvPower(5):  FRU is powered off because of power problem in
                       the FRU.  for example, the FRU's power
                       translation (DC-DC converter) or distribution
                       failed.
      
      offEnvTemp(6):   FRU is powered off because of temperature
                       problem.
      
      offEnvFan(7):    FRU is powered off because of fan problems.
      
      failed(8):       FRU is in failed state. 
      
      onButFanFail(9): FRU is on, but fan has failed.
      
      offCooling(10):  FRU is powered off because of the system's 
                       insufficient cooling capacity.
      
      offConnectorRating(11): FRU is powered off because of the 
                              system's connector rating exceeded.
      
      onButInlinePowerFail(12): The FRU on, but no inline power
                                is being delivered as the
                                data/inline power component of the
                                FRU has failed.";
  }

  typedef FRUCurrentType {
    type int32 {
      range "-1000000000..1000000000";
    }
    description
     "a current measurement, on the system power supply
      primary output, expressed in cefcPowerUnits.  Range is 
      from negative 1 million to positive one million
      amperes.  
      
      A negative value expresses current used by the FRU.
      A positive value expresses current supplied by the FRU.";
  }

  typedef ModuleAdminType {
    type enumeration {
      enum "enabled" {
        value "1";
      }
      enum "disabled" {
        value "2";
      }
      enum "reset" {
        value "3";
      }
      enum "outOfServiceAdmin" {
        value "4";
      }
    }
    description
     "Administratively desired module states.  Valid values are:
      
      enabled(1)     module is operational.
      disabled(2)    module is not operational.
      reset(3)       module is reset. This value may be specified
                     in a management protocol set operation, it will
                     not be returned in response to a management 
                     protocol retrieval operation. 
      outOfServiceAdmin(4)   module is powered on but out of 
                             service, set by CLI.";
  }

  typedef ModuleOperType {
    type enumeration {
      enum "unknown" {
        value "1";
      }
      enum "ok" {
        value "2";
      }
      enum "disabled" {
        value "3";
      }
      enum "okButDiagFailed" {
        value "4";
      }
      enum "boot" {
        value "5";
      }
      enum "selfTest" {
        value "6";
      }
      enum "failed" {
        value "7";
      }
      enum "missing" {
        value "8";
      }
      enum "mismatchWithParent" {
        value "9";
      }
      enum "mismatchConfig" {
        value "10";
      }
      enum "diagFailed" {
        value "11";
      }
      enum "dormant" {
        value "12";
      }
      enum "outOfServiceAdmin" {
        value "13";
      }
      enum "outOfServiceEnvTemp" {
        value "14";
      }
      enum "poweredDown" {
        value "15";
      }
      enum "poweredUp" {
        value "16";
      }
      enum "powerDenied" {
        value "17";
      }
      enum "powerCycled" {
        value "18";
      }
      enum "okButPowerOverWarning" {
        value "19";
      }
      enum "okButPowerOverCritical" {
        value "20";
      }
      enum "syncInProgress" {
        value "21";
      }
      enum "upgrading" {
        value "22";
      }
      enum "okButAuthFailed" {
        value "23";
      }
      enum "mdr" {
        value "24";
      }
      enum "fwMismatchFound" {
        value "25";
      }
      enum "fwDownloadSuccess" {
        value "26";
      }
      enum "fwDownloadFailure" {
        value "27";
      }
    }
    description
     "Operational module states.  Valid values are :
      
      unknown(1)           Module is not in one of other states
      
       normal operational states:
      
      ok(2)                 Module is operational.
      
      disabled(3)           Module is administratively disabled.
      
      okButDiagFailed(4)    Module is operational but there is some
                           diagnostic information available.
      
       transitional states:
      
      boot(5)               Module is currently in the process of
                           bringing up image.  After boot, it starts
                           its operational software and transitions
                           to the appropriate state.
      
      selfTest(6)           Module is performing selfTest.
      
      
       failure states:
      
      failed(7)              Module has failed due to some condition
                            not stated above.
      
      missing(8)             Module has been provisioned, but it is
                            missing
      
      mismatchWithParent(9)  Module is not compatible with parent
                            entity. Module has not been provisioned
                            and wrong type of module is plugged in.
                            This state can be cleared by plugging
                            in the appropriate module.
      
      mismatchConfig(10)     Module is not compatible with the
      current
                            configuration. Module was correctly
                            provisioned earlier, however the module
                            was replaced by an incompatible module.
                            This state can be resolved by clearing
                            the configuration, or replacing with the
                            appropriate module.
      
      diagFailed(11)         Module diagnostic test failed due to
      some
                            hardware failure.
      
      dormant(12)            Module is waiting for an external or
                            internal event to become operational.
      
      outOfServiceAdmin(13)  module is administratively set to be
                            powered on but out of service.
      
      outOfServiceEnvTemp(14)Module is powered on but out of service,
                            due to environmental temperature problem.
                            An out-o-service module consumes less
                            power thus will cool down the board.
      
      poweredDown(15)       Module is in powered down state.
      
      poweredUp(16)         Module is in powered up state.
      
      powerDenied(17)       System does not have enough power in
                            power budget to power on this module.
      
      powerCycled(18)       Module is being power cycled.
      
      okButPowerOverWarning(19) Module is drawing more power than 
                            allocated to this module. The module
                            is still operational but may go into
                            a failure state. This state may be
                            caused by misconfiguration of power 
                            requirements (especially for inline 
                            power). 
      
      okButPowerOverCritical(20) Module is drawing more power
                            than this module is designed to 
                            handle. The module is still 
                            operational but may go into a 
                            failure state and could potentially
                            take the system down. This state
                            may be caused by gross misconfi-
                            guration of power requirements      
                            (especially for inline power). 
      
      syncInProgress(21)    Synchronization in progress.
                            In a high availability system there 
                            will be 2 control modules, active and 
                            standby. 
                            This transitional state specifies the
                            synchronization of data between the
                            active and standby modules.
      
      upgrading(22)         Module is upgrading.
      
      okButAuthFailed(23)   Module is operational but did not pass 
                            hardware integrity verification.
      
      mdr(24)               Module is undergoing a Minimum 
                            Disruptive Restart (MDR) upgrade.
      
       firmware download states:
      
      fwMismatchFound(25)   Mistmatch found between current firmware 
                            version and the firmware version in the 
                            system image.
      
      fwDownloadSuccess(26) Module firmware download succeeded.
      
      fwDownloadFailure(27) Module firmware download failed.";
  }

  typedef ModuleResetReasonType {
    type enumeration {
      enum "unknown" {
        value "1";
      }
      enum "powerUp" {
        value "2";
      }
      enum "parityError" {
        value "3";
      }
      enum "clearConfigReset" {
        value "4";
      }
      enum "manualReset" {
        value "5";
      }
      enum "watchDogTimeoutReset" {
        value "6";
      }
      enum "resourceOverflowReset" {
        value "7";
      }
      enum "missingTaskReset" {
        value "8";
      }
      enum "lowVoltageReset" {
        value "9";
      }
      enum "controllerReset" {
        value "10";
      }
      enum "systemReset" {
        value "11";
      }
      enum "switchoverReset" {
        value "12";
      }
      enum "upgradeReset" {
        value "13";
      }
      enum "downgradeReset" {
        value "14";
      }
      enum "cacheErrorReset" {
        value "15";
      }
      enum "deviceDriverReset" {
        value "16";
      }
      enum "softwareExceptionReset" {
        value "17";
      }
      enum "restoreConfigReset" {
        value "18";
      }
      enum "abortRevReset" {
        value "19";
      }
      enum "burnBootReset" {
        value "20";
      }
      enum "standbyCdHealthierReset" {
        value "21";
      }
      enum "nonNativeConfigClearReset" {
        value "22";
      }
      enum "memoryProtectionErrorReset" {
        value "23";
      }
    }
    description
     "Describes the reason for the last module reset operation.
      
      unknown(1)                      source of the reset is not 
                                      identified
      
      powerUp(2)                      system power up operation
      
      parityError(3)                  parity error during system 
                                      bring up operation
      
      clearConfigReset(4)             reset due to clear 
                                      configuration operation
      
      manualReset(5)                  reset due to administrative 
                                      request
      
      watchDogTimeoutReset(6)         reset due to watchdog timeout
      
      resourceOverflowReset(7)        reset due to resource overflow
      
      missingTaskReset(8)             reset due to missing task
      
      lowVoltageReset(9)              reset due to low voltage
      
      controllerReset(10)             reset by controller
      
      systemReset(11)                 system reset
      
      switchoverReset(12)             reset due to user initiated 
                                      graceful switchover
      
      upgradeReset(13)                reset due to upgrade
      
      downgradeReset(14)              reset due to downgrade
      
      cacheErrorReset(15)             reset due to cache error
      
      deviceDriverReset(16)           reset due to device driver 
                                      error
      
      softwareExceptionReset(17)      reset due to software 
                                      exception
      
      restoreConfigReset(18)          reset due to configuration
                                      restoration
      
      abortRevReset(19)               reset due to revision change 
                                      abort
      
      burnBootReset(20)               reset due to boot image 
                                      change
      
      standbyCdHealthierReset(21)     reset to switch to healthier 
                                      standby card
      
      nonNativeConfigClearReset(22)   reset due clearing of 
                                      non-native configuration
      
      memoryProtectionErrorReset(23)  reset due to memory protection 
                                      violation.";
  }

  typedef FRUTimeSeconds {
    type uint32;
    description
     "This is a non-negative integer which represents
      the time in second between two epochs.
      
      Since time is not discrete, it is rounded up to
      the nearest second. For example, if the elapsed
      time is greater than zero and less or equal to
      one second, then one second is returned, etc.
      
      When objects are defined which use this type, the
      description of the object identifies both of the
      reference epochs.";
  }

  typedef FRUCoolingUnit {
    type enumeration {
      enum "cfm" {
        value "1";
      }
      enum "watts" {
        value "2";
      }
    }
    description
     "The unit for the cooling capacity and requirement.
      
      cfm(1)    Cubic feet per minute
      watts(2)  Watts";
  }


  container CISCO-ENTITY-FRU-CONTROL-MIB {
    config false;

    container cefcFRUPower {
      smiv2:oid "1.3.6.1.4.1.9.9.117.1.1";

      leaf cefcMaxDefaultInLinePower {
        type int32 {
          range "0..12500";
        }
        units "miliwatts";
        status deprecated;
        description
         "The system will provide power to the device connecting
          to the FRU if the device needs power, like an IP Phone.
          We call the providing power inline power.
          
          This MIB object controls the maximum default inline power
          for the device connecting to the FRU in the system. If the
          maximum default inline power of the device is greater than
          the maximum value reportable by this object, then this
          object should report its maximum reportable value (12500)
          and cefcMaxDefaultHighInLinePower must be used to report
          the actual maximum default inline power.";
        smiv2:defval "12500";
        smiv2:max-access "read-write";
        smiv2:oid "1.3.6.1.4.1.9.9.117.1.1.3";
      }

      leaf cefcMaxDefaultHighInLinePower {
        type uint32;
        units "miliwatts";
        description
         "The system will provide power to the device connecting
          to the FRU if the device needs power, like an IP Phone.
          We call the providing power inline power.
          
          This MIB object controls the maximum default inline power
          for the device connecting to the FRU in the system.";
        smiv2:max-access "read-write";
        smiv2:oid "1.3.6.1.4.1.9.9.117.1.1.5";
      }
    }

    container cefcMIBNotificationEnables {
      smiv2:oid "1.3.6.1.4.1.9.9.117.1.3";

      leaf cefcMIBEnableStatusNotification {
        type boolean;
        description
         "This variable indicates whether the system
          produces the following notifications:
          cefcModuleStatusChange, cefcPowerStatusChange, 
          cefcFRUInserted, cefcFRURemoved, 
          cefcUnrecognizedFRU and cefcFanTrayStatusChange.
          
          A false value will prevent these notifications
          from being generated.";
        smiv2:defval "false";
        smiv2:max-access "read-write";
        smiv2:oid "1.3.6.1.4.1.9.9.117.1.3.1";
      }

      leaf cefcEnablePSOutputChangeNotif {
        type boolean;
        description
         "This variable indicates whether the system
          produces the cefcPowerSupplyOutputChange 
          notifications when the output capacity of 
          a power supply has changed. A false value 
          will prevent this notification to generated.";
        smiv2:defval "false";
        smiv2:max-access "read-write";
        smiv2:oid "1.3.6.1.4.1.9.9.117.1.3.2";
      }
    }

    container cefcFRUPowerSupplyGroupTable {
      description
       "This table lists the redundancy mode and the
        operational status of the power supply groups
        in the system.";
      smiv2:oid "1.3.6.1.4.1.9.9.117.1.1.1";

      list cefcFRUPowerSupplyGroupEntry {
        key "entPhysicalIndex";
        description
         "An cefcFRUPowerSupplyGroupTable entry lists the desired
          redundancy mode, the units of the power outputs and the 
          available and drawn current for the power supply group.
          
          Entries are created by the agent when a power supply group
          is added to the entPhysicalTable. Entries are deleted by 
          the agent at power supply group removal.";
        smiv2:oid "1.3.6.1.4.1.9.9.117.1.1.1.1";

        leaf entPhysicalIndex {
          type leafref {
            path "/entity-mib:ENTITY-MIB/entity-mib:entPhysicalTable/entity-mib:entPhysicalEntry/entity-mib:entPhysicalIndex";
          }
        }

        leaf cefcPowerRedundancyMode {
          type CISCO-ENTITY-FRU-CONTROL-MIB:PowerRedundancyType;
          description
           "The administratively desired power supply redundancy
            mode.";
          smiv2:max-access "read-write";
          smiv2:oid "1.3.6.1.4.1.9.9.117.1.1.1.1.1";
        }

        leaf cefcPowerUnits {
          type snmpv2-tc:DisplayString;
          description
           "The units of primary supply to interpret
            cefcTotalAvailableCurrent and cefcTotalDrawnCurrent
            as power.
            
            For example, one 1000-watt power supply could 
            deliver 100 amperes at 10 volts DC.  So the value
            of cefcPowerUnits would be 'at 10 volts DC'.
            
            cefcPowerUnits is for display purposes only.";
          smiv2:max-access "read-only";
          smiv2:oid "1.3.6.1.4.1.9.9.117.1.1.1.1.2";
        }

        leaf cefcTotalAvailableCurrent {
          type CISCO-ENTITY-FRU-CONTROL-MIB:FRUCurrentType;
          description
           "Total current available for FRU usage.";
          smiv2:max-access "read-only";
          smiv2:oid "1.3.6.1.4.1.9.9.117.1.1.1.1.3";
        }

        leaf cefcTotalDrawnCurrent {
          type CISCO-ENTITY-FRU-CONTROL-MIB:FRUCurrentType;
          description
           "Total current drawn by powered-on FRUs.";
          smiv2:max-access "read-only";
          smiv2:oid "1.3.6.1.4.1.9.9.117.1.1.1.1.4";
        }

        leaf cefcPowerRedundancyOperMode {
          type CISCO-ENTITY-FRU-CONTROL-MIB:PowerRedundancyType;
          description
           "The power supply redundancy operational mode.";
          smiv2:max-access "read-only";
          smiv2:oid "1.3.6.1.4.1.9.9.117.1.1.1.1.5";
        }

        leaf cefcPowerNonRedundantReason {
          type enumeration {
            enum "notApplicable" {
              value "1";
            }
            enum "unknown" {
              value "2";
            }
            enum "singleSupply" {
              value "3";
            }
            enum "mismatchedSupplies" {
              value "4";
            }
            enum "supplyError" {
              value "5";
            }
          }
          description
           "This object has the value of notApplicable(1) when
            cefcPowerRedundancyOperMode of the instance does not
            have the value of nonRedundant(4).
            
            The other values explain the reason why 
            cefcPowerRedundancyOperMode is nonRedundant(4), e.g.
            
            unknown(2)             the reason is not identified.
            
            singleSupply(3)        There is only one power supply
                                   in the group.
            
            mismatchedSupplies(4)  There are more than one power
                                   supplies in the groups. However
                                   they are mismatched and can not
                                   work redundantly.
            
            supplyError(5)         Some power supply or supplies
                                   does or do not working properly.";
          smiv2:max-access "read-only";
          smiv2:oid "1.3.6.1.4.1.9.9.117.1.1.1.1.6";
        }

        leaf cefcTotalDrawnInlineCurrent {
          type CISCO-ENTITY-FRU-CONTROL-MIB:FRUCurrentType;
          description
           "Total inline current drawn for inline operation.";
          smiv2:max-access "read-only";
          smiv2:oid "1.3.6.1.4.1.9.9.117.1.1.1.1.7";
        }
      }
    }

    container cefcFRUPowerStatusTable {
      description
       "This table lists the power-related administrative status
        and operational status of the manageable components
        in the system.";
      smiv2:oid "1.3.6.1.4.1.9.9.117.1.1.2";

      list cefcFRUPowerStatusEntry {
        key "entPhysicalIndex";
        description
         "An cefcFRUPowerStatusTable entry lists the desired
          administrative status, the operational status of the 
          power manageable component, and the current required by 
          the component for operation.
          
          Entries are created by the agent at system power-up or 
          the insertion of the component.  Entries are deleted by
          the agent at the removal of the component.
          
          Only components with power control are listed in the 
          table.";
        smiv2:oid "1.3.6.1.4.1.9.9.117.1.1.2.1";

        leaf entPhysicalIndex {
          type leafref {
            path "/entity-mib:ENTITY-MIB/entity-mib:entPhysicalTable/entity-mib:entPhysicalEntry/entity-mib:entPhysicalIndex";
          }
        }

        leaf cefcFRUPowerAdminStatus {
          type CISCO-ENTITY-FRU-CONTROL-MIB:PowerAdminType;
          description
           "Administratively desired FRU power state.";
          smiv2:max-access "read-write";
          smiv2:oid "1.3.6.1.4.1.9.9.117.1.1.2.1.1";
        }

        leaf cefcFRUPowerOperStatus {
          type CISCO-ENTITY-FRU-CONTROL-MIB:PowerOperType;
          description
           "Operational FRU power state.";
          smiv2:max-access "read-only";
          smiv2:oid "1.3.6.1.4.1.9.9.117.1.1.2.1.2";
        }

        leaf cefcFRUCurrent {
          type CISCO-ENTITY-FRU-CONTROL-MIB:FRUCurrentType;
          description
           "Current supplied by the FRU (positive values)
            or current required to operate the FRU (negative values).";
          smiv2:max-access "read-only";
          smiv2:oid "1.3.6.1.4.1.9.9.117.1.1.2.1.3";
        }

        leaf cefcFRUPowerCapability {
          type bits {
            bit realTimeCurrent {
              position "0";
            }
          }
          description
           "This object indicates the set of supported power capabilities
            of the FRU.
            
            realTimeCurrent(0) -
                cefcFRURealTimeCurrent is supported by the FRU.";
          smiv2:max-access "read-only";
          smiv2:oid "1.3.6.1.4.1.9.9.117.1.1.2.1.4";
        }

        leaf cefcFRURealTimeCurrent {
          type CISCO-ENTITY-FRU-CONTROL-MIB:FRUCurrentType;
          description
           "This object indicates the realtime value of current supplied
            by the FRU (positive values) or the realtime value of current
            drawn by the FRU (negative values).";
          smiv2:max-access "read-only";
          smiv2:oid "1.3.6.1.4.1.9.9.117.1.1.2.1.5";
        }
      }
    }

    container cefcFRUPowerSupplyValueTable {
      description
       "This table lists the power capacity of a power FRU in the
        system if it provides variable power. Power supplies usually
        provide either system or inline power. They cannot be 
        controlled by software to dictate how they distribute power.
        We can also have what are known as variable power supplies.
        They can provide both system and inline power and can be 
        varied within hardware defined ranges for system and inline
        limited by a total maximum combined output. They could be
        configured by the user via CLI or SNMP or be controlled by
        software internally.
        This table supplements the information in the
        cefcFRUPowerStatusTable for power supply FRUs. The 
        cefcFRUCurrent attribute in that table provides the overall
        current the power supply FRU can provide while this table 
        gives us the individual contribution towards system and 
        inline power.";
      smiv2:oid "1.3.6.1.4.1.9.9.117.1.1.4";

      list cefcFRUPowerSupplyValueEntry {
        key "entPhysicalIndex";
        description
         "An cefcFRUPowerSupplyValueTable entry lists the current
          provided by the FRU for operation.
          
          Entries are created by the agent at system power-up or 
          FRU insertion.  Entries are deleted by the agent at FRU
          removal.
          
          Only power supply FRUs are listed in the table.";
        smiv2:oid "1.3.6.1.4.1.9.9.117.1.1.4.1";

        leaf entPhysicalIndex {
          type leafref {
            path "/entity-mib:ENTITY-MIB/entity-mib:entPhysicalTable/entity-mib:entPhysicalEntry/entity-mib:entPhysicalIndex";
          }
        }

        leaf cefcFRUTotalSystemCurrent {
          type CISCO-ENTITY-FRU-CONTROL-MIB:FRUCurrentType;
          description
           "Total current that could be supplied by the FRU (positive
            values) for system operations.";
          smiv2:max-access "read-write";
          smiv2:oid "1.3.6.1.4.1.9.9.117.1.1.4.1.1";
        }

        leaf cefcFRUDrawnSystemCurrent {
          type CISCO-ENTITY-FRU-CONTROL-MIB:FRUCurrentType;
          description
           "Amount of current drawn by the FRU's in the system towards
            system operations from this FRU";
          smiv2:max-access "read-write";
          smiv2:oid "1.3.6.1.4.1.9.9.117.1.1.4.1.2";
        }

        leaf cefcFRUTotalInlineCurrent {
          type CISCO-ENTITY-FRU-CONTROL-MIB:FRUCurrentType;
          description
           "Total current supplied by the FRU (positive values) for
            inline operations.";
          smiv2:max-access "read-write";
          smiv2:oid "1.3.6.1.4.1.9.9.117.1.1.4.1.3";
        }

        leaf cefcFRUDrawnInlineCurrent {
          type CISCO-ENTITY-FRU-CONTROL-MIB:FRUCurrentType;
          description
           "Amount of current that is being drawn from this FRU for inline
            operation.";
          smiv2:max-access "read-write";
          smiv2:oid "1.3.6.1.4.1.9.9.117.1.1.4.1.4";
        }
      }
    }

    container cefcModuleTable {
      description
       "A cefcModuleTable entry lists the operational and
        administrative status information for ENTITY-MIB
        entPhysicalTable entries for manageable components
        of type PhysicalClass module(9).";
      smiv2:oid "1.3.6.1.4.1.9.9.117.1.2.1";

      list cefcModuleEntry {
        key "entPhysicalIndex";
        description
         "A cefcModuleStatusTable entry lists the operational and
          administrative status information for ENTITY-MIB
          entPhysicalTable entries for manageable components 
          of type PhysicalClass module(9).
          
          Entries are created by the agent at the system power-up or
          module insertion.
          
          Entries are deleted by the agent upon module removal.";
        smiv2:oid "1.3.6.1.4.1.9.9.117.1.2.1.1";

        leaf entPhysicalIndex {
          type leafref {
            path "/entity-mib:ENTITY-MIB/entity-mib:entPhysicalTable/entity-mib:entPhysicalEntry/entity-mib:entPhysicalIndex";
          }
        }

        leaf cefcModuleAdminStatus {
          type CISCO-ENTITY-FRU-CONTROL-MIB:ModuleAdminType;
          description
           "This object provides administrative control of the
            module.";
          smiv2:max-access "read-write";
          smiv2:oid "1.3.6.1.4.1.9.9.117.1.2.1.1.1";
        }

        leaf cefcModuleOperStatus {
          type CISCO-ENTITY-FRU-CONTROL-MIB:ModuleOperType;
          description
           "This object shows the module's operational state.";
          smiv2:max-access "read-only";
          smiv2:oid "1.3.6.1.4.1.9.9.117.1.2.1.1.2";
        }

        leaf cefcModuleResetReason {
          type CISCO-ENTITY-FRU-CONTROL-MIB:ModuleResetReasonType;
          description
           "This object identifies the reason for the last reset performed
            on the module.";
          smiv2:max-access "read-only";
          smiv2:oid "1.3.6.1.4.1.9.9.117.1.2.1.1.3";
        }

        leaf cefcModuleStatusLastChangeTime {
          type yang:timestamp;
          description
           "The value of sysUpTime at the time the cefcModuleOperStatus
            is changed.";
          smiv2:max-access "read-only";
          smiv2:oid "1.3.6.1.4.1.9.9.117.1.2.1.1.4";
        }

        leaf cefcModuleLastClearConfigTime {
          type yang:timestamp;
          description
           "The value of sysUpTime when the
            configuration was most recently cleared.";
          smiv2:max-access "read-only";
          smiv2:oid "1.3.6.1.4.1.9.9.117.1.2.1.1.5";
        }

        leaf cefcModuleResetReasonDescription {
          type snmpv2-tc:DisplayString;
          description
           "A description qualifying the module reset reason
            specified in cefcModuleResetReason. 
            
            Examples:
              command xyz              
              missing task
              switch over
              watchdog timeout    
              etc.
            
            cefcModuleResetReasonDescription is for display purposes only.
            NMS applications must not parse.";
          smiv2:max-access "read-only";
          smiv2:oid "1.3.6.1.4.1.9.9.117.1.2.1.1.6";
        }

        leaf cefcModuleStateChangeReasonDescr {
          type snmpv2-tc:DisplayString;
          description
           "This object displays human-readable textual string which
            describes the cause of the last state change of the
            module. This object contains zero length string
            if no meaningful reason could be provided.
            
            Examples:
            'Invalid software version'
            'Software download failed'
            'Software version mismatch'
            'Module is in standby state'
            etc.
            
            This object is for display purposes only.
            NMS applications must not parse this object
            and take any decision based on its value.";
          smiv2:max-access "read-only";
          smiv2:oid "1.3.6.1.4.1.9.9.117.1.2.1.1.7";
        }

        leaf cefcModuleUpTime {
          type CISCO-ENTITY-FRU-CONTROL-MIB:FRUTimeSeconds;
          description
           "This object provides the up time for the module
            since it was last re-initialized.
            
            This object is not persistent; if a module reset,
            restart, power off, the up time starts from zero.";
          smiv2:max-access "read-only";
          smiv2:oid "1.3.6.1.4.1.9.9.117.1.2.1.1.8";
        }
      }
    }

    container cefcIntelliModuleTable {
      description
       "This table sparsely augments the
        cefcModuleTable (i.e., every row in
        this table corresponds to a row in
        the cefcModuleTable but not necessarily
        vice-versa).
        
        A cefcIntelliModuleTable entry lists the
        information specific to intelligent
        modules which cannot be provided by the
        cefcModuleTable.";
      smiv2:oid "1.3.6.1.4.1.9.9.117.1.2.2";

      list cefcIntelliModuleEntry {
        key "entPhysicalIndex";
        description
         "A cefcIntelliModuleTable entry lists the
          information specific to an intelligent
          module which cannot be provided by
          this module's corresponding instance in
          the cefcModuleTable. Only an intelligent
          module with Internet address configured has
          its entry here.
          
          An entry of this table is created if an 
          intelligent module is detected by the 
          managed system and its management Internet
          address is configured on the intelligent 
          module.
          
          An entry of this table is deleted if the 
          removal of Internet address configuration of 
          this module or the module itself.";
        smiv2:oid "1.3.6.1.4.1.9.9.117.1.2.2.1";

        leaf entPhysicalIndex {
          type leafref {
            path "/entity-mib:ENTITY-MIB/entity-mib:entPhysicalTable/entity-mib:entPhysicalEntry/entity-mib:entPhysicalIndex";
          }
        }

        leaf cefcIntelliModuleIPAddrType {
          type inet-address:InetAddressType;
          description
           "The type of Internet address by which the
            intelligent module is reachable.";
          smiv2:max-access "read-only";
          smiv2:oid "1.3.6.1.4.1.9.9.117.1.2.2.1.1";
        }

        leaf cefcIntelliModuleIPAddr {
          type inet-address:InetAddress;
          description
           "The Internet address configured
            for the intelligent module.
            The type of this address is 
            determined by the value of the object 
            cefcIntelliModuleIPAddrType.";
          smiv2:max-access "read-only";
          smiv2:oid "1.3.6.1.4.1.9.9.117.1.2.2.1.2";
        }
      }
    }

    container cefcModuleLocalSwitchingTable {
      description
       "This table sparsely augments the cefcModuleTable
        (i.e., every row in this table corresponds to a row in
        the cefcModuleTable but not necessarily vice-versa).
        
        A cefcModuleLocalSwitchingTable entry lists the
        information specific to local switching capable
        modules which cannot be provided by the
        cefcModuleTable.";
      smiv2:oid "1.3.6.1.4.1.9.9.117.1.2.3";

      list cefcModuleLocalSwitchingEntry {
        key "entPhysicalIndex";
        description
         "A cefcModuleLocalSwitchingTable entry lists the
          information specific to a local switching capable
          module which cannot be provided by this module's
          corresponding instance in the cefcModuleTable.
          Only a module which is capable of local switching
          has its entry here.
          
          An entry of this table is created if a module which
          is capable of local switching is detected by the
          managed system.
          
          An entry of this table is deleted if the
          removal of this module.";
        smiv2:oid "1.3.6.1.4.1.9.9.117.1.2.3.1";

        leaf entPhysicalIndex {
          type leafref {
            path "/entity-mib:ENTITY-MIB/entity-mib:entPhysicalTable/entity-mib:entPhysicalEntry/entity-mib:entPhysicalIndex";
          }
        }

        leaf cefcModuleLocalSwitchingMode {
          type enumeration {
            enum "enabled" {
              value "1";
            }
            enum "disabled" {
              value "2";
            }
          }
          description
           "This object specifies the mode of local switching.
            
            enabled(1)  - local switching is enabled.
            disabled(2) - local switching is disabled.";
          smiv2:max-access "read-write";
          smiv2:oid "1.3.6.1.4.1.9.9.117.1.2.3.1.1";
        }
      }
    }

    container cefcFanTrayStatusTable {
      description
       "This table contains the operational status information
        for all ENTITY-MIB entPhysicalTable entries which have 
        an entPhysicalClass of 'fan'; specifically, all  
        entPhysicalTable entries which represent either: one 
        physical fan, or a single physical 'fan tray' which is a
        manufactured (inseparable in the field) combination of 
        multiple fans.";
      smiv2:oid "1.3.6.1.4.1.9.9.117.1.4.1";

      list cefcFanTrayStatusEntry {
        key "entPhysicalIndex";
        description
         "An cefcFanTrayStatusTable entry lists the operational
          status information for the ENTITY-MIB entPhysicalTable 
          entry which is identified by the value of entPhysicalIndex.
          The value of entPhysicalClass for the identified entry will
          be 'fan', and the represented physical entity will be 
          either: one physical fan, or a single physical 'fan tray' 
          which is a manufactured (inseparable in the field) 
          combination of multiple fans.
          
          Entries are created by the agent at system power-up or 
          fan or fan tray insertion.  Entries are deleted 
          by the agent at the fan or fan tray removal.";
        smiv2:oid "1.3.6.1.4.1.9.9.117.1.4.1.1";

        leaf entPhysicalIndex {
          type leafref {
            path "/entity-mib:ENTITY-MIB/entity-mib:entPhysicalTable/entity-mib:entPhysicalEntry/entity-mib:entPhysicalIndex";
          }
        }

        leaf cefcFanTrayOperStatus {
          type enumeration {
            enum "unknown" {
              value "1";
            }
            enum "up" {
              value "2";
            }
            enum "down" {
              value "3";
            }
            enum "warning" {
              value "4";
            }
          }
          description
           "The operational state of the fan or fan tray.
            unknown(1) - unknown.
            up(2) - powered on.
            down(3) - powered down.
            warning(4) - partial failure, needs replacement 
                         as soon as possible.";
          smiv2:max-access "read-only";
          smiv2:oid "1.3.6.1.4.1.9.9.117.1.4.1.1.1";
        }
      }
    }

    container cefcPhysicalTable {
      description
       "This table contains one row per physical entity.";
      smiv2:oid "1.3.6.1.4.1.9.9.117.1.5.1";

      list cefcPhysicalEntry {
        key "entPhysicalIndex";
        description
         "Information about a particular physical entity.";
        smiv2:oid "1.3.6.1.4.1.9.9.117.1.5.1.1";

        leaf entPhysicalIndex {
          type leafref {
            path "/entity-mib:ENTITY-MIB/entity-mib:entPhysicalTable/entity-mib:entPhysicalEntry/entity-mib:entPhysicalIndex";
          }
        }

        leaf cefcPhysicalStatus {
          type enumeration {
            enum "other" {
              value "1";
            }
            enum "supported" {
              value "2";
            }
            enum "unsupported" {
              value "3";
            }
            enum "incompatible" {
              value "4";
            }
          }
          description
           "The status of this physical entity.
            other(1) - the status is not any of the listed below.
            supported(2) - this entity is supported.
            unsupported(3) - this entity is unsupported.
            incompatible(4) - this entity is incompatible.
            It would be unsupported(3), if the ID read from Serial
            EPROM is not supported. It would be incompatible(4), if
            in the present configuration this FRU is not supported.";
          smiv2:max-access "read-only";
          smiv2:oid "1.3.6.1.4.1.9.9.117.1.5.1.1.1";
        }
      }
    }

    container cefcPowerSupplyInputTable {
      description
       "This table contains the power input information
        for all the power supplies that have entPhysicalTable
        entries with 'powerSupply' in the entPhysicalClass. 
        
        The entries are created by the agent at the system
        power-up or power supply insertion.
        
        Entries are deleted by the agent upon power supply
        removal.
        
        The number of entries is determined by the number of
        power supplies and number of power inputs on the power 
        supply.";
      smiv2:oid "1.3.6.1.4.1.9.9.117.1.6.1";

      list cefcPowerSupplyInputEntry {
        key "entPhysicalIndex cefcPowerSupplyInputIndex";
        description
         "An entry containing power input management information
          applicable to a particular power supply and input.";
        smiv2:oid "1.3.6.1.4.1.9.9.117.1.6.1.1";

        leaf entPhysicalIndex {
          type leafref {
            path "/entity-mib:ENTITY-MIB/entity-mib:entPhysicalTable/entity-mib:entPhysicalEntry/entity-mib:entPhysicalIndex";
          }
        }

        leaf cefcPowerSupplyInputIndex {
          type uint32;
          description
           "A unique value, greater than zero, for each input on
            a power supply.";
          smiv2:max-access "not-accessible";
          smiv2:oid "1.3.6.1.4.1.9.9.117.1.6.1.1.1";
        }

        leaf cefcPowerSupplyInputType {
          type enumeration {
            enum "unknown" {
              value "1";
            }
            enum "acLow" {
              value "2";
            }
            enum "acHigh" {
              value "3";
            }
            enum "dcLow" {
              value "4";
            }
            enum "dcHigh" {
              value "5";
            }
          }
          description
           "The type of an input power detected on the power
            supply.
            
            unknown(1): No input power is detected.
            
            acLow(2): Lower rating AC input power is detected.
            
            acHigh(3): Higher rating AC input power is detected.
            
            dcLow(4): Lower rating DC input power is detected.
            
            dcHigh(5): Higher rating DC input power is detected.";
          smiv2:max-access "read-only";
          smiv2:oid "1.3.6.1.4.1.9.9.117.1.6.1.1.2";
        }
      }
    }

    container cefcPowerSupplyOutputTable {
      description
       "This table contains a list of possible output
        mode for the power supplies, whose ENTITY-MIB
        entPhysicalTable entries have an entPhysicalClass
        of 'powerSupply'. It also indicate which mode
        is the operational mode within the system.";
      smiv2:oid "1.3.6.1.4.1.9.9.117.1.6.2";

      list cefcPowerSupplyOutputEntry {
        key "entPhysicalIndex cefcPSOutputModeIndex";
        description
         "A cefcPowerSupplyOutputTable entry lists the
          power output capacity and its operational status
          for manageable components of type PhysicalClass
          'powerSupply'.
          
          Entries are created by the agent at the system
          power-up or power supply insertion.
          
          Entries are deleted by the agent upon power supply
          removal.
          
          The number of entries of a power supply is determined
          by the power supply.";
        smiv2:oid "1.3.6.1.4.1.9.9.117.1.6.2.1";

        leaf entPhysicalIndex {
          type leafref {
            path "/entity-mib:ENTITY-MIB/entity-mib:entPhysicalTable/entity-mib:entPhysicalEntry/entity-mib:entPhysicalIndex";
          }
        }

        leaf cefcPSOutputModeIndex {
          type uint32;
          description
           "A unique value, greater than zero, for each
            possible output mode on a power supply.";
          smiv2:max-access "not-accessible";
          smiv2:oid "1.3.6.1.4.1.9.9.117.1.6.2.1.1";
        }

        leaf cefcPSOutputModeCurrent {
          type CISCO-ENTITY-FRU-CONTROL-MIB:FRUCurrentType;
          description
           "The output capacity of the power supply.";
          smiv2:max-access "read-only";
          smiv2:oid "1.3.6.1.4.1.9.9.117.1.6.2.1.2";
        }

        leaf cefcPSOutputModeInOperation {
          type boolean;
          description
           "A value of 'true' indicates that this mode is the
            operational mode of the power supply output
            capacity.
            
            A value of 'false' indicates that this mode is not
            the operational mode of the power supply output
            capacity.
            
            For a given power supply's entPhysicalIndex, 
            at most one instance of this object can have the
            value of true(1).";
          smiv2:max-access "read-only";
          smiv2:oid "1.3.6.1.4.1.9.9.117.1.6.2.1.3";
        }
      }
    }

    container cefcChassisCoolingTable {
      description
       "This table contains the cooling capacity
        information of the chassis whose ENTITY-MIB
        entPhysicalTable entries have an
        entPhysicalClass of 'chassis'.";
      smiv2:oid "1.3.6.1.4.1.9.9.117.1.7.1";

      list cefcChassisCoolingEntry {
        key "entPhysicalIndex";
        description
         "A cefcChassisCoolingEntry lists the maximum
          cooling capacity that could be provided 
          for one slot on the manageable components of type
          PhysicalClass 'chassis'.
          
          Entries are created by the agent if the corresponding
          entry is created in ENTITY-MIB entPhysicalTable.
          
          Entries are deleted by the agent if the corresponding
          entry is deleted in ENTITY-MIB entPhysicalTable.";
        smiv2:oid "1.3.6.1.4.1.9.9.117.1.7.1.1";

        leaf entPhysicalIndex {
          type leafref {
            path "/entity-mib:ENTITY-MIB/entity-mib:entPhysicalTable/entity-mib:entPhysicalEntry/entity-mib:entPhysicalIndex";
          }
        }

        leaf cefcChassisPerSlotCoolingCap {
          type uint32;
          description
           "The maximum cooling capacity that could be provided
            for any slot in this chassis.
            
            The default unit of the cooling capacity is 'cfm', if
            cefcChassisPerSlotCoolingUnit is not supported.";
          smiv2:max-access "read-only";
          smiv2:oid "1.3.6.1.4.1.9.9.117.1.7.1.1.1";
        }

        leaf cefcChassisPerSlotCoolingUnit {
          type CISCO-ENTITY-FRU-CONTROL-MIB:FRUCoolingUnit;
          description
           "The unit of the maximum cooling capacity for any slot
            in this chassis.";
          smiv2:max-access "read-only";
          smiv2:oid "1.3.6.1.4.1.9.9.117.1.7.1.1.2";
        }
      }
    }

    container cefcFanCoolingTable {
      description
       "This table contains the cooling capacity
        information of the fans whose ENTITY-MIB
        entPhysicalTable entries have an
        entPhysicalClass of 'fan'.";
      smiv2:oid "1.3.6.1.4.1.9.9.117.1.7.2";

      list cefcFanCoolingEntry {
        key "entPhysicalIndex";
        description
         "A cefcFanCoolingEntry lists the cooling
          capacity that is provided by the 
          manageable components of type PhysicalClass 
          'fan'.
          
          Entries are created by the agent if the corresponding
          entry is created in ENTITY-MIB entPhysicalTable.
          
          Entries are deleted by the agent if the corresponding
          entry is deleted in ENTITY-MIB entPhysicalTable.";
        smiv2:oid "1.3.6.1.4.1.9.9.117.1.7.2.1";

        leaf entPhysicalIndex {
          type leafref {
            path "/entity-mib:ENTITY-MIB/entity-mib:entPhysicalTable/entity-mib:entPhysicalEntry/entity-mib:entPhysicalIndex";
          }
        }

        leaf cefcFanCoolingCapacity {
          type uint32;
          description
           "The cooling capacity that is provided by this fan.
            
            The default unit of the fan cooling capacity is 'cfm',
            if cefcFanCoolingCapacityUnit is not supported.";
          smiv2:max-access "read-only";
          smiv2:oid "1.3.6.1.4.1.9.9.117.1.7.2.1.1";
        }

        leaf cefcFanCoolingCapacityUnit {
          type CISCO-ENTITY-FRU-CONTROL-MIB:FRUCoolingUnit;
          description
           "The unit of the fan cooling capacity.";
          smiv2:max-access "read-only";
          smiv2:oid "1.3.6.1.4.1.9.9.117.1.7.2.1.2";
        }
      }
    }

    container cefcModuleCoolingTable {
      description
       "This table contains the cooling requirement for
        all the manageable components of type entPhysicalClass
        'module'.";
      smiv2:oid "1.3.6.1.4.1.9.9.117.1.7.3";

      list cefcModuleCoolingEntry {
        key "entPhysicalIndex";
        description
         "A cefcModuleCoolingEntry lists the cooling
          requirement for a manageable components of type
          entPhysicalClass 'module'.
          
          Entries are created by the agent at the system
          power-up or module insertion.
          
          Entries are deleted by the agent upon module
          removal.";
        smiv2:oid "1.3.6.1.4.1.9.9.117.1.7.3.1";

        leaf entPhysicalIndex {
          type leafref {
            path "/entity-mib:ENTITY-MIB/entity-mib:entPhysicalTable/entity-mib:entPhysicalEntry/entity-mib:entPhysicalIndex";
          }
        }

        leaf cefcModuleCooling {
          type uint32;
          description
           "The cooling requirement of the module and its daughter
            cards.
            
            The default unit of the module cooling requirement is
            'cfm', if cefcModuleCoolingUnit is not supported.";
          smiv2:max-access "read-only";
          smiv2:oid "1.3.6.1.4.1.9.9.117.1.7.3.1.1";
        }

        leaf cefcModuleCoolingUnit {
          type CISCO-ENTITY-FRU-CONTROL-MIB:FRUCoolingUnit;
          description
           "The unit of the cooling requirement of the module and its
            daughter cards.";
          smiv2:max-access "read-only";
          smiv2:oid "1.3.6.1.4.1.9.9.117.1.7.3.1.2";
        }
      }
    }

    container cefcFanCoolingCapTable {
      description
       "This table contains a list of the possible cooling
        capacity modes and properties of the fans, whose 
        ENTITY-MIB entPhysicalTable entries have an 
        entPhysicalClass of 'fan'.";
      smiv2:oid "1.3.6.1.4.1.9.9.117.1.7.4";

      list cefcFanCoolingCapEntry {
        key "entPhysicalIndex cefcFanCoolingCapIndex";
        description
         "A cefcFanCoolingCapacityEntry lists the cooling
          capacity mode of a manageable components of type
          entPhysicalClass 'fan'. It also lists the corresponding
          cooling capacity provided and the power consumed
          by the fan on this mode.
          
          
          Entries are created by the agent if the corresponding
          entry is created in ENTITY-MIB entPhysicalTable.
          
          Entries are deleted by the agent if the corresponding
          entry is deleted in ENTITY-MIB entPhysicalTable.";
        smiv2:oid "1.3.6.1.4.1.9.9.117.1.7.4.1";

        leaf entPhysicalIndex {
          type leafref {
            path "/entity-mib:ENTITY-MIB/entity-mib:entPhysicalTable/entity-mib:entPhysicalEntry/entity-mib:entPhysicalIndex";
          }
        }

        leaf cefcFanCoolingCapIndex {
          type uint32 {
            range "1..4095";
          }
          description
           "An arbitrary value that uniquely identifies a
            cooling capacity mode for a fan.";
          smiv2:max-access "not-accessible";
          smiv2:oid "1.3.6.1.4.1.9.9.117.1.7.4.1.1";
        }

        leaf cefcFanCoolingCapModeDescr {
          type snmp-framework:SnmpAdminString;
          description
           "A textual description of the cooling capacity
            mode of the fan.";
          smiv2:max-access "read-only";
          smiv2:oid "1.3.6.1.4.1.9.9.117.1.7.4.1.2";
        }

        leaf cefcFanCoolingCapCapacity {
          type uint32;
          description
           "The cooling capacity that could be provided
            when the fan is operating in this mode.
            
            The default unit of the cooling capacity is 'cfm',
            if cefcFanCoolingCapCapacityUnit is not supported.";
          smiv2:max-access "read-only";
          smiv2:oid "1.3.6.1.4.1.9.9.117.1.7.4.1.3";
        }

        leaf cefcFanCoolingCapCurrent {
          type CISCO-ENTITY-FRU-CONTROL-MIB:FRUCurrentType;
          description
           "The power consumption of the fan when operating in
            in this mode.";
          smiv2:max-access "read-only";
          smiv2:oid "1.3.6.1.4.1.9.9.117.1.7.4.1.4";
        }

        leaf cefcFanCoolingCapCapacityUnit {
          type CISCO-ENTITY-FRU-CONTROL-MIB:FRUCoolingUnit;
          description
           "The unit of the fan cooling capacity when operating
            in this mode.";
          smiv2:max-access "read-only";
          smiv2:oid "1.3.6.1.4.1.9.9.117.1.7.4.1.5";
        }
      }
    }

    container cefcConnectorRatingTable {
      description
       "This table contains the connector power
        ratings of FRUs. 
        
        Only components with power connector rating 
        management are listed in this table.";
      smiv2:oid "1.3.6.1.4.1.9.9.117.1.8.1";

      list cefcConnectorRatingEntry {
        key "entPhysicalIndex";
        description
         "A cefcConnectorRatingEntry lists the
          power connector rating information of a 
          component in the system.
          
          An entry or entries are created by the agent
          when an physical entity with connector rating 
          management is added to the ENTITY-MIB 
          entPhysicalTable. An entry is deleted 
          by the agent at the entity removal.";
        smiv2:oid "1.3.6.1.4.1.9.9.117.1.8.1.1";

        leaf entPhysicalIndex {
          type leafref {
            path "/entity-mib:ENTITY-MIB/entity-mib:entPhysicalTable/entity-mib:entPhysicalEntry/entity-mib:entPhysicalIndex";
          }
        }

        leaf cefcConnectorRating {
          type CISCO-ENTITY-FRU-CONTROL-MIB:FRUCurrentType;
          description
           "The maximum power that the component's
            connector can withdraw.";
          smiv2:max-access "read-only";
          smiv2:oid "1.3.6.1.4.1.9.9.117.1.8.1.1.1";
        }
      }
    }

    container cefcModulePowerConsumptionTable {
      description
       "This table contains the total power consumption
        information for modules whose ENTITY-MIB 
        entPhysicalTable entries have an entPhysicalClass 
        of 'module'.";
      smiv2:oid "1.3.6.1.4.1.9.9.117.1.8.2";

      list cefcModulePowerConsumptionEntry {
        key "entPhysicalIndex";
        description
         "A cefcModulePowerConsumptionEntry lists the total
          power consumption of a manageable components of type
          entPhysicalClass 'module'.
          
          Entries are created by the agent at the system
          power-up or module insertion.
          
          Entries are deleted by the agent upon module
          removal.";
        smiv2:oid "1.3.6.1.4.1.9.9.117.1.8.2.1";

        leaf entPhysicalIndex {
          type leafref {
            path "/entity-mib:ENTITY-MIB/entity-mib:entPhysicalTable/entity-mib:entPhysicalEntry/entity-mib:entPhysicalIndex";
          }
        }

        leaf cefcModulePowerConsumption {
          type CISCO-ENTITY-FRU-CONTROL-MIB:FRUCurrentType;
          description
           "The combined power consumption to operate the module
            and its submodule(s) and inline-power device(s).";
          smiv2:max-access "read-only";
          smiv2:oid "1.3.6.1.4.1.9.9.117.1.8.2.1.1";
        }
      }
    }
  }

  notification cefcModuleStatusChange {
    description
     "This notification is generated when the value of
      cefcModuleOperStatus changes. It can be utilized by 
      an NMS to update the status of the module it is
      managing.";
    smiv2:oid "1.3.6.1.4.1.9.9.117.2.0.1";

    container object-1 {

      leaf entPhysicalIndex {
        type leafref {
          path "/entity-mib:ENTITY-MIB/entity-mib:entPhysicalTable/entity-mib:entPhysicalEntry/entity-mib:entPhysicalIndex";
        }
      }

      leaf cefcModuleOperStatus {
        type leafref {
          path "/CISCO-ENTITY-FRU-CONTROL-MIB:CISCO-ENTITY-FRU-CONTROL-MIB/CISCO-ENTITY-FRU-CONTROL-MIB:cefcModuleTable/CISCO-ENTITY-FRU-CONTROL-MIB:cefcModuleEntry/CISCO-ENTITY-FRU-CONTROL-MIB:cefcModuleOperStatus";
        }
      }
    }

    container object-2 {

      leaf entPhysicalIndex {
        type leafref {
          path "/entity-mib:ENTITY-MIB/entity-mib:entPhysicalTable/entity-mib:entPhysicalEntry/entity-mib:entPhysicalIndex";
        }
      }

      leaf cefcModuleStatusLastChangeTime {
        type leafref {
          path "/CISCO-ENTITY-FRU-CONTROL-MIB:CISCO-ENTITY-FRU-CONTROL-MIB/CISCO-ENTITY-FRU-CONTROL-MIB:cefcModuleTable/CISCO-ENTITY-FRU-CONTROL-MIB:cefcModuleEntry/CISCO-ENTITY-FRU-CONTROL-MIB:cefcModuleStatusLastChangeTime";
        }
      }
    }
  }

  notification cefcPowerStatusChange {
    description
     "The cefcFRUPowerStatusChange notification indicates that
      the power status of a FRU has changed. The varbind for this
      notification indicates the entPhysicalIndex of the FRU,
      and the new operational-status of the FRU.";
    smiv2:oid "1.3.6.1.4.1.9.9.117.2.0.2";

    container object-1 {

      leaf entPhysicalIndex {
        type leafref {
          path "/entity-mib:ENTITY-MIB/entity-mib:entPhysicalTable/entity-mib:entPhysicalEntry/entity-mib:entPhysicalIndex";
        }
      }

      leaf cefcFRUPowerOperStatus {
        type leafref {
          path "/CISCO-ENTITY-FRU-CONTROL-MIB:CISCO-ENTITY-FRU-CONTROL-MIB/CISCO-ENTITY-FRU-CONTROL-MIB:cefcFRUPowerStatusTable/CISCO-ENTITY-FRU-CONTROL-MIB:cefcFRUPowerStatusEntry/CISCO-ENTITY-FRU-CONTROL-MIB:cefcFRUPowerOperStatus";
        }
      }
    }

    container object-2 {

      leaf entPhysicalIndex {
        type leafref {
          path "/entity-mib:ENTITY-MIB/entity-mib:entPhysicalTable/entity-mib:entPhysicalEntry/entity-mib:entPhysicalIndex";
        }
      }

      leaf cefcFRUPowerAdminStatus {
        type leafref {
          path "/CISCO-ENTITY-FRU-CONTROL-MIB:CISCO-ENTITY-FRU-CONTROL-MIB/CISCO-ENTITY-FRU-CONTROL-MIB:cefcFRUPowerStatusTable/CISCO-ENTITY-FRU-CONTROL-MIB:cefcFRUPowerStatusEntry/CISCO-ENTITY-FRU-CONTROL-MIB:cefcFRUPowerAdminStatus";
        }
      }
    }
  }

  notification cefcFRUInserted {
    description
     "The cecfFRUInserted notification indicates that a FRU was
      inserted. The varbind for this notification indicates the
      entPhysicalIndex of the inserted FRU, and the entPhysicalIndex
      of the FRU's container.";
    smiv2:oid "1.3.6.1.4.1.9.9.117.2.0.3";

    container object-1 {

      leaf entPhysicalIndex {
        type leafref {
          path "/entity-mib:ENTITY-MIB/entity-mib:entPhysicalTable/entity-mib:entPhysicalEntry/entity-mib:entPhysicalIndex";
        }
      }

      leaf entPhysicalContainedIn {
        type leafref {
          path "/entity-mib:ENTITY-MIB/entity-mib:entPhysicalTable/entity-mib:entPhysicalEntry/entity-mib:entPhysicalContainedIn";
        }
      }
    }
  }

  notification cefcFRURemoved {
    description
     "The cefcFRURemoved notification indicates that a FRU was
      removed. The varbind for this notification indicates the
      entPhysicalIndex of the removed FRU, and the entPhysicalIndex
      of the FRU's container.";
    smiv2:oid "1.3.6.1.4.1.9.9.117.2.0.4";

    container object-1 {

      leaf entPhysicalIndex {
        type leafref {
          path "/entity-mib:ENTITY-MIB/entity-mib:entPhysicalTable/entity-mib:entPhysicalEntry/entity-mib:entPhysicalIndex";
        }
      }

      leaf entPhysicalContainedIn {
        type leafref {
          path "/entity-mib:ENTITY-MIB/entity-mib:entPhysicalTable/entity-mib:entPhysicalEntry/entity-mib:entPhysicalContainedIn";
        }
      }
    }
  }

  notification cefcUnrecognizedFRU {
    description
     "The cefcUnrecognizedFRU notification indicates that a FRU was
      inserted whose product ID is not supported. The varbind for
      this notification indicates the entPhysicalIndex of the 
      inserted FRU, the entPhysicalClass this FRU belongs to, the
      entPhysicalVendorType of this FRU, the entPhysicalName
      of the FRU, the entPhysicalModelName of the inserted FRU, and
      the cefcPhysicalStatus telling the reason code for sending this
      notification.";
    smiv2:oid "1.3.6.1.4.1.9.9.117.2.0.5";

    container object-1 {

      leaf entPhysicalIndex {
        type leafref {
          path "/entity-mib:ENTITY-MIB/entity-mib:entPhysicalTable/entity-mib:entPhysicalEntry/entity-mib:entPhysicalIndex";
        }
      }

      leaf entPhysicalClass {
        type leafref {
          path "/entity-mib:ENTITY-MIB/entity-mib:entPhysicalTable/entity-mib:entPhysicalEntry/entity-mib:entPhysicalClass";
        }
      }
    }

    container object-2 {

      leaf entPhysicalIndex {
        type leafref {
          path "/entity-mib:ENTITY-MIB/entity-mib:entPhysicalTable/entity-mib:entPhysicalEntry/entity-mib:entPhysicalIndex";
        }
      }

      leaf entPhysicalVendorType {
        type leafref {
          path "/entity-mib:ENTITY-MIB/entity-mib:entPhysicalTable/entity-mib:entPhysicalEntry/entity-mib:entPhysicalVendorType";
        }
      }
    }

    container object-3 {

      leaf entPhysicalIndex {
        type leafref {
          path "/entity-mib:ENTITY-MIB/entity-mib:entPhysicalTable/entity-mib:entPhysicalEntry/entity-mib:entPhysicalIndex";
        }
      }

      leaf entPhysicalName {
        type leafref {
          path "/entity-mib:ENTITY-MIB/entity-mib:entPhysicalTable/entity-mib:entPhysicalEntry/entity-mib:entPhysicalName";
        }
      }
    }

    container object-4 {

      leaf entPhysicalIndex {
        type leafref {
          path "/entity-mib:ENTITY-MIB/entity-mib:entPhysicalTable/entity-mib:entPhysicalEntry/entity-mib:entPhysicalIndex";
        }
      }

      leaf entPhysicalModelName {
        type leafref {
          path "/entity-mib:ENTITY-MIB/entity-mib:entPhysicalTable/entity-mib:entPhysicalEntry/entity-mib:entPhysicalModelName";
        }
      }
    }

    container object-5 {

      leaf entPhysicalIndex {
        type leafref {
          path "/entity-mib:ENTITY-MIB/entity-mib:entPhysicalTable/entity-mib:entPhysicalEntry/entity-mib:entPhysicalIndex";
        }
      }

      leaf cefcPhysicalStatus {
        type leafref {
          path "/CISCO-ENTITY-FRU-CONTROL-MIB:CISCO-ENTITY-FRU-CONTROL-MIB/CISCO-ENTITY-FRU-CONTROL-MIB:cefcPhysicalTable/CISCO-ENTITY-FRU-CONTROL-MIB:cefcPhysicalEntry/CISCO-ENTITY-FRU-CONTROL-MIB:cefcPhysicalStatus";
        }
      }
    }
  }

  notification cefcFanTrayStatusChange {
    description
     "This notification is generated when the value of
      cefcFanTrayOperStatus changes.";
    smiv2:oid "1.3.6.1.4.1.9.9.117.2.0.6";

    container object-1 {

      leaf entPhysicalIndex {
        type leafref {
          path "/entity-mib:ENTITY-MIB/entity-mib:entPhysicalTable/entity-mib:entPhysicalEntry/entity-mib:entPhysicalIndex";
        }
      }

      leaf cefcFanTrayOperStatus {
        type leafref {
          path "/CISCO-ENTITY-FRU-CONTROL-MIB:CISCO-ENTITY-FRU-CONTROL-MIB/CISCO-ENTITY-FRU-CONTROL-MIB:cefcFanTrayStatusTable/CISCO-ENTITY-FRU-CONTROL-MIB:cefcFanTrayStatusEntry/CISCO-ENTITY-FRU-CONTROL-MIB:cefcFanTrayOperStatus";
        }
      }
    }
  }

  notification cefcPowerSupplyOutputChange {
    description
     "The notification indicates that the power
      supply's output capacity has changed.
      
      This notification is triggered whenever one instance 
      of the power supply's cefcPSOutputModeInOperation 
      has transitioned from 'false' to 'true'.";
    smiv2:oid "1.3.6.1.4.1.9.9.117.2.0.7";

    container object-1 {

      leaf entPhysicalIndex {
        type leafref {
          path "/entity-mib:ENTITY-MIB/entity-mib:entPhysicalTable/entity-mib:entPhysicalEntry/entity-mib:entPhysicalIndex";
        }
      }

      leaf entPhysicalName {
        type leafref {
          path "/entity-mib:ENTITY-MIB/entity-mib:entPhysicalTable/entity-mib:entPhysicalEntry/entity-mib:entPhysicalName";
        }
      }
    }

    container object-2 {

      leaf entPhysicalIndex {
        type leafref {
          path "/entity-mib:ENTITY-MIB/entity-mib:entPhysicalTable/entity-mib:entPhysicalEntry/entity-mib:entPhysicalIndex";
        }
      }

      leaf entPhysicalModelName {
        type leafref {
          path "/entity-mib:ENTITY-MIB/entity-mib:entPhysicalTable/entity-mib:entPhysicalEntry/entity-mib:entPhysicalModelName";
        }
      }
    }

    container object-3 {

      leaf entPhysicalIndex {
        type leafref {
          path "/entity-mib:ENTITY-MIB/entity-mib:entPhysicalTable/entity-mib:entPhysicalEntry/entity-mib:entPhysicalIndex";
        }
      }

      leaf cefcPSOutputModeIndex {
        type leafref {
          path "/CISCO-ENTITY-FRU-CONTROL-MIB:CISCO-ENTITY-FRU-CONTROL-MIB/CISCO-ENTITY-FRU-CONTROL-MIB:cefcPowerSupplyOutputTable/CISCO-ENTITY-FRU-CONTROL-MIB:cefcPowerSupplyOutputEntry/CISCO-ENTITY-FRU-CONTROL-MIB:cefcPSOutputModeIndex";
        }
      }

      leaf cefcPSOutputModeCurrent {
        type leafref {
          path "/CISCO-ENTITY-FRU-CONTROL-MIB:CISCO-ENTITY-FRU-CONTROL-MIB/CISCO-ENTITY-FRU-CONTROL-MIB:cefcPowerSupplyOutputTable/CISCO-ENTITY-FRU-CONTROL-MIB:cefcPowerSupplyOutputEntry/CISCO-ENTITY-FRU-CONTROL-MIB:cefcPSOutputModeCurrent";
        }
      }
    }
  }

  smiv2:alias "ciscoEntityFRUControlMIB" {
    smiv2:oid "1.3.6.1.4.1.9.9.117";
  }

  smiv2:alias "cefcMIBObjects" {
    smiv2:oid "1.3.6.1.4.1.9.9.117.1";
  }

  smiv2:alias "cefcFRUPower" {
    smiv2:oid "1.3.6.1.4.1.9.9.117.1.1";
  }

  smiv2:alias "cefcModule" {
    smiv2:oid "1.3.6.1.4.1.9.9.117.1.2";
  }

  smiv2:alias "cefcMIBNotificationEnables" {
    smiv2:oid "1.3.6.1.4.1.9.9.117.1.3";
  }

  smiv2:alias "cefcFRUFan" {
    smiv2:oid "1.3.6.1.4.1.9.9.117.1.4";
  }

  smiv2:alias "cefcPhysical" {
    smiv2:oid "1.3.6.1.4.1.9.9.117.1.5";
  }

  smiv2:alias "cefcPowerCapacity" {
    smiv2:oid "1.3.6.1.4.1.9.9.117.1.6";
  }

  smiv2:alias "cefcCooling" {
    smiv2:oid "1.3.6.1.4.1.9.9.117.1.7";
  }

  smiv2:alias "cefcConnector" {
    smiv2:oid "1.3.6.1.4.1.9.9.117.1.8";
  }

  smiv2:alias "cefcFRUMIBNotificationPrefix" {
    smiv2:oid "1.3.6.1.4.1.9.9.117.2";
  }

  smiv2:alias "cefcMIBNotifications" {
    smiv2:oid "1.3.6.1.4.1.9.9.117.2.0";
  }

  smiv2:alias "cefcMIBConformance" {
    smiv2:oid "1.3.6.1.4.1.9.9.117.3";
  }

  smiv2:alias "cefcMIBCompliances" {
    smiv2:oid "1.3.6.1.4.1.9.9.117.3.1";
  }

  smiv2:alias "cefcMIBGroups" {
    smiv2:oid "1.3.6.1.4.1.9.9.117.3.2";
  }

}
