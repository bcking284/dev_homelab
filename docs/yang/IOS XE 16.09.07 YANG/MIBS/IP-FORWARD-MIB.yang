/*
 * Generated by confdc --mib2yang-std
 * Source: mgmt/dmi/model/mib/src/IP-FORWARD-MIB.mib
 */
/*
 * This YANG module has been generated by smidump 0.5.0:
 *
 *      smidump -f yang IP-FORWARD-MIB
 *
 * Do not edit. Edit the source file instead!
 */

module IP-FORWARD-MIB {

  namespace "urn:ietf:params:xml:ns:yang:smiv2:IP-FORWARD-MIB";
  prefix IP-FORWARD-MIB;

  import SNMPv2-TC {
    prefix "snmpv2-tc";
  }

  import ietf-inet-types {
    prefix "inet";
  }

  import ietf-yang-smiv2 {
    prefix "smiv2";
  }

  import ietf-yang-types {
    prefix "yang";
  }

  organization
   "IETF OSPF Working Group";

  contact
   "        Fred Baker
    Postal: Cisco Systems
            519 Lado Drive
            Santa Barbara, California 93111
    
    Phone:  +1 805 681 0115
    Email:  fred@cisco.com";

  description
   "The MIB module for the display of CIDR multipath IP Routes.";

  revision 1996-09-19 {
    description
     "Revisions made by the OSPF WG.";
  }


  container IP-FORWARD-MIB {
    config false;

    container ipForward {
      smiv2:oid "1.3.6.1.2.1.4.24";

      leaf ipForwardNumber {
        type yang:gauge32;
        status obsolete;
        description
         "The number of current  ipForwardTable  entries
          that are not invalid.";
        smiv2:max-access "read-only";
        smiv2:oid "1.3.6.1.2.1.4.24.1";
      }

      leaf ipCidrRouteNumber {
        type yang:gauge32;
        description
         "The number of current ipCidrRouteTable entries
          that are not invalid.";
        smiv2:max-access "read-only";
        smiv2:oid "1.3.6.1.2.1.4.24.3";
      }
    }

    container ipForwardTable {
      status obsolete;
      description
       "This entity's IP Routing table.";
      reference
       "RFC 1213 Section 6.6, The IP Group";
      smiv2:oid "1.3.6.1.2.1.4.24.2";

      list ipForwardEntry {
        key "ipForwardDest ipForwardProto ipForwardPolicy ipForwardNextHop";
        status obsolete;
        description
         "A particular route to  a  particular  destina-
          tion, under a particular policy.";
        smiv2:oid "1.3.6.1.2.1.4.24.2.1";

        leaf ipForwardDest {
          type inet:ipv4-address;
          status obsolete;
          description
           "The destination IP address of this route.   An
            entry  with  a value of 0.0.0.0 is considered a
            default route.
            
            This object may not take a Multicast (Class  D)
            address value.
            
            Any assignment (implicit or  otherwise)  of  an
            instance  of  this  object to a value x must be
            rejected if the bitwise logical-AND of  x  with
            the  value of the corresponding instance of the
            ipForwardMask object is not equal to x.";
          smiv2:max-access "read-only";
          smiv2:oid "1.3.6.1.2.1.4.24.2.1.1";
        }

        leaf ipForwardMask {
          type inet:ipv4-address;
          status obsolete;
          description
           "Indicate the mask to be logical-ANDed with the
            destination  address  before  being compared to
            the value  in  the  ipForwardDest  field.   For
            those  systems  that  do  not support arbitrary
            subnet masks, an agent constructs the value  of
            the  ipForwardMask  by  reference to the IP Ad-
            dress Class.
            
            Any assignment (implicit or  otherwise)  of  an
            instance  of  this  object to a value x must be
            rejected if the bitwise logical-AND of  x  with
            the  value of the corresponding instance of the
            ipForwardDest object is not equal to ipForward-
            Dest.";
          smiv2:defval "'00000000'H";
          smiv2:max-access "read-write";
          smiv2:oid "1.3.6.1.2.1.4.24.2.1.2";
        }

        leaf ipForwardPolicy {
          type int32;
          status obsolete;
          description
           "The general set of conditions that would cause
            the  selection  of  one multipath route (set of
            next hops for a given destination) is  referred
            to as 'policy'.
            
            Unless the mechanism indicated by ipForwardPro-
            to specifies otherwise, the policy specifier is
            the IP TOS Field.  The encoding of IP TOS is as
             specified  by  the  following convention.  Zero
            indicates the default path if no more  specific
            policy applies.
            
            +-----+-----+-----+-----+-----+-----+-----+-----+
            |                 |                       |     |
            |   PRECEDENCE    |    TYPE OF SERVICE    |  0  |
            |                 |                       |     |
            +-----+-----+-----+-----+-----+-----+-----+-----+
            
                     IP TOS                IP TOS
                Field     Policy      Field     Policy
                Contents    Code      Contents    Code
                0 0 0 0  ==>   0      0 0 0 1  ==>   2
                0 0 1 0  ==>   4      0 0 1 1  ==>   6
                0 1 0 0  ==>   8      0 1 0 1  ==>  10
                0 1 1 0  ==>  12      0 1 1 1  ==>  14
                1 0 0 0  ==>  16      1 0 0 1  ==>  18
                1 0 1 0  ==>  20      1 0 1 1  ==>  22
                1 1 0 0  ==>  24      1 1 0 1  ==>  26
                1 1 1 0  ==>  28      1 1 1 1  ==>  30
            
            Protocols defining 'policy' otherwise must  ei-
            ther define a set of values which are valid for
            this  object  or  must  implement  an  integer-
            instanced  policy table for which this object's
            value acts as an index.";
          smiv2:max-access "read-only";
          smiv2:oid "1.3.6.1.2.1.4.24.2.1.3";
        }

        leaf ipForwardNextHop {
          type inet:ipv4-address;
          status obsolete;
          description
           "On remote routes, the address of the next sys-
            tem en route; Otherwise, 0.0.0.0.";
          smiv2:max-access "read-only";
          smiv2:oid "1.3.6.1.2.1.4.24.2.1.4";
        }

        leaf ipForwardIfIndex {
          type int32;
          status obsolete;
          description
           "The ifIndex value which identifies  the  local
            interface  through  which  the next hop of this
            route should be reached.";
          smiv2:defval "0";
          smiv2:max-access "read-write";
          smiv2:oid "1.3.6.1.2.1.4.24.2.1.5";
        }

        leaf ipForwardType {
          type enumeration {
            enum "other" {
              value "1";
            }
            enum "invalid" {
              value "2";
            }
            enum "local" {
              value "3";
            }
            enum "remote" {
              value "4";
            }
          }
          status obsolete;
          description
           "The type of route.  Note that local(3)  refers
            to  a route for which the next hop is the final
            destination; remote(4) refers to  a  route  for
            which  the  next  hop is not the final destina-
            tion.
            
            Setting this object to the value invalid(2) has
            the  effect  of  invalidating the corresponding
            entry in the ipForwardTable object.   That  is,
            it  effectively  disassociates  the destination
            identified with said entry from the route iden-
            tified    with    said   entry.    It   is   an
            implementation-specific matter  as  to  whether
            the agent removes an invalidated entry from the
            table.  Accordingly, management  stations  must
            be prepared to receive tabular information from
            agents that corresponds to entries not current-
            ly  in  use.  Proper interpretation of such en-
            tries requires examination of the relevant  ip-
            ForwardType object.";
          smiv2:defval "invalid";
          smiv2:max-access "read-write";
          smiv2:oid "1.3.6.1.2.1.4.24.2.1.6";
        }

        leaf ipForwardProto {
          type enumeration {
            enum "other" {
              value "1";
            }
            enum "local" {
              value "2";
            }
            enum "netmgmt" {
              value "3";
            }
            enum "icmp" {
              value "4";
            }
            enum "egp" {
              value "5";
            }
            enum "ggp" {
              value "6";
            }
            enum "hello" {
              value "7";
            }
            enum "rip" {
              value "8";
            }
            enum "is-is" {
              value "9";
            }
            enum "es-is" {
              value "10";
            }
            enum "ciscoIgrp" {
              value "11";
            }
            enum "bbnSpfIgp" {
              value "12";
            }
            enum "ospf" {
              value "13";
            }
            enum "bgp" {
              value "14";
            }
            enum "idpr" {
              value "15";
            }
          }
          status obsolete;
          description
           "The routing mechanism via which this route was
            learned.  Inclusion of values for gateway rout-
            ing protocols is not  intended  to  imply  that
            hosts should support those protocols.";
          smiv2:max-access "read-only";
          smiv2:oid "1.3.6.1.2.1.4.24.2.1.7";
        }

        leaf ipForwardAge {
          type int32;
          status obsolete;
          description
           "The number of seconds  since  this  route  was
            last  updated  or  otherwise  determined  to be
            correct.  Note that no semantics of  `too  old'
            can  be implied except through knowledge of the
            routing  protocol  by  which  the   route   was
            learned.";
          smiv2:defval "0";
          smiv2:max-access "read-only";
          smiv2:oid "1.3.6.1.2.1.4.24.2.1.8";
        }

        leaf ipForwardInfo {
          type yang:object-identifier-128;
          status obsolete;
          description
           "A reference to MIB definitions specific to the
            particular  routing protocol which is responsi-
            ble for this route, as determined by the  value
            specified  in the route's ipForwardProto value.
            If this information is not present,  its  value
            should be set to the OBJECT IDENTIFIER { 0 0 },
            which is a syntactically valid object  identif-
            ier, and any implementation conforming to ASN.1
            and the Basic Encoding Rules must  be  able  to
            generate and recognize this value.";
          smiv2:max-access "read-write";
          smiv2:oid "1.3.6.1.2.1.4.24.2.1.9";
        }

        leaf ipForwardNextHopAS {
          type int32;
          status obsolete;
          description
           "The Autonomous System Number of the Next  Hop.
            When  this  is  unknown  or not relevant to the
            protocol indicated by ipForwardProto, zero.";
          smiv2:defval "0";
          smiv2:max-access "read-write";
          smiv2:oid "1.3.6.1.2.1.4.24.2.1.10";
        }

        leaf ipForwardMetric1 {
          type int32;
          status obsolete;
          description
           "The primary routing  metric  for  this  route.
            The  semantics of this metric are determined by
            the routing-protocol specified in  the  route's
            ipForwardProto  value.   If  this metric is not
            used, its value should be set to -1.";
          smiv2:defval "-1";
          smiv2:max-access "read-write";
          smiv2:oid "1.3.6.1.2.1.4.24.2.1.11";
        }

        leaf ipForwardMetric2 {
          type int32;
          status obsolete;
          description
           "An alternate routing metric  for  this  route.
            The  semantics of this metric are determined by
            the routing-protocol specified in  the  route's
            ipForwardProto  value.   If  this metric is not
            used, its value should be set to -1.";
          smiv2:defval "-1";
          smiv2:max-access "read-write";
          smiv2:oid "1.3.6.1.2.1.4.24.2.1.12";
        }

        leaf ipForwardMetric3 {
          type int32;
          status obsolete;
          description
           "An alternate routing metric  for  this  route.
            The  semantics of this metric are determined by
            the routing-protocol specified in  the  route's
            ipForwardProto  value.   If  this metric is not
            used, its value should be set to -1.";
          smiv2:defval "-1";
          smiv2:max-access "read-write";
          smiv2:oid "1.3.6.1.2.1.4.24.2.1.13";
        }

        leaf ipForwardMetric4 {
          type int32;
          status obsolete;
          description
           "An alternate routing metric  for  this  route.
            The  semantics of this metric are determined by
            the routing-protocol specified in  the  route's
            ipForwardProto  value.   If  this metric is not
            used, its value should be set to -1.";
          smiv2:defval "-1";
          smiv2:max-access "read-write";
          smiv2:oid "1.3.6.1.2.1.4.24.2.1.14";
        }

        leaf ipForwardMetric5 {
          type int32;
          status obsolete;
          description
           "An alternate routing metric  for  this  route.
            The  semantics of this metric are determined by
            the routing-protocol specified in  the  route's
            ipForwardProto  value.   If  this metric is not
            used, its value should be set to -1.";
          smiv2:defval "-1";
          smiv2:max-access "read-write";
          smiv2:oid "1.3.6.1.2.1.4.24.2.1.15";
        }
      }
    }

    container ipCidrRouteTable {
      description
       "This entity's IP Routing table.";
      reference
       "RFC 1213 Section 6.6, The IP Group";
      smiv2:oid "1.3.6.1.2.1.4.24.4";

      list ipCidrRouteEntry {
        key "ipCidrRouteDest ipCidrRouteMask ipCidrRouteTos ipCidrRouteNextHop";
        description
         "A particular route to  a  particular  destina-
          tion, under a particular policy.";
        smiv2:oid "1.3.6.1.2.1.4.24.4.1";

        leaf ipCidrRouteDest {
          type inet:ipv4-address;
          description
           "The destination IP address of this route.
            
            This object may not take a Multicast (Class  D)
            address value.
            
            Any assignment (implicit or  otherwise)  of  an
            instance  of  this  object to a value x must be
            rejected if the bitwise logical-AND of  x  with
            the  value of the corresponding instance of the
            ipCidrRouteMask object is not equal to x.";
          smiv2:max-access "read-only";
          smiv2:oid "1.3.6.1.2.1.4.24.4.1.1";
        }

        leaf ipCidrRouteMask {
          type inet:ipv4-address;
          description
           "Indicate the mask to be logical-ANDed with the
            destination  address  before  being compared to
            the value  in  the  ipCidrRouteDest  field.   For
            those  systems  that  do  not support arbitrary
            subnet masks, an agent constructs the value  of
            the  ipCidrRouteMask  by  reference to the IP Ad-
            dress Class.
            
            Any assignment (implicit or  otherwise)  of  an
            instance  of  this  object to a value x must be
            rejected if the bitwise logical-AND of  x  with
            the  value of the corresponding instance of the
            ipCidrRouteDest object is not equal to ipCidrRoute-
            Dest.";
          smiv2:max-access "read-only";
          smiv2:oid "1.3.6.1.2.1.4.24.4.1.2";
        }

        leaf ipCidrRouteTos {
          type int32;
          description
           "The policy specifier is the IP TOS Field.  The encoding
            of IP TOS is as specified  by  the  following convention.
            Zero indicates the default path if no more  specific
            policy applies.
            
            +-----+-----+-----+-----+-----+-----+-----+-----+
            |                 |                       |     |
            |   PRECEDENCE    |    TYPE OF SERVICE    |  0  |
            |                 |                       |     |
            +-----+-----+-----+-----+-----+-----+-----+-----+
            
                     IP TOS                IP TOS
                Field     Policy      Field     Policy
                Contents    Code      Contents    Code
                0 0 0 0  ==>   0      0 0 0 1  ==>   2
                0 0 1 0  ==>   4      0 0 1 1  ==>   6
                0 1 0 0  ==>   8      0 1 0 1  ==>  10
                0 1 1 0  ==>  12      0 1 1 1  ==>  14
                1 0 0 0  ==>  16      1 0 0 1  ==>  18
                1 0 1 0  ==>  20      1 0 1 1  ==>  22
                1 1 0 0  ==>  24      1 1 0 1  ==>  26
                1 1 1 0  ==>  28      1 1 1 1  ==>  30";
          smiv2:max-access "read-only";
          smiv2:oid "1.3.6.1.2.1.4.24.4.1.3";
        }

        leaf ipCidrRouteNextHop {
          type inet:ipv4-address;
          description
           "On remote routes, the address of the next sys-
            tem en route; Otherwise, 0.0.0.0.";
          smiv2:max-access "read-only";
          smiv2:oid "1.3.6.1.2.1.4.24.4.1.4";
        }

        leaf ipCidrRouteIfIndex {
          type int32;
          description
           "The ifIndex value which identifies  the  local
            interface  through  which  the next hop of this
            route should be reached.";
          smiv2:defval "0";
          smiv2:max-access "read-write";
          smiv2:oid "1.3.6.1.2.1.4.24.4.1.5";
        }

        leaf ipCidrRouteType {
          type enumeration {
            enum "other" {
              value "1";
            }
            enum "reject" {
              value "2";
            }
            enum "local" {
              value "3";
            }
            enum "remote" {
              value "4";
            }
          }
          description
           "The type of route.  Note that local(3)  refers
            to  a route for which the next hop is the final
            destination; remote(4) refers to  a  route  for
            which  the  next  hop is not the final destina-
            tion.
            
            Routes which do not result in traffic forwarding or
            rejection should not be displayed even if the
            implementation keeps them stored internally.
            
            
            reject (2) refers to a route which, if matched, discards
            the message as unreachable. This is used in some
            protocols as a means of correctly aggregating routes.";
          smiv2:max-access "read-write";
          smiv2:oid "1.3.6.1.2.1.4.24.4.1.6";
        }

        leaf ipCidrRouteProto {
          type enumeration {
            enum "other" {
              value "1";
            }
            enum "local" {
              value "2";
            }
            enum "netmgmt" {
              value "3";
            }
            enum "icmp" {
              value "4";
            }
            enum "egp" {
              value "5";
            }
            enum "ggp" {
              value "6";
            }
            enum "hello" {
              value "7";
            }
            enum "rip" {
              value "8";
            }
            enum "isIs" {
              value "9";
            }
            enum "esIs" {
              value "10";
            }
            enum "ciscoIgrp" {
              value "11";
            }
            enum "bbnSpfIgp" {
              value "12";
            }
            enum "ospf" {
              value "13";
            }
            enum "bgp" {
              value "14";
            }
            enum "idpr" {
              value "15";
            }
            enum "ciscoEigrp" {
              value "16";
            }
          }
          description
           "The routing mechanism via which this route was
            learned.  Inclusion of values for gateway rout-
            ing protocols is not  intended  to  imply  that
            hosts should support those protocols.";
          smiv2:max-access "read-only";
          smiv2:oid "1.3.6.1.2.1.4.24.4.1.7";
        }

        leaf ipCidrRouteAge {
          type int32;
          description
           "The number of seconds  since  this  route  was
            last  updated  or  otherwise  determined  to be
            correct.  Note that no semantics of  `too  old'
            can  be implied except through knowledge of the
            routing  protocol  by  which  the   route   was
            learned.";
          smiv2:defval "0";
          smiv2:max-access "read-only";
          smiv2:oid "1.3.6.1.2.1.4.24.4.1.8";
        }

        leaf ipCidrRouteInfo {
          type yang:object-identifier-128;
          description
           "A reference to MIB definitions specific to the
            particular  routing protocol which is responsi-
            ble for this route, as determined by the  value
            specified  in the route's ipCidrRouteProto value.
            If this information is not present,  its  value
            should be set to the OBJECT IDENTIFIER { 0 0 },
            which is a syntactically valid object  identif-
            ier, and any implementation conforming to ASN.1
            and the Basic Encoding Rules must  be  able  to
            generate and recognize this value.";
          smiv2:max-access "read-write";
          smiv2:oid "1.3.6.1.2.1.4.24.4.1.9";
        }

        leaf ipCidrRouteNextHopAS {
          type int32;
          description
           "The Autonomous System Number of the Next  Hop.
            The  semantics of this object are determined by
            the routing-protocol specified in  the  route's
            ipCidrRouteProto  value. When  this object is
            unknown or not relevant its value should be set
            to zero.";
          smiv2:defval "0";
          smiv2:max-access "read-write";
          smiv2:oid "1.3.6.1.2.1.4.24.4.1.10";
        }

        leaf ipCidrRouteMetric1 {
          type int32;
          description
           "The primary routing  metric  for  this  route.
            The  semantics of this metric are determined by
            the routing-protocol specified in  the  route's
            ipCidrRouteProto  value.   If  this metric is not
            used, its value should be set to -1.";
          smiv2:defval "-1";
          smiv2:max-access "read-write";
          smiv2:oid "1.3.6.1.2.1.4.24.4.1.11";
        }

        leaf ipCidrRouteMetric2 {
          type int32;
          description
           "An alternate routing metric  for  this  route.
            The  semantics of this metric are determined by
            the routing-protocol specified in  the  route's
            ipCidrRouteProto  value.   If  this metric is not
            used, its value should be set to -1.";
          smiv2:defval "-1";
          smiv2:max-access "read-write";
          smiv2:oid "1.3.6.1.2.1.4.24.4.1.12";
        }

        leaf ipCidrRouteMetric3 {
          type int32;
          description
           "An alternate routing metric  for  this  route.
            The  semantics of this metric are determined by
            the routing-protocol specified in  the  route's
            ipCidrRouteProto  value.   If  this metric is not
            used, its value should be set to -1.";
          smiv2:defval "-1";
          smiv2:max-access "read-write";
          smiv2:oid "1.3.6.1.2.1.4.24.4.1.13";
        }

        leaf ipCidrRouteMetric4 {
          type int32;
          description
           "An alternate routing metric  for  this  route.
            The  semantics of this metric are determined by
            the routing-protocol specified in  the  route's
            ipCidrRouteProto  value.   If  this metric is not
            used, its value should be set to -1.";
          smiv2:defval "-1";
          smiv2:max-access "read-write";
          smiv2:oid "1.3.6.1.2.1.4.24.4.1.14";
        }

        leaf ipCidrRouteMetric5 {
          type int32;
          description
           "An alternate routing metric  for  this  route.
            The  semantics of this metric are determined by
            the routing-protocol specified in  the  route's
            ipCidrRouteProto  value.   If  this metric is not
            used, its value should be set to -1.";
          smiv2:defval "-1";
          smiv2:max-access "read-write";
          smiv2:oid "1.3.6.1.2.1.4.24.4.1.15";
        }

        leaf ipCidrRouteStatus {
          type snmpv2-tc:RowStatus;
          description
           "The row status variable, used according to
            row installation and removal conventions.";
          smiv2:max-access "read-write";
          smiv2:oid "1.3.6.1.2.1.4.24.4.1.16";
        }
      }
    }
  }

  smiv2:alias "ipForward" {
    smiv2:oid "1.3.6.1.2.1.4.24";
  }

  smiv2:alias "ipForwardConformance" {
    smiv2:oid "1.3.6.1.2.1.4.24.5";
  }

  smiv2:alias "ipForwardGroups" {
    smiv2:oid "1.3.6.1.2.1.4.24.5.1";
  }

  smiv2:alias "ipForwardCompliances" {
    smiv2:oid "1.3.6.1.2.1.4.24.5.2";
  }

}
