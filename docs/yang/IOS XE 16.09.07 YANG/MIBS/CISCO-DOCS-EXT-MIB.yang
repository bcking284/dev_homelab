/*
 * Generated by confdc --mib2yang-std
 * Source: mgmt/dmi/model/mib/src/CISCO-DOCS-EXT-MIB.mib
 */
/*
 * This YANG module has been generated by smidump 0.5.0:
 *
 *      smidump -f yang CISCO-DOCS-EXT-MIB
 *
 * Do not edit. Edit the source file instead!
 */

module CISCO-DOCS-EXT-MIB {

  namespace "urn:ietf:params:xml:ns:yang:smiv2:CISCO-DOCS-EXT-MIB";
  prefix CISCO-DOCS-EXT-MIB;

  import DOCS-IF-MIB {
    prefix "docs-if";
  }

  import DOCS-IF3-MIB {
    prefix "docs-if3";
  }

  import IF-MIB {
    prefix "if-mib";
  }

  import INET-ADDRESS-MIB {
    prefix "inet-address";
  }

  import SNMP-FRAMEWORK-MIB {
    prefix "snmp-framework";
  }

  import SNMP-TARGET-MIB {
    prefix "snmp-target";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "        Cisco Systems
    Customer Service
    
    Postal: Cisco Systems
    170 West Tasman Drive
    San Jose, CA 95134
    U.S.A.
    Phone:  +1 800 553-NETS 
    E-mail: cs-ubr@cisco.com";

  description
   "This is the MIB module for the Cisco specific extension 
    objects of Data Over Cable Service, Radio Frequency 
    interface.  There is a standard MIB for Data-Over-Cable 
    Service Interface Specifications (DOCSIS) and in Cisco,
    it is called DOCS-IF-MIB. Besides the objects in 
    DOCS-IF-MIB, this MIB module contains the extension 
    objects to manage the Cable Modem Termination Systems 
    (CMTS).
    
    This MIB module includes objects for the scheduler 
    that supports Quality of Service (QoS) of MCNS/DOCSIS 
    compliant Radio Frequency (RF) interfaces in Cable Modem 
    Termination Systems (CMTS). And the purpose is to let 
    users configure attributes of the schedulers in 
    order to ensure the Quality of Service and fairness for 
    modem requests according to users' business needs. 
    Also this MIB shows various states of the schedulers 
    for users to monitor of the schedulers' current status. 
    
    This MIB module also includes connection status objects
    for cable modems and Customer Premise Equipment (CPE) 
    and the purpose is to let users easily get the connection 
    status and manage access group information about cable 
    modems and CPE.
    
    This MIB module also includes objects for upstream 
    configuration for automated spectrum management in 
    order to mitigate upstream impairment.
    
    This MIB module also includes objects to keep count of
    the total # of modems, # of registered and # of active
    modems on the mac interface as well as each 
    upstream. 
    
    Glossary:
    BE       Best Effort
    
    CPE      Customer Premise Equipment
    
    CM       Cable Modem
    
    CMTS     Cable Modem Termination Systems
    
    DMIC     Dynamic Message Integrity Check
    
    DOCSIS   Data Over Cable Service Interface Specifications
    
    IE       Information Element
    
    NIC      Network Interface Card
    
    QoS      Quality of Service
    
    RF       Radio Frequency
    
    RTPS     Real-Time Polling Service
    
    SFID     Service Flow ID
    
    SID      Service Id
    
    TOD      Time of the Day
    
    UGS      Unsolicited Grant Service
    
    UGS-AD   Unsolicited Grant Service with Activity Detection";

  revision 2017-11-10 {
    description
     "Modified index of cdxBundleIpHelperTable
      and cdxBundleIPv6DHCPRelayDestTable";
  }

  revision 2017-07-20 {
    description
     "Modified cdxCmtsCmOnOffNotification, use 
      docsIfCmtsCmStatusInetAddressType and
      docsIfCmtsCmStatusInetAddress to replace
      the deprecated docsIfCmtsCmStatusIpAddress";
  }

  revision 2017-02-18 {
    description
     "Added following tables:
      cdxBundleIpHelperTable
      cdxBundleIPv6DHCPRelayTable
      cdxBundleIPv6DHCPRelayDestTable";
  }

  revision 2016-06-08 {
    description
     "[Revision added by libsmi due to a LAST-UPDATED clause.]";
  }

  revision 2016-06-08 {
    description
     "Added the cdxWBResilCmTable;
      Added the following notifications:
      cdxWBResilUsPartialServiceNotif
      cdxWBResilUsFullServiceNotif";
  }

  revision 2013-12-10 {
    description
     "Added following OBJECT-GROUP:
      cdxCmtsD30LBGroup";
  }

  revision 2013-03-27 {
    description
     "Added following tables:
      cdxCpeIpPrefixTable
      cdxCmtsMtcCmTable
      cdxCmtsUscbSflowTable
      Added following OBJECT-GROUPs:
      cdxCpeIpPrefixGroup
      cdxCmtsMtcCmGroup
      cdxCmtsUscbSflowGroup";
  }

  revision 2012-09-07 {
    description
     "Add the following mib groups:
      cdxWBResilGroup, cdxNotifGroupExt, cdxQosCtrlGroupExt, 
      cdxDownstreamGroup";
  }

  revision 2010-06-09 {
    description
     "Add new object cdxCmCpeDeleteNow to cdxCmCpeTable to delete the
      cable modems.";
  }

  revision 2006-03-06 {
    description
     "Following tables are added.
      
      cdxCmToCpeTable
      cdxCpeToCmTable
      
      These are used for the direct correlation between
      Cable Modem and Customer Premises Equipment.";
  }

  revision 2005-07-01 {
    description
     "Modified the description of cdxCmtsServiceExtEntry.
      Modified the value of lockingMode from 2 to 3. ";
  }

  revision 2005-04-25 {
    description
     "Modified dxCmtsCmDefaultMaxCpes' lower range from 0
      to -1.";
  }

  revision 2004-07-22 {
    description
     "Modified dxCmtsCmDefaultMaxCpes' lower range from 0
      to -1.";
  }

  revision 2003-07-30 {
    description
     "Added new objects for supporting DMIC. The objects are
      cdxCmtsCmDMICMode, cdxCmtsCmDMICLockQos and a new table
      cdxCmtsCmStatusDMICTable. Also, one more trap,
      cdxCmtsCmDMICLockNotification is added. Two more states
      were added to cdxCmtsCmStatusValue.";
  }

  revision 2003-02-20 {
    description
     "Added new object cdxCmtsCmQosProfile to cdxCmtsCmTable to 
      associate a cable modem with a qos profile.";
  }

  revision 2002-10-11 {
    description
     "Added new object cdxCmtsCmQosProfile to cdxCmtsCmTable to 
      associate a cable modem with a qos profile.";
  }

  revision 2001-10-07 {
    description
     "Added new objects cdxIfCmtsCmStatusOnlineTimesNum and
      cdxIfCmtsCmStatusLastResetTime to 
      cdxCmtsCmStatusExtTable. ";
  }

  revision 2001-08-06 {
    description
     "DOCSIS 1.1 Changes:
      Added new objects cdxIfUpChannelAvgUtil, 
      cdxIfUpChannelAvgContSlots, 
      cdxIfUpChannelRangeSlots in 
      cdxIfUpstreamChannelExtTable. 
      
      NON-DOCSIS 1.1 Changes:
      Added following objects in cdxIfUpstreamChannelExtTable 
      for providing per upstream UGS statistics information:
      cdxIfUpChannelNumActiveUGS,
      cdxIfUpChannelMaxUGSLastOneHour, 
      cdxIfUpChannelMinUGSLastOneHour,
      cdxIfUpChannelAvgUGSLastOneHour, 
      cdxIfUpChannelMaxUGSLastFiveMins,
      cdxIfUpChannelMinUGSLastFiveMins, 
      cdxIfUpChannelAvgUGSLastFiveMins. ";
  }

  revision 2001-04-01 {
    description
     "DOCSIS 1.1 Changes:
      1.  Added  cdxUpInfoElemStatsTable to display the per 
      Information Element (IE) statistics.
         
      2. Added the new queue types in cdxBWQueueNameCode to 
      support the new priority queues of the MAC-Scheduler.
      
      3. Added the new CM states in cdxCmtsCmStatusValue.
      
      Non-DOCSIS 1.1 changes:
      4. Added new status information for CM if the connection
      is noisy or if the maximum power has been reached.
      
      5. Changed the Description for cdxIfUpChannelWidth to
      cater for non-awacs card.
      
      6. Added new object cdxIfUpChannelInputPowerLevel for
      Upstream Input Power Level. ";
  }

  revision 2000-07-19 {
    description
     "1.  Added  cdxCmtsCmTotal,cdxCmtsCmActive,
      cdxCmtsCmRegistered to the cdxCmtsMacExtTable to report 
      the number of active,registered,total cable 
      modems on a cable mac interface since boot.
      
      2.  Added cdxIfUpChannelCmTotal, cdxIfUpChannelCmActive,
      cdxIfUpChannelCmRegistered to the 
      cdxIfUpstreamChannelExtTable to report the number of 
      active,registered,total cable modems connected on an 
      upstream.";
  }

  revision 2000-05-17 {
    description
     "1.  Added cdxCmCpeResetNow to reset CM or CPE.
      2.  Added cdxCmtsCmCurrCpeNumber to report the current
      number of CPE connecting to the CM.";
  }

  revision 1999-12-28 {
    description
     " 1. Added new objects cdxSpecMgmtObjects. 
      2. Added new object cdxIfCmtsCmStatusDynSidCount. 
      3. Enhanced cdxQosIfRateLimitTable for a new rate limit 
         algorithm.
      4. Added more status for cdxCmtsCmStatusValue. ";
  }

  revision 1999-01-21 {
    description
     "Initial version of this MIB module.";
  }

  typedef CdxResettableCounter32 {
    type yang:gauge32;
    description
     "This TC describes an object which counts events with the 
      following semantics: objects of this type will be set to
      zero(0) on creation or reset indirectly by other objects or
      certain event and will thereafter count appropriate events,
      wrapping back to zero(0) when the value 2^32 is reached.
      
      Provided that an application discovers the new object within
      the minimum time to wrap it can use the initial value as a
      delta since it last polled the table of which this object is
      part.
      
      Typically this TC is used in table where the statistical 
      information needs to be re-count after a reset. ";
  }

  typedef CdxUpstreamBondGrpList {
    type string;
    description
     "This data type is a human-readable string that represents
      the upstream bonding group list within a MAC Domain.
      When there is no upstream bonding group in a MAC Domain, it
      will be empty.";
    smiv2:display-hint "320a";
  }


  container CISCO-DOCS-EXT-MIB {
    config false;

    container cdxCmtsCmCpeObjects {
      smiv2:oid "1.3.6.1.4.1.9.9.116.1.3";

      leaf cdxCmtsCmChOverTimeExpiration {
        type int32 {
          range "1..86400";
        }
        units "minutes";
        description
         "The time period to expire a CMTS channel override operation. 
          Within the time period, if the CMTS cannot send out a 
          RNG-RSP message with channel override fields to a cable 
          modem specified in the operation, the CMTS will abort 
          the operation. The possible reason is that the cable 
          modem does not repeat the initial ranging. 
          
          The change to this object will not affect the already active 
          operations in this cdxCmtsCmChOverTable.   
           
          Once the operation completes, the management station should
          retrieve the values of the cdxCmtsCmChOverState 
          object of interest, and should then delete the entry
          from cdxCmtsCmChOverTable.  In order to prevent old 
          entries from clogging the table, entries will be aged out, 
          but an entry will never be deleted within 15 minutes of 
          completing. ";
        reference
         "Data-Over-Cable Service Interface Specifications (DOCSIS)
          Radio Frequency Interface Specification (SP-RFI-I04-980724),
          6.3.2.5.3 Overriding Channels. ";
        smiv2:max-access "read-write";
        smiv2:oid "1.3.6.1.4.1.9.9.116.1.3.4";
      }
    }

    container cdxWBResilObjects {
      smiv2:oid "1.3.6.1.4.1.9.9.116.1.5";

      leaf cdxWBResilRFChangeDampenTime {
        type int32 {
          range "1..65535";
        }
        units "Second";
        description
         "This object specifies the amount of time an RF channel must
          remain in its new state, either UP or DOWN, before the
          transition is considered valid.  This value applies to all
          non-primary RF channels in the CMTS.";
        smiv2:defval "30";
        smiv2:max-access "read-write";
        smiv2:oid "1.3.6.1.4.1.9.9.116.1.5.1";
      }

      leaf cdxWBResilRFChangeTriggerPercentage {
        type int32 {
          range "0..100";
        }
        units "Percentage";
        description
         "This object specifies the percentage of cable modems (CMs) that
          must report that a particular Non Primary RF channel is DOWN,
          before that channel is removed from any/all bonding groups
          with that Non Primary RF channel configured. The value of 0
          will prevent from any bonding group modifications. In order to
          dampen state's changes for an RF channel, the trigger for 
          a channel being restored is one half of this object's value. ";
        smiv2:defval "0";
        smiv2:max-access "read-write";
        smiv2:oid "1.3.6.1.4.1.9.9.116.1.5.2";
      }

      leaf cdxWBResilRFChangeTriggerCount {
        type int32 {
          range "0..65535";
        }
        description
         "This object specifies the count of cable modems (CMs) that
          must report that a particular Non Primary RF channel is DOWN,
          before that channel is removed from any/all bonding groups
          with that Non Primary RF channel configured. The value of 0
          will prevent from any bonding group modifications. In order to
          dampen state's changes for an RF channel, the trigger for 
          a channel being restored is one half of this object's value.";
        smiv2:defval "0";
        smiv2:max-access "read-write";
        smiv2:oid "1.3.6.1.4.1.9.9.116.1.5.3";
      }

      leaf cdxWBResilRFChangeTriggerMoveSecondary {
        type boolean;
        description
         "This object specifies whether the secondary service flows are
          allowed to be moved and created on the narrowband interface.";
        smiv2:defval "false";
        smiv2:max-access "read-write";
        smiv2:oid "1.3.6.1.4.1.9.9.116.1.5.4";
      }

      leaf cdxWBResilNotificationEnable {
        type bits {
          bit event {
            position "0";
          }
          bit cm-recover {
            position "1";
          }
          bit cm-pmode {
            position "2";
          }
          bit rf-up {
            position "3";
          }
          bit rf-down {
            position "4";
          }
          bit us-resil-recover {
            position "5";
          }
          bit us-resil-pmode {
            position "6";
          }
        }
        description
         "An indication of whether the cdxWBResilRFDown, cdxWBResilRFUp, 
          cdxWBResilCMPartialServiceNotif, cdxWBResilCMFullServiceNotif, 
          cdxWBResilEvent, cdxWBResilUsFullServiceNotif
          and cdxWBResilUsPartialServiceNotif are enabled.";
        smiv2:defval "{}";
        smiv2:max-access "read-write";
        smiv2:oid "1.3.6.1.4.1.9.9.116.1.5.5";
      }

      leaf cdxWBResilNotificationsInterval {
        type int32 {
          range "0..86400";
        }
        units "Second";
        description
         "This object specifies the interval that cdxWBResilEvent traps 
          could be sent per cable modem. It is to avoid too many cdxWBResilEvent
          traps sent for a cable modem during a short period of time.
          The default value is 1 (second). If the value is 0, the trap 
          cdxWBResilEvent will be sent for every wideband resiliency event.
          If the value is set to any value greater than 0, for the wideband 
          resiliency events which occurred in the same specific period of time, 
          the CMTS will send only one trap.";
        smiv2:defval "1";
        smiv2:max-access "read-write";
        smiv2:oid "1.3.6.1.4.1.9.9.116.1.5.6";
      }
    }

    container cdxCmtsDocsisLBObjects {
      smiv2:oid "1.3.6.1.4.1.9.9.116.1.8";

      leaf cdxCmtsDocsisLBEnable {
        type enumeration {
          enum "true" {
            value "1";
          }
          enum "false" {
            value "2";
          }
        }
        description
         "This is a cisco private object. Setting this object to true(1)
          enables d2.0 loadbalancing on CMTS and allows user to further
          config other options for d3.0 loadbalancing(cdxCmtsD30LBEnable,
          cdxCmtsD30LBUpstreamEnable cdxCmtsD30LBStaticEnable 
          		and cdxCmtsD30LBDynEnable). 
          Setting it to false(2) disables all oad balancing operations.";
        smiv2:defval "false";
        smiv2:max-access "read-write";
        smiv2:oid "1.3.6.1.4.1.9.9.116.1.8.1";
      }

      leaf cdxCmtsD30LBEnable {
        type enumeration {
          enum "true" {
            value "1";
          }
          enum "false" {
            value "2";
          }
        }
        description
         "Setting this object to true(1) enables d3.0 static
          loadbalancing on CMTS and allows user to further config other
          objects for d3.0 loadbalancing(cdxCmtsD30LBUpstreamEnable and
          cdxCmtsD30LBStaticEnable and cdxCmtsD30LBDynEnable) .
          Setting it to false(2) disables d3.0 loadbalancing.";
        smiv2:defval "false";
        smiv2:max-access "read-write";
        smiv2:oid "1.3.6.1.4.1.9.9.116.1.8.2";
      }

      leaf cdxCmtsD30LBUpstreamEnable {
        type enumeration {
          enum "true" {
            value "1";
          }
          enum "false" {
            value "2";
          }
        }
        description
         "Setting this object to true(1) enables upstream loadbalancing
          in docsis 3.0 static loadbalancing. Default is false(2).Only
          if docsis-enable and docsis30-enable set to true can this object
          take effect.";
        smiv2:defval "false";
        smiv2:max-access "read-write";
        smiv2:oid "1.3.6.1.4.1.9.9.116.1.8.3";
      }

      leaf cdxCmtsD30LBStaticEnable {
        type enumeration {
          enum "true" {
            value "1";
          }
          enum "false" {
            value "2";
          }
        }
        description
         "Setting this to true(1) enables autonomous D30 LB to move
          wideband modems if LB group is not in a balancing state.Default
          is false(2).
          Only if docsis-enable and docsis30-enable is set to true can
          this object set to true(1)";
        smiv2:defval "false";
        smiv2:max-access "read-write";
        smiv2:oid "1.3.6.1.4.1.9.9.116.1.8.4";
      }

      leaf cdxCmtsD30LBDynEnable {
        type enumeration {
          enum "true" {
            value "1";
          }
          enum "false" {
            value "2";
          }
        }
        description
         "Setting this to true(1) enables autonomous D30 LB to move
          wideband modems if LB group is not in a balancing state.Default
          is false(2).
          Only if docsis-enable and docsis30-enable is set to true can
          this object set to true(1)";
        smiv2:defval "false";
        smiv2:max-access "read-write";
        smiv2:oid "1.3.6.1.4.1.9.9.116.1.8.5";
      }
    }

    container cdxQosCtrlUpTable {
      description
       "For each upstream interface, this table maintains a number 
        of objects related to Quality of Service scheduler which uses
        these attributes to control cable modem registration. ";
      smiv2:oid "1.3.6.1.4.1.9.9.116.1.1.1";

      list cdxQosCtrlUpEntry {
        key "ifIndex";
        description
         "A list of attributes for each upstream MAC scheduler 
          that supports Quality of Service.  Entries in this table
          exist for each ifEntry with ifType of docsCableUpstream(129). ";
        reference
         "Data-Over-Cable Service Interface Specifications (DOCSIS)
          Radio Frequency Interface Specification (SP-RFI-I04-980724), 
          section 6.4 and appendix C.
          
          docsIfQosProfileTable and docsIfCmtsServiceTable in 
          DOCS-IF-MIB.my. ";
        smiv2:oid "1.3.6.1.4.1.9.9.116.1.1.1.1";

        leaf ifIndex {
          type leafref {
            path "/if-mib:IF-MIB/if-mib:ifTable/if-mib:ifEntry/if-mib:ifIndex";
          }
        }

        leaf cdxQosCtrlUpAdmissionCtrl {
          type boolean;
          description
           "The admission control status for minimum guaranteed upstream 
            bandwidth scheduling service requests for this upstream.
            
            When this object is set to 'true', if there is a new modem 
            with minimum guaranteed upstream bandwidth scheduling service
            in its QoS class requesting to be supported in this upstream,
            the upstream scheduler will check the virtual reserved 
            bandwidth remaining capacity before giving admission to this 
            new modem. If there is not enough reserved upstream bandwidth
            to serve the modem's minimum guaranteed bandwidth, the 
            registration request will be rejected.  
            
            This object is set to 'false' to disable admission control.
            That is, there will be no checking for bandwidth capacity and
            the upstream interface scheduler just admits modem
            registration requests. 
            
            This object is not meant for Unsolicited Grant Service(UGS) 
            scheduling service as admission control is a requirement in 
            this case. ";
          smiv2:max-access "read-write";
          smiv2:oid "1.3.6.1.4.1.9.9.116.1.1.1.1.1";
        }

        leaf cdxQosCtrlUpMaxRsvdBWPercent {
          type int32 {
            range "10..1000";
          }
          units "percent";
          description
           "The percentage of upstream maximum reserved bandwidth to the 
            raw bandwidth if the admission control is enabled on this 
            upstream. 
            
            For example, if the upstream interface has raw bandwidth 
            1,600,000 bits/second and cdxQosCtrlUpMaxRsvdBWPercent is 200 
            percent, then this upstream scheduler will set the maximum of 
            virtual reserved bandwidth capacity to 3,200,000 bits/second 
            (1,600,000 * 2) to serve cable modems with minimum guaranteed 
            upstream bandwidth.  
            
            The default value is 100 percent (that is, maximum reserved 
            bandwidth is the raw bandwidth.) Whenever the admission control 
            is changed (on to off, off to on), this value will be reset to 
            the default value 100.  
            
            If the admission control is disabled, the value will be reset 
            to 100 (the default value). ";
          smiv2:max-access "read-write";
          smiv2:oid "1.3.6.1.4.1.9.9.116.1.1.1.1.2";
        }

        leaf cdxQosCtrlUpAdmissionRejects {
          type yang:counter32;
          description
           "The count of cable modem registration requests rejected on 
            this upstream interface due to insufficient reserved 
            bandwidth for serving the cable modems with Unsolicited 
            Grant Service (UGS) scheduling service when UGS is 
            supported and for serving the cable modems with minimum 
            guaranteed bandwidth in its Quality of Service class when
            admission control is enabled on this upstream interface .";
          smiv2:max-access "read-only";
          smiv2:oid "1.3.6.1.4.1.9.9.116.1.1.1.1.3";
        }

        leaf cdxQosCtrlUpReservedBW {
          type int32 {
            range "0..102400000";
          }
          units "bits/second";
          description
           "The current total reserved bandwidth in bits per second of 
            this upstream interface.  It is the sum of all cable modems'
            minimum guaranteed bandwidth in bits per second currently 
            supported on this upstream. ";
          smiv2:max-access "read-only";
          smiv2:oid "1.3.6.1.4.1.9.9.116.1.1.1.1.4";
        }

        leaf cdxQosCtrlUpMaxVirtualBW {
          type int32 {
            range "0..102400000";
          }
          units "bits/second";
          description
           "The maximum virtual bandwidth capacity of this upstream interface
            if the admission control is enabled. It is the raw bandwidth 
            in bits per second times the percentage. If the admission 
            control is disabled, then this object will contain the value 
            zero. ";
          smiv2:max-access "read-only";
          smiv2:oid "1.3.6.1.4.1.9.9.116.1.1.1.1.5";
        }
      }
    }

    container cdxQosIfRateLimitTable {
      description
       "This table describes the attributes of rate limiting for 
        schedulers in cable upstream and downstream interfaces that 
        support Quality of Service.  The rate limiting process is 
        to ensure the Quality of Service and fairness. ";
      smiv2:oid "1.3.6.1.4.1.9.9.116.1.1.2";

      list cdxQosIfRateLimitEntry {
        key "ifIndex";
        description
         "List of the rate limiting attributes for cable upstream and 
          downstream interfaces schedulers that support Quality of 
          Service. Entries in this table exist for each ifEntry with 
          ifType of docsCableUpstream(129) and docsCableDownstream(128).";
        reference
         "Data-Over-Cable Service Interface Specifications (DOCSIS)
          Radio Frequency Interface Specification (SP-RFI-I04-980724),
          section 6.4 and appendix C.
          
          docsIfQosProfileTable and docsIfCmtsServiceTable in
          DOCS-IF-MIB.my. ";
        smiv2:oid "1.3.6.1.4.1.9.9.116.1.1.2.1";

        leaf ifIndex {
          type leafref {
            path "/if-mib:IF-MIB/if-mib:ifTable/if-mib:ifEntry/if-mib:ifIndex";
          }
        }

        leaf cdxQosIfRateLimitAlgm {
          type enumeration {
            enum "noRateLimit" {
              value "1";
            }
            enum "oneSecBurst" {
              value "2";
            }
            enum "carLike" {
              value "3";
            }
            enum "wtExPacketDiscard" {
              value "4";
            }
            enum "shaping" {
              value "5";
            }
          }
          description
           "To ensure fairness, the CMTS will throttle the rate for bandwidth 
            request (upstream)/packet sent (downstream) at which CMTS issues 
            grants(upstream) or allow packet to be send(downstream) such that 
            the flow never gets more than its provisioned peak rate in bps. 
            
            There are two directions for every Service Id (Sid) traffic: 
            downstream and upstream. Each direction is called a service flow 
            here and assigned one token bucket with chosen algorithm. 
            
            The enumerations for the rate limiting algorithm are:
             noRateLimit(1): The rate limiting is disabled. No rate limiting.
             oneSecBurst(2): Bursty 1 second token bucket algorithm.
             carLike(3)    : Average token usage (CAR-like) algorithm 
             wtExPacketDiscard(4) : Weighted excess packet discard algorithm.
             shaping(5): token bucket algorithm with shaping
            
            Upstream supports the following: 
              No rate limiting (1), 
              Bursty 1 second token bucket algorithm(2), 
              Average token usage (CAR-like) algorithm(3),
              Token bucket algorithm with shaping(5).
            
            Downstream supports the following:
              No rate limiting (1), 
              Bursty 1 second token bucket algorithm(2),
              Average token usage (CAR-like) algorithm(3),
              Weighted excess packet discard algorithm(4), and
              Token bucket algorithm with shaping(5).
            
            Token bucket algorithm with shaping is the
            default algorithm for upstream if CMTS is in DOCSIS 1.0 mode
            or DOCSIS 1.1 mode.
            
            
            Bursty 1 second token bucket algorithm is the 
            default algorithm for downstream if the CMTS is in
            DOCSIS 1.0 mode. If it is in DOCSIS 1.1 mode the default
            algorithm for downstream is  Token bucket algorithm with
            shaping .
            
            Each algorithm is described as below:
              No rate limiting: 
                The rate limiting process is disabled and no checking 
                against the maximum bandwidth allowed. 
            
              Bursty 1 second token bucket rate limiting algorithm: 
                In this algorithm, at the start of every 1 second interval, 
                a service flow's token usage is reset to 0, and every time 
                the modem for that service flow sends a request (upstream) / 
                packet (downstream) the upstream/downstream bandwidth 
                token usage is incremented by the size of the 
                request/packet sent. As long as the service flow's bandwidth 
                token usage is less than the maximum bandwidth in bits 
                per second (peak rate limit) its QoS service class 
                allows, the request/packets will not be restricted. 
                Once the service flow has sent more than its peak rate in the 
                one second interval, it is prevented from sending more 
                data by rejecting request (upstream) or dropping 
                packets (downstream). This is expected to slow down
                the higher layer sources. The token usage counter gets 
                reset to 0 after the 1 second interval has elapsed. The 
                modem for that service flow is free to send more data up to the 
                peak rate limit in the new 1 second interval that follows.  
            
              Average token usage (Cisco CAR like) algorithm: 
                This algorithm maintains a continuous average of the 
                burst token usage of a service flow. There is no sudden 
                refilling of tokens every 1 second interval. Every time a 
                request/packet is to be handled, the scheduler tries to see 
                how much time has elapsed since last transmission, and 
                computes the number of tokens accumulated by this service flow 
                at its QoS class peak rate. If burst usage of the service flow 
                is less than tokens accumulated, the burst usage is reset to 0 
                and request/packet is forwarded. If the service flow has 
                accumulated fewer tokens than its burst usage, the burst usage 
                shows an outstanding balance usage after decrementing by the 
                tokens accumulated. In such cases, the request/packet is still 
                forwarded, provided the service flow's outstanding usage does 
                not exceed peak rate limit of its QoS class. If outstanding 
                burst usage exceeds the peak rate of the class, the service 
                flow is given some token credit up to a certain maximum credit 
                limit and the request/packet is forwarded. The request/packet 
                is dropped when outstanding usage exceeds peak rate and maximum 
                credit has been used up by this service flow. This algorithm 
                tracks long term average bandwidth usage of the service flow 
                and controls this average usage at the peak rate limit.
            
              Weighted excess packet discard algorithm:
                This rate limiting algorithm is only available as an option 
                for downstream rate limiting. The algorithm is to maintain an 
                weighted exponential moving average of the loss rate of a 
                service flow over time. The loss rate, expressed in packets, 
                represents the number of packets that can be sent from this 
                service flow in a one second interval before a packet will 
                be dropped. At every one second interval, the loss rate gets 
                updated using the ratio between the flow peak rate (in bps) 
                in its QoS profile and the service flow actual usage (in bps). 
                If the service flow begins to send more than its peak rate 
                continuously, the number of packets it can send in an one 
                second interval before experiencing a drop will slowly keep 
                reducing until cable modem for that service flow slows down 
                as indicated by actual usage less or equal to the peak rate. 
            
              Token bucket algorithm with shaping:
                 If there is no QoS class peak rate limit, forward the 
                 request/packet without delay. If there is a QoS peak rate 
                 limit, every time a request/packet is to be handled, the 
                 scheduler determines the number of bandwidth tokens that this 
                 service flow has accumulated over the elapsed time at its 
                 QoS class peak rate and increments the tokens counter of the 
                 service flow accordingly.  The scheduler limits the token 
                 count to the maximum transmit burst (token bucket depth).  
                 If token count is greater than the number of tokens required 
                 to handle current request/packet, decrement token count by 
                 size of request/packet and forwards the request/packet 
                 without delay.  If token count is less than the size of 
                 request/packet, compute the shaping delay time after 
                 which the deficit number of tokens would be available. If 
                 shaping delay time is less than the maximum shaping delay, 
                 decrement tokens count by size of request/packet and 
                 forward this request/packet with the shaping delay in the 
                 shaping delay queue. When the delay time expires, the 
                 request/packet is forwarded. If shaping delay time is 
                 greater than the maximum shaping delay that the subsequent 
                 shaper can handle, the request/packet is dropped. Users can
                 use cdxQosIfRateLimitShpMaxDelay to configure the the maximum 
                 shaping delay and cdxQosIfRateLimitShpGranularity to 
                 configure the shaping granularity.  ";
          smiv2:max-access "read-write";
          smiv2:oid "1.3.6.1.4.1.9.9.116.1.1.2.1.1";
        }

        leaf cdxQosIfRateLimitExpWt {
          type int32 {
            range "1..4";
          }
          description
           "Weight for exponential moving average of loss rate for 
            weighted excess packet discard algorithm to maintain.
            The higher value of the weight makes the algorithm
            more sensitive to the recent bandwidth usage by the Sid. 
            
            The default value is 1 and whenever the rate limiting
            algorithm is changed to weighted excess packet discard 
            algorithm, this value will be reset to the default 1.
            
            If the rate limiting algorithm is not weighted excess 
            packet discard algorithm, the value will be always the 
            default value 1. ";
          smiv2:max-access "read-write";
          smiv2:oid "1.3.6.1.4.1.9.9.116.1.1.2.1.2";
        }

        leaf cdxQosIfRateLimitShpMaxDelay {
          type enumeration {
            enum "na" {
              value "1";
            }
            enum "msec128" {
              value "2";
            }
            enum "msec256" {
              value "3";
            }
            enum "msec512" {
              value "4";
            }
            enum "msec1024" {
              value "5";
            }
          }
          description
           "The maximum shaping delay in milliseconds. That is, the maximum 
            amount time of buffering the CMTS will allow for any rate exceeded 
            flow.  If the max buffering delay is large, the grants/packets of 
            the flow will be buffered for a longer period of time even though 
            the flow is rate exceeded. This means fewer chances of drops for
            such rate exceeded flow. However, too large a max shaping delay 
            can result is quick drainage of packet buffers at the CMTS, since 
            several packets will be in the shaping (delay) queue waiting for 
            their proper transmission time. Another important point to be noted 
            is that delaying a flows packets (especially TCP flows) for 
            extended periods of time is useless, since the higher protocol 
            layers may assume a packet loss after a certain amount of time.
            
            The maximum shaping delay is only applied to rate limit algorithm: 
            Token bucket algorithm with shaping.  If the rate limit 
            algorithm is not Token bucket algorithm with shaping, the 
            value is always na(1) which is not applicable.
            
            If the token count is less than the size of request/packet, CMTS 
            computes the shaping delay time after which the deficit number of 
            tokens would be available. If the shaping delay time is greater 
            than the maximum shaping delay, the request/packet will be dropped.  
            
            The enumerations for maximum shaping delay are:
              na(1): maximum shaping delay is not applied to the current 
                     rate limit algorithm
             msec128(2): maximum shaping delay is 128 milliseconds  
             msec256(3): maximum shaping delay is 256 milliseconds 
             msec512(4): maximum shaping delay is 512 milliseconds 
            msec1024(5): maximum shaping delay is 1024 milliseconds 
            
            The downstream maximum shaping delay is configurable and the
            default value is msec128(2). Whenever the downstream rate 
            limit algorithm is changed to Token bucket algorithm with 
            shaping from other rate limit algorithm, the value will 
            be reset to the default value. 
            
            The upstream maximum shaping delay is not configurable and it 
            is read-only value.  ";
          smiv2:max-access "read-write";
          smiv2:oid "1.3.6.1.4.1.9.9.116.1.1.2.1.3";
        }

        leaf cdxQosIfRateLimitShpGranularity {
          type enumeration {
            enum "na" {
              value "1";
            }
            enum "msec1" {
              value "2";
            }
            enum "msec2" {
              value "3";
            }
            enum "msec4" {
              value "4";
            }
            enum "msec8" {
              value "5";
            }
            enum "msec16" {
              value "6";
            }
          }
          description
           "The width in milliseconds of each element in shaping 
            delay queue, that is, the shaping granularity.
            
            The shaping granularity is only applied to rate limit
            algorithm: Token bucket algorithm with shaping. It 
            controls how accurately the algorithm quantizes the shaping 
            delay for a rate exceeded flow. If granularity is large, several 
            shaping delay values will all be quantized to the same element 
            in the queue resulting in less accurate rate shaping for the flows 
            in bits/sec. On the other hand, choosing too small granularity 
            causes more memory to be used for the shaper block, and also 
            can cost a bit more in runtime overhead.
            
            If the rate limit algorithm is not Token bucket algorithm with 
            shaping, the value is always na(1) which is not applicable.
            
            The enumerations for shaping granularity are:
              na(1): shaping granularity is not applied to the current 
                     rate limit algorithm
               msec1(2): shaping granularity in 1 milliseconds 
               msec2(3): shaping granularity in 2 milliseconds 
               msec4(4): shaping granularity in 4 milliseconds 
               msec8(5): shaping granularity in 8 milliseconds 
              msec16(6): shaping granularity in 16 milliseconds  
            
            The downstream shaping granularity is configurable and the
            default value is msec4(4). Whenever the downstream rate limit 
            algorithm is changed to Token bucket algorithm with shaping 
            from other rate limit algorithm, the value will be reset to the 
            default value. 
            
            The upstream shaping granularity is not configurable and 
            it is read-only value.  ";
          smiv2:max-access "read-write";
          smiv2:oid "1.3.6.1.4.1.9.9.116.1.1.2.1.4";
        }
      }
    }

    container cdxCmtsServiceExtTable {
      description
       "The list contains the additional attributes of a single Service
        ID that provided by docsIfCmtsServiceEntry. ";
      smiv2:oid "1.3.6.1.4.1.9.9.116.1.1.3";

      list cdxCmtsServiceExtEntry {
        key "ifIndex docsIfCmtsServiceId";
        description
         "Additional objects for docsIfCmtsServiceTable entry including 
          downstream traffic statistics and excess counts against the 
          Quality of Service limits for each Service ID.
          From DOCSIS 1.1 onwards statistics are maintained for each 
          Service Flow(instead of the Service ID) in the DOCS-QOS-MIB 
          in docsQosServiceFlowStatsTable objects. For Cable modems
          not running in DOCSIS 1.0 mode, the objects  
          cdxIfCmtsServiceOutOctets and cdxIfCmtsServiceOutPackets
          will only support primary service flow. ";
        reference
         "Data-Over-Cable Service Interface Specifications (DOCSIS)
          Radio Frequency Interface Specification (SP-RFI-I04-980724),
          section 6.4 and appendix C.
          
          docsIfQosProfileTable and docsIfCmtsServiceTable in
          DOCS-IF-MIB.my. ";
        smiv2:oid "1.3.6.1.4.1.9.9.116.1.1.3.1";

        leaf ifIndex {
          type leafref {
            path "/if-mib:IF-MIB/if-mib:ifTable/if-mib:ifEntry/if-mib:ifIndex";
          }
        }

        leaf docsIfCmtsServiceId {
          type leafref {
            path "/docs-if:DOCS-IF-MIB/docs-if:docsIfCmtsServiceTable/docs-if:docsIfCmtsServiceEntry/docs-if:docsIfCmtsServiceId";
          }
        }

        leaf cdxIfCmtsServiceOutOctets {
          type yang:counter32;
          description
           "The cumulative number of Packet Data octets sent for this 
            Service ID. ";
          smiv2:max-access "read-only";
          smiv2:oid "1.3.6.1.4.1.9.9.116.1.1.3.1.1";
        }

        leaf cdxIfCmtsServiceOutPackets {
          type yang:counter32;
          description
           "The cumulative number of Packet data packets sent for this 
            Service ID. ";
          smiv2:max-access "read-only";
          smiv2:oid "1.3.6.1.4.1.9.9.116.1.1.3.1.2";
        }

        leaf cdxQosMaxUpBWExcessRequests {
          type yang:counter32;
          description
           "The number of upstream bandwidth requests which exceeds the
            maximum upstream bandwidth allowed for a service defined 
            in the Quality of Service profile associated with this Sid. 
            The request which exceeds the maximum upstream bandwidth 
            allowed will be rejected by the upstream's rate limiting 
            process using one of the rate limiting algorithm. 
            
            Note that the value of this counter cannot be directly used 
            to know the number of upstream packets that got dropped at 
            the cable modem.  A single upstream packet drop of a modem 
            can result in up to 16 increments in this counter, since the 
            modem keeps retrying and keeps getting bandwidth request 
            drops at CMTS if it has consumed its peak rate.  ";
          reference
           "docsIfQosProfMaxUpBandwidth object in DOCS-IF-MIB.my. ";
          smiv2:max-access "read-only";
          smiv2:oid "1.3.6.1.4.1.9.9.116.1.1.3.1.3";
        }

        leaf cdxQosMaxDownBWExcessPackets {
          type yang:counter32;
          description
           "The number of downstream bandwidth packets which exceeds the
            maximum downstream bandwidth allowed for a service defined
            in the Quality of Service profile associated with this Sid. 
            The packet which exceeds the maximum downstream bandwidth 
            allowed will be dropped by the downstream's rate limiting 
            process using one of the rate limiting algorithm. ";
          reference
           "docsIfQosProfMaxDownBandwidth object in DOCS-IF-MIB.my. ";
          smiv2:max-access "read-only";
          smiv2:oid "1.3.6.1.4.1.9.9.116.1.1.3.1.4";
        }

        leaf cdxIfCmtsServiceHCInOctets {
          type yang:counter64;
          description
           "The cumulative number of Packet Data octets received on this
            Service ID. The count does not include the size of the Cable
            MAC header. This object is a 64-bit version of
            docsIfCmtsServiceInOctets.";
          smiv2:max-access "read-only";
          smiv2:oid "1.3.6.1.4.1.9.9.116.1.1.3.1.5";
        }

        leaf cdxIfCmtsServiceHCInPackets {
          type yang:counter64;
          description
           "The cumulative number of Packet Data packets received on this
            Service ID. This object is a 64-bit version of
            docsIfCmtsServiceInPackets.";
          smiv2:max-access "read-only";
          smiv2:oid "1.3.6.1.4.1.9.9.116.1.1.3.1.6";
        }

        leaf cdxIfCmtsServiceHCOutOctets {
          type yang:counter64;
          description
           "The cumulative number of Packet Data octets sent for this
            Service ID. This object is a 64-bit version of
            cdxIfCmtsServiceOutOctets.";
          smiv2:max-access "read-only";
          smiv2:oid "1.3.6.1.4.1.9.9.116.1.1.3.1.7";
        }

        leaf cdxIfCmtsServiceHCOutPackets {
          type yang:counter64;
          description
           "The cumulative number of Packet Data packets sent for this
            Service ID. This object is a 64-bit version of
            cdxIfCmtsServiceOutPackets.";
          smiv2:max-access "read-only";
          smiv2:oid "1.3.6.1.4.1.9.9.116.1.1.3.1.8";
        }
      }
    }

    container cdxUpInfoElemStatsTable {
      description
       "The table contains the attributes of a particular 
        Information Element type for each instance of the MAC 
        scheduler. It is indexed by upstream ifIndex. An Entry
        exists for each ifEntry with ifType of docsCableUpstream(129)
        Since each upstream has an instance of a MAC Scheduler so 
        this table has the per MAC scheduler slot information on a
        per Information Element basis. ";
      smiv2:oid "1.3.6.1.4.1.9.9.116.1.1.4";

      list cdxUpInfoElemStatsEntry {
        key "ifIndex cdxUpInfoElemStatsNameCode";
        description
         "The list of statistics for a type of Information Element(IE)
          which defines the allowed usage for a range of upstream mini
          slots. One entry exists for each Information Element (IE) in
          a upstream which ifType is docsCableUpstream (12).";
        reference
         "Data-Over-Cable Service Interface Specifications (DOCSIS)
          Radio Frequency Interface Specification (SP-RFI-I05-000714)
          section 7.1.2 ";
        smiv2:oid "1.3.6.1.4.1.9.9.116.1.1.4.1";

        leaf ifIndex {
          type leafref {
            path "/if-mib:IF-MIB/if-mib:ifTable/if-mib:ifEntry/if-mib:ifIndex";
          }
        }

        leaf cdxUpInfoElemStatsNameCode {
          type enumeration {
            enum "reqIE" {
              value "1";
            }
            enum "reqOrDataIE" {
              value "2";
            }
            enum "initMtnIE" {
              value "3";
            }
            enum "stnMtnIE" {
              value "4";
            }
            enum "shortGrantIE" {
              value "5";
            }
            enum "longGrantIE" {
              value "6";
            }
          }
          description
           "This entry describes the Information Element (IE) type.
            Enumerations are :
            reqIE(1)          : Request Information Element,
                                The request Information Element provides
                                an upstream interval in which a CM can
                                request the CMTS for bandwidth on the 
                                upstream channel.
            reqOrDataIE(2)    : Request/Data Information Element,
                                The Request/data Information Element 
                                provides an upstream interval in which 
                                request may be made by the CM to the 
                                CMTS for bandwidth or short data 
                                packets may be transmitted on the
                                upstream channel.
            initMtnIE(3)      : Initial Maintenance Information Element,
                                The Initial Maintenance Information 
                                Element provides an interval in which 
                                new stations may join the network.
            stnMtnIE(4)       : Station Maintenance Information Element,
                                The Station Maintenance Information 
                                Element provides an interval in which 
                                stations are expected to perform some 
                                aspect of routine network maintenance , 
                                such as ranging or power adjustment.
            shortGrantIE(5)   : Short Data Grant Information Element,
                                Short data grant Information Element
                                provides the CM an opportunity to 
                                transmit one or more upstream PDU's.
                                Short data grants are used with 
                                intervals equal to or less than the 
                                maximum burst size for the usage 
                                specified in the Upstream Channel 
                                Descriptor.
            longGrantIE(6)    : Long Data Grant Information Element,
                                The long data grant Information Element
                                also provides the CM an opportunity to
                                transmit one or more upstream PDU's.
                                All long data grant Information Elements
                                must have a larger number of mini-slots
                                than that defined for a short data grant
                                Information Element profile defined in
                                the Upstream Channel Descriptor. ";
          smiv2:max-access "not-accessible";
          smiv2:oid "1.3.6.1.4.1.9.9.116.1.1.4.1.1";
        }

        leaf cdxUpInfoElemStatsIEType {
          type int32;
          description
           "The current number of mini-slots used for the Information 
            Element type. The value is only a snapshot since the 
            current number of mini-slots of this IE type could be
            changing rapidly. ";
          smiv2:max-access "read-only";
          smiv2:oid "1.3.6.1.4.1.9.9.116.1.1.4.1.2";
        }
      }
    }

    container cdxBWQueueTable {
      description
       "This table describes the attributes of queues  
        in cable interfaces schedulers that support 
        Quality of Service.";
      smiv2:oid "1.3.6.1.4.1.9.9.116.1.2.1";

      list cdxBWQueueEntry {
        key "ifIndex cdxBWQueueNameCode";
        description
         "The list of queue attributes in cable upstream and downstream
          interfaces schedulers that supports Quality of Service. 
          Entries in this table exist for each ifEntry with ifType of 
          docsCableUpstream(129) and docsCableDownstream(128). ";
        reference
         "Data-Over-Cable Service Interface Specifications (DOCSIS)
          Radio Frequency Interface Specification (SP-RFI-I04-980724), 
          section 6.4 and appendix C. ";
        smiv2:oid "1.3.6.1.4.1.9.9.116.1.2.1.1";

        leaf ifIndex {
          type leafref {
            path "/if-mib:IF-MIB/if-mib:ifTable/if-mib:ifEntry/if-mib:ifIndex";
          }
        }

        leaf cdxBWQueueNameCode {
          type enumeration {
            enum "cirQ" {
              value "1";
            }
            enum "tbeQ" {
              value "2";
            }
            enum "p0BEGrantQ" {
              value "3";
            }
            enum "p1BEGrantQ" {
              value "4";
            }
            enum "p2BEGrantQ" {
              value "5";
            }
            enum "p3BEGrantQ" {
              value "6";
            }
            enum "p4BEGrantQ" {
              value "7";
            }
            enum "p5BEGrantQ" {
              value "8";
            }
            enum "p6BEGrantQ" {
              value "9";
            }
            enum "p7BEGrantQ" {
              value "10";
            }
            enum "rngPollQ" {
              value "11";
            }
          }
          description
           "The name code for the queue.
            
            cirQ :CIR queue. The queue is for Committed Information Rate 
                  (CIR) type of service which serves Service IDs which
                  have minimum guaranteed rate in its QoS profile.
                  It is applicable if CMTS is running is either of 
                  DOCSIS 1.0 or 1.1 modes.For DOCSIS 1.1 it has 
                  priority 8.
                             
            tbeQ :TBE Queue.The queue is for TIERED BEST EFFORT type 
                  service which serves Service IDs which does not have 
                  minimum guaranteed rate in its QoS profile. It is 
                  only applicable if CMTS is running in DOCSIS 1.0
                  mode.
            
            p0BEGrantQ-p7BEGrantQ : BEST EFFORT Queue
                  The queues p0BEGrantQ to P7BEGrantQ are for TIERED 
                  BEST EFFORT type service which serves Service IDs 
                  which do not have minimum guaranteed rate specified
                  in the QoS parameters. P0 has lowest priority and P7
                  has highest.Best Effort type is purely handled with 
                  prioritization in FIFO's and hence demands more 
                  number of queues. These queues are applicable only if
                  CMTS is running under mode DOCSIS 1.1.
                                         
            rngPollQ : RngPoll queue.
                  The queue is for the ranging SID's.It has the highest
                  priority. This queue information is only provided if
                  CMTS is running under mode DOCSIS 1.1. ";
          reference
           "Data-Over-Cable Service Interface Specifications (DOCSIS)
            Radio Frequency Interface Specification(SP-RFI-I06-001215) 
            section 6.4 and appendix C.";
          smiv2:max-access "not-accessible";
          smiv2:oid "1.3.6.1.4.1.9.9.116.1.2.1.1.1";
        }

        leaf cdxBWQueueOrder {
          type int32 {
            range "0..10";
          }
          description
           "The relative order of this queue to the other queues within the 
            cable interface. The smaller number has higher order. That is,
            0 is the highest order and 10 is the lowest order.  The 
            scheduler will serve the requests in higher order queue up to 
            the number of requests defined in cdxBWQueueNumServedBeforeYield
            before serving requests in the next higher order queue.  
            
            If there are n queues on this interface, the queue order will 
            be 0 to n-1 and maximum number of requests defined as 
            cdxBWQueueNumServedBeforeYield in order 0 queue will be served 
            before the requests in order 1 queue to be served. ";
          smiv2:max-access "read-only";
          smiv2:oid "1.3.6.1.4.1.9.9.116.1.2.1.1.2";
        }

        leaf cdxBWQueueNumServedBeforeYield {
          type int32 {
            range "0..64";
          }
          description
           "The maximum number of requests/packets the scheduler can 
            serve before yielding to another queue. The value 0 means all 
            requests must be served before yielding to another queue. The 
            range is 0-50 for DOCSIS 1.0 and for DOCSIS 1.1 it is 0-64. ";
          smiv2:max-access "read-only";
          smiv2:oid "1.3.6.1.4.1.9.9.116.1.2.1.1.3";
        }

        leaf cdxBWQueueType {
          type enumeration {
            enum "unknown" {
              value "1";
            }
            enum "other" {
              value "2";
            }
            enum "fifo" {
              value "3";
            }
            enum "priority" {
              value "4";
            }
          }
          description
           "The queuing type which decides the position of a request/packet
            within the queue.
              unknown : queue type unknown. 
              other   : not fifo, and not priority.
              fifo    : first in first out.
              priority: each bandwidth request has a priority and the 
                        position of the request within the queue depends 
                        on its priority.
              For DOCSIS1.1 all the priority queues are fifo queues. ";
          smiv2:max-access "read-only";
          smiv2:oid "1.3.6.1.4.1.9.9.116.1.2.1.1.4";
        }

        leaf cdxBWQueueMaxDepth {
          type int32 {
            range "0..64";
          }
          description
           "The maximum number of requests/packets which the queue can 
            support.The range is 0-50 for DOCSIS1.0 and for
            DOCSIS1.1 it is 0-64. ";
          smiv2:max-access "read-only";
          smiv2:oid "1.3.6.1.4.1.9.9.116.1.2.1.1.5";
        }

        leaf cdxBWQueueDepth {
          type int32 {
            range "0..64";
          }
          description
           "The current number of requests/packets in the queue.
            The range is 0-50 for DOCSIS1.0 and for
            DOCSIS1.1 it is 0-64. ";
          smiv2:max-access "read-only";
          smiv2:oid "1.3.6.1.4.1.9.9.116.1.2.1.1.6";
        }

        leaf cdxBWQueueDiscards {
          type yang:counter32;
          description
           "The number of requests/packets discarded because of queue
            overflow (queue depth > queue maximum depth). ";
          smiv2:max-access "read-only";
          smiv2:oid "1.3.6.1.4.1.9.9.116.1.2.1.1.7";
        }
      }
    }

    container cdxCmCpeTable {
      description
       "This table contains information about cable modems (CM) or 
        Customer Premises Equipments (CPE). ";
      smiv2:oid "1.3.6.1.4.1.9.9.116.1.3.1";

      list cdxCmCpeEntry {
        key "cdxCmCpeMacAddress";
        description
         "The list contains information for a cable modem (CM) or a
          Customer Premises Equipment (CPE). An entry exist for 
          each cable modem supported by CMTS and each Customer Premises 
          Equipment connected to a cable modem supported by CMTS. ";
        reference
         "Data-Over-Cable Service Interface Specifications (DOCSIS)
          Radio Frequency Interface Specification (SP-RFI-I04-980724.)
          docsIfCmtsCmStatusTable, docsIfCmtsServiceTable in 
          DOCS-IF-MIB.my. ";
        smiv2:oid "1.3.6.1.4.1.9.9.116.1.3.1.1";

        leaf cdxCmCpeMacAddress {
          type yang:mac-address;
          description
           "The Mac address to identify a cable modem or a Customer 
            Premises Equipment. ";
          smiv2:max-access "not-accessible";
          smiv2:oid "1.3.6.1.4.1.9.9.116.1.3.1.1.1";
        }

        leaf cdxCmCpeType {
          type enumeration {
            enum "cm" {
              value "1";
            }
            enum "cpe" {
              value "2";
            }
          }
          description
           "Indicate this entry is for cable modem or Customer Premises 
            Equipment.  The enumerations are: 
             cm(1): cable modem
             cpe(2): Customer Premises Equipment ";
          smiv2:max-access "read-only";
          smiv2:oid "1.3.6.1.4.1.9.9.116.1.3.1.1.2";
        }

        leaf cdxCmCpeIpAddress {
          type inet:ipv4-address;
          description
           "Ip address of the cable modem or Customer Premises Equipment. ";
          smiv2:max-access "read-only";
          smiv2:oid "1.3.6.1.4.1.9.9.116.1.3.1.1.3";
        }

        leaf cdxCmCpeIfIndex {
          type if-mib:InterfaceIndex;
          description
           "The CMTS cable MAC interface index (ifType of 
            docsCableMaclayer(127)) that cable modem or Customer Premises 
            Equipment connects to.  
            
            Use cdxCmCpeIfIndex and cdxCmCpeCmtsServiceId to identify
            an  entry in docsIfCmtsServiceTable.  ";
          smiv2:max-access "read-only";
          smiv2:oid "1.3.6.1.4.1.9.9.116.1.3.1.1.4";
        }

        leaf cdxCmCpeCmtsServiceId {
          type int32 {
            range "1..16383";
          }
          description
           "The cable modem's primary Service ID if the type is cm. 
            The primary Service ID for the CM which the CPE connects if the 
            type is cpe.
            
            Use cdxCmCpeIfIndex and cdxCmCpeCmtsServiceId to identify an 
            entry in docsIfCmtsServiceTable.  ";
          smiv2:max-access "read-only";
          smiv2:oid "1.3.6.1.4.1.9.9.116.1.3.1.1.5";
        }

        leaf cdxCmCpeCmStatusIndex {
          type int32 {
            range "1..2147483647";
          }
          description
           "Pointer to an entry in docsIfCmtsCmStatusTable identifying 
            status of the CM (which the CPE connects to.) ";
          smiv2:max-access "read-only";
          smiv2:oid "1.3.6.1.4.1.9.9.116.1.3.1.1.6";
        }

        leaf cdxCmCpeAccessGroup {
          type snmpv2-tc:DisplayString;
          description
           "ASCII text to identify the Access Group for a CM or CPE. 
            Access Group is to filter the upstream traffic for that
            CM or CPE.  ";
          smiv2:max-access "read-write";
          smiv2:oid "1.3.6.1.4.1.9.9.116.1.3.1.1.7";
        }

        leaf cdxCmCpeResetNow {
          type boolean;
          description
           "Setting this object to true(1) causes the device to 
            reset.  Reading this object always returns false(2).
            
            For cdxCmCpeType value cm(1),  CMTS removes the 
            CM from the Station Maintenance List and would cause 
            the CM to reset its interface.
            
            For cdxCmCpeType value cpe(2), CMTS removes the 
            CPE's MAC address from the internal address table.  
            It then rediscovers and associates the CPE with the 
            correct CM during the next DHCP lease cycle.  By resetting 
            the CPE, the user can replace an existing CPE or change 
            its network interface card (NIC).";
          smiv2:max-access "read-write";
          smiv2:oid "1.3.6.1.4.1.9.9.116.1.3.1.1.8";
        }

        leaf cdxCmCpeDeleteNow {
          type boolean;
          description
           "Setting this object to true(1) causes the CM/CPE to
            be deleted.  Reading this object always returns false(2).
            
            For cdxCmCpeType value cm(1),  CMTS delete CM from 
            its interface.
            
            For cdxCmCpeType value cpe(2), CMTS delete CPE from 
            its associated CM.";
          smiv2:max-access "read-write";
          smiv2:oid "1.3.6.1.4.1.9.9.116.1.3.1.1.9";
        }
      }
    }

    container cdxCmtsCmStatusExtTable {
      description
       "The list contains the additional CM status information. ";
      smiv2:oid "1.3.6.1.4.1.9.9.116.1.3.2";

      list cdxCmtsCmStatusExtEntry {
        key "docsIfCmtsCmStatusIndex";
        description
         "Additional objects for docsIfCmtsCmStatusTable entry. ";
        reference
         "Data-Over-Cable Service Interface Specifications (DOCSIS)
          Radio Frequency Interface Specification (SP-RFI-I04-980724.)
          docsIfCmtsCmStatusTable in DOCS-IF-MIB.my. ";
        smiv2:oid "1.3.6.1.4.1.9.9.116.1.3.2.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf cdxCmtsCmStatusValue {
          type enumeration {
            enum "offline" {
              value "1";
            }
            enum "others" {
              value "2";
            }
            enum "initRangingRcvd" {
              value "3";
            }
            enum "initDhcpReqRcvd" {
              value "4";
            }
            enum "onlineNetAccessDisabled" {
              value "5";
            }
            enum "onlineKekAssigned" {
              value "6";
            }
            enum "onlineTekAssigned" {
              value "7";
            }
            enum "rejectBadMic" {
              value "8";
            }
            enum "rejectBadCos" {
              value "9";
            }
            enum "kekRejected" {
              value "10";
            }
            enum "tekRejected" {
              value "11";
            }
            enum "online" {
              value "12";
            }
            enum "initTftpPacketRcvd" {
              value "13";
            }
            enum "initTodRequestRcvd" {
              value "14";
            }
            enum "reset" {
              value "15";
            }
            enum "rangingInProgress" {
              value "16";
            }
            enum "rangingCompleted" {
              value "17";
            }
            enum "dhcpGotIpAddr" {
              value "18";
            }
            enum "rejStaleConfig" {
              value "19";
            }
            enum "rejIpSpoof" {
              value "20";
            }
            enum "rejClassFail" {
              value "21";
            }
            enum "rejRegNack" {
              value "22";
            }
            enum "bpiKekExpired" {
              value "23";
            }
            enum "bpiTekExpired" {
              value "24";
            }
            enum "shutdown" {
              value "25";
            }
            enum "channelChgInitRangingRcvd" {
              value "26";
            }
            enum "channelChgRangingInProgress" {
              value "27";
            }
          }
          description
           "Current Cable Modem connectivity state. The object extends 
            states in docsIfCmtsCmStatusValue in more details. 
            
            The enumerations are:
            offline(1)                : modem considered offline.
            others(2)                 : states is in 
                                        docsIfCmtsCmStatusValue.
            initRangingRcvd(3)        : modem sent initial ranging.
            initDhcpReqRcvd(4)        : dhcp request received.
            onlineNetAccessDisabled(5): modem registered, but network    
                                        access for the CM is disabled.
            onlineKekAssigned(6)      : modem registered, BPI enabled
                                        and KEK assigned.
            onlineTekAssigned(7)      : modem registered, BPI enabled
                                        and TEK assigned.
            rejectBadMic(8)           : modem did attempt to register but
                                        registration was refused due to
                                        bad mic.
            rejectBadCos(9)           : modem did attempt to register but
                                        registration was refused due to
                                        bad COS.
            kekRejected(10)           : KEK modem key assignment rejected.
            tekRejected(11)           : TEK modem key assignment rejected.
            online(12)                : modem registered, enabled for data.
            initTftpPacketRcvd(13)    : tftp packet received and option
                                        file transfer started. 
            initTodRquestRcvd(14)     : Time of the Day (TOD) request 
                                        received.
            reset(15)                 : modem is resetting.
            rangingInProgress(16)     : initial ranging is in progress.
            --            rangingCompleted(17)      : initial ranging is completed. (deprecated)
            dhcpGotIpAddr(18)         : modem has got an IP address 
                                        from the DHCP server.
            rejStaleConfig(19)        : modem did attempt to register
                                        but registration was refused
                                        due to stale Config.
            rejIpSpoof(20)            : modem did attempt to register but
                                        registration was refused due to IP
                                        Spoof.
            rejClassFail(21)          : modem did attempt to register but
                                        registration was refused due to 
                                        Class failure.
            rejRegNack(22)            : modem did attempt to register but
                                        no acknowledgement was 
                                        received.
            bpiKekExpired(23)         : KEK modem key assignment expired.
            bpiTekExpired(24)         : TEK modem key assignment expired.
            shutdown(25)              : modem is in shutdown state.
            channelChgInitRangingRcvd(26)  : modem sent initial ranging
                                              during channel change.
            channelChgRangingInProgress(27) : initial ranging is in
                                              progress during channel
                                              change.
            
            This cdxCmtsCmStatusValue could return initRangingRcvd(3)
            or rangingInProgress(16) when the docsIfCmtsCmStatusValue
            is ranging(2).
            
            This cdxCmtsCmStatusValue will return others(2) when the
            docsIfCmtsCmStatusValue states is either
            rangingAborted(3), rangingComplete(4), and
            ipComplete(5).
            
            This cdxCmtsCmStatusValue could return online(12), or
            onlineNetAccessDisabled(5) for CM with BPI disabled, or
            onlineNetAccessDisabled(5) or onlineTekAssigned(7) for
            CM with BPI enabled, when the docsIfCmtsCmStatusValue
            is registrationComplete(6).
            
            This cdxCmtsCmStatusValue could return either
            rejectBadMic(8), rejectBadCos(9) rejStaleConfig(19) or
            rejRegNack(22) when the docsIfCmtsCmStatusValue
            is accessDenied(7) for possible reasons of cable modem
            registration abort.
            
            This cdxCmtsCmStatusValue could return either
            onlineKekAssigned(6), kekRejected(10), tekRejected(11),
            or online(12) for the CM with BPI enabled when the
            docsIfCmtsCmStatusValue is registeredBPIInitializing(9).
            
            
            
            FOR DOCSIS 1.0
            --------------
            The ranging, rangingAborted, rangingComplete, and ipComplete 
            states in docsIfCmtsCmStatusValue is others in this object
            since this object is extension of docsIfCmtsCmStatusValue. 
            
            The registrationComplete state in docsIfCmtsCmStatusValue 
            could be online, onlineNetAccessDisabled, onlineKekAssigned, or 
            onlineTekAssigned in this object.  
            
            The accessDenied state in docsIfCmtsCmStatusValue could be 
            rejectBadMic, rejectBadCos in this object for the possible
            reasons of cable modem registration abort.
            
            The states 15 to 25 are not applicable.
            
            FOR DOCSIS 1.1
            -------------- 
                        
            The registrationComplete state in docsIfCmtsCmStatusValue 
            could be online, onlineNetAccessDisabled, 
            onlineBpiKekAssigned,or onlineBpiTekAssigned in this 
            object.  
            
            The accessDenied state in docsIfCmtsCmStatusValue could be 
            rejMicFail, rejStaleConfig, rejIpSpoof, rejClassFail, 
            rejRegNack in this object for the possible reasons of cable
            modem registration abort.
            
            The CMTS only reports states it is able to detect. States
            Online(2) and  rejectBadCos(9) are not applicable for 
            DOCSIS1.1 modems. ";
          smiv2:max-access "read-only";
          smiv2:oid "1.3.6.1.4.1.9.9.116.1.3.2.1.1";
        }

        leaf cdxIfCmtsCmStatusOnlineTimes {
          type yang:counter32;
          description
           "The number of times that the modem changes the connectivity 
            state from 'offline' to 'online' over the time period from 
            the modem's first ranging message received by CMTS until 
            now.
            
            The modem is considered as 'online' when the value for 
            cdxCmtsCmStatusValue is any of the values: online(5), 
            onlineNetAccessDisabled(6), onlineKekAssigned(7), and 
            onlineTekAssigned(8), and the modem is considered as
            'offline' for other values for cdxCmtsCmStatusValue.  ";
          reference
           "cdxCmtsCmStatusValue object.";
          smiv2:max-access "read-only";
          smiv2:oid "1.3.6.1.4.1.9.9.116.1.3.2.1.2";
        }

        leaf cdxIfCmtsCmStatusPercentOnline {
          type int32 {
            range "0..10000";
          }
          description
           "The percentage of time that the modem stays 'online' over 
            the time period from the modem's first ranging message 
            received by CMTS until now. 
            
            The value for this object is 100 times bigger than the real 
            percentage value. For example, 32.15% will be value 3215.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.3";
        }

        leaf cdxIfCmtsCmStatusMinOnlineTime {
          type snmpv2-tc:TimeInterval;
          description
           "The minimum period of time the modem stayed 'online' over
            the time period from the modem's first ranging message 
            received by CMTS until now.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.4";
        }

        leaf cdxIfCmtsCmStatusAvgOnlineTime {
          type snmpv2-tc:TimeInterval;
          description
           "The average period of time the modem stayed 'online' over
            the time period from the modem's first ranging message 
            received by CMTS until now.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.5";
        }

        leaf cdxIfCmtsCmStatusMaxOnlineTime {
          type snmpv2-tc:TimeInterval;
          description
           "The maximum period of time the modem stayed 'online' over
            the time period from the modem's first ranging message 
            received by CMTS until now.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.6";
        }

        leaf cdxIfCmtsCmStatusMinOfflineTime {
          type snmpv2-tc:TimeInterval;
          description
           "The minimum period of time modem stayed 'offline' over
            the time period from the modem's first ranging message 
            received by CMTS until now.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.7";
        }

        leaf cdxIfCmtsCmStatusAvgOfflineTime {
          type snmpv2-tc:TimeInterval;
          description
           "The average period of time the modem stayed 'offline' over
            the time period from the modem's first ranging message 
            received by CMTS until now.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.8";
        }

        leaf cdxIfCmtsCmStatusMaxOfflineTime {
          type snmpv2-tc:TimeInterval;
          description
           "The maximum period of time the modem stayed 'offline' over
            the time period from the modem's first ranging message 
            received by CMTS until now.
            
            The modem is considered as 'online' when the value for 
            cdxCmtsCmStatusValue is any of the values: online(5), 
            onlineNetAccessDisabled(6), onlineKekAssigned(7), and 
            onlineTekAssigned(8), and the modem is considered as 
            'offline' for other values for cdxCmtsCmStatusValue.  ";
          reference
           "cdxCmtsCmStatusValue object.";
          smiv2:max-access "read-only";
          smiv2:oid "1.3.6.1.4.1.9.9.116.1.3.2.1.9";
        }

        leaf cdxIfCmtsCmStatusDynSidCount {
          type int32 {
            range "0..16383";
          }
          description
           "The number of active dynamic SIDs on this modem.
            Prior to getting the assigned the Service Flow IDs(SFID)
            the CM must must complete a number of protocol 
            transactions. The CMTS assigns a temporary Service ID
            (SID) to complete these steps.";
          smiv2:max-access "read-only";
          smiv2:oid "1.3.6.1.4.1.9.9.116.1.3.2.1.10";
        }

        leaf cdxIfCmtsCmStatusAddlInfo {
          type bits {
            bit noisyPlant {
              position "0";
            }
            bit modemPowerMaxOut {
              position "1";
            }
          }
          description
           "This object indicates additional attributes regarding
            the CM.
            1. noisyPlant indicates that the CM connection is noisy.
            2. modemPowerMaxOut indicates that the modem has reached
            its maximum power level.
            
            A bit of of this object is set to 1 if the condition
            indicated by the bit is satisfied.
            
            Note that BITS are encoded most significant bit
            first. ";
          smiv2:max-access "read-only";
          smiv2:oid "1.3.6.1.4.1.9.9.116.1.3.2.1.11";
        }

        leaf cdxIfCmtsCmStatusOnlineTimesNum {
          type CISCO-DOCS-EXT-MIB:CdxResettableCounter32;
          description
           "The number of times that the modem changes the connectivity
            state from 'offline' to 'online' over the time period from
            the modem's first ranging message received by CMTS until now.
            
            The modem is considered as 'online' when the value for
            cdxCmtsCmStatusValue is any of the values: online(5),
            onlineNetAccessDisabled(6), onlineKekAssigned(7), and
            onlineTekAssigned(8), and the modem is considered as 'offline'
            for other values for cdxCmtsCmStatusValue.
            
            The value of this object is reset to 0 if the value in
            cdxIfCmtsCmStatusLastResetTime is changed. ";
          smiv2:max-access "read-only";
          smiv2:oid "1.3.6.1.4.1.9.9.116.1.3.2.1.12";
        }

        leaf cdxIfCmtsCmStatusLastResetTime {
          type yang:timestamp;
          description
           "The last cable modem connectivity statistics reset time. If
            the value of  this object is '0', then the cable modem
            connectivity statistics had not been reset.";
          smiv2:max-access "read-only";
          smiv2:oid "1.3.6.1.4.1.9.9.116.1.3.2.1.13";
        }
      }
    }

    container cdxCmtsMacExtTable {
      description
       "This table contains the additions attributes of a CMTS MAC
        interface that provided by docsIfCmtsMacTable. ";
      smiv2:oid "1.3.6.1.4.1.9.9.116.1.3.3";

      list cdxCmtsMacExtEntry {
        key "ifIndex";
        description
         "Additional objects for docsIfCmtsMacTable entry including
          the cable modem notification enable/disable and the interval 
          of cable modem notification sent by the CMTS for a cable modem
          that the Mac interface supports. An entry in this table exists 
          for each ifEntry with an ifType of docsCableMaclayer(127).
          Additional objects added to determine the number of 
          active/registered/total cable modems on this cable mac 
          interface since boot. Also, it contains the object to set
          the Dynamic Message Integrity Check (DMIC) which users 
          can configure how cable modems are handled if CMs fail 
          the DMIC.";
        reference
         "docsIfCmtsMacTable in DOCS-IF-MIB.my. ";
        smiv2:oid "1.3.6.1.4.1.9.9.116.1.3.3.1";

        leaf ifIndex {
          type leafref {
            path "/if-mib:IF-MIB/if-mib:ifTable/if-mib:ifEntry/if-mib:ifIndex";
          }
        }

        leaf cdxCmtsCmOnOffTrapEnable {
          type boolean;
          description
           "An indication of whether the cdxCmtsCmOnOffNotification 
            is enabled. The default value is false(2). ";
          smiv2:max-access "read-write";
          smiv2:oid "1.3.6.1.4.1.9.9.116.1.3.3.1.1";
        }

        leaf cdxCmtsCmOnOffTrapInterval {
          type int32 {
            range "0..86400";
          }
          units "seconds";
          description
           "The interval for cdxCmtsCmOnOffNotification sent by CMTS for
            one online/offline state change if cdxCmtsCmOnOffTrapEnable 
            is true. 
            
            If there are more than one state changes to online/offline 
            for a cable modem during this interval, only one 
            cdxCmtsCmOnOffNotification is sent by CMTS for the first 
            state change to online and one cdxCmtsCmOnOffNotification 
            for the first state changing to offline if 
            cdxCmtsCmOnOffTrapEnable is true.
            
            This is to avoid too many notifications sent for a cable 
            modem online/offline state changes during a short period
            of time. 
            
            If the value is 0, then cdxCmtsCmOnOffNotification will be 
            sent for every state changes to online/offline for a cable 
            modem if cdxCmtsCmOnOffTrapEnable is true.  
            
            If cdxCmtsCmOnOffTrapEnable value changes from true to false 
            or from false to true, this value will remain no change as 
            before. 
            
            The default value is 600 seconds. ";
          smiv2:max-access "read-write";
          smiv2:oid "1.3.6.1.4.1.9.9.116.1.3.3.1.2";
        }

        leaf cdxCmtsCmDefaultMaxCpes {
          type int32 {
            range "-1..255";
          }
          description
           "The default maximum number of permitted CPEs per modem 
            in this cable interface. A modem can override this 
            value by setting the object cdxCmtsCmMaxCpeNumber
            in the cdxCmtsCmTable.  
            
            The value -1 means the default value of maximum hosts 
            per modem in this cable interface is not specified.
            
            The value 0 means no maximum limit.
            
            Setting the value will not affect the already connected
            CPEs to the modems in this cable interface. ";
          smiv2:max-access "read-write";
          smiv2:oid "1.3.6.1.4.1.9.9.116.1.3.3.1.3";
        }

        leaf cdxCmtsCmTotal {
          type int32 {
            range "0..2147483647";
          }
          description
           "The total count of cable modems on this cable mac interface
            since boot.";
          smiv2:max-access "read-only";
          smiv2:oid "1.3.6.1.4.1.9.9.116.1.3.3.1.4";
        }

        leaf cdxCmtsCmActive {
          type int32 {
            range "0..2147483647";
          }
          description
           "The count of cable modems that are active. Active cable 
            modems are recognized by the cdxCmtsCmStatusValue 
            other than offline(1). ";
          smiv2:max-access "read-only";
          smiv2:oid "1.3.6.1.4.1.9.9.116.1.3.3.1.5";
        }

        leaf cdxCmtsCmRegistered {
          type int32 {
            range "0..2147483647";
          }
          description
           "The count of cable modems that are registered and online 
            on this cable mac interface. Registered cable modems are 
            those with one of the following values. 
            registrationComplete(6) of docsIfCmtsCmStatusValue OR 
            either of online(12), kekRejected(10), 
            onlineKekAssigned(6),tekRejected(11), onlineTekAssigned(7)
            of cdxCmtsCmStatusValue";
          smiv2:max-access "read-only";
          smiv2:oid "1.3.6.1.4.1.9.9.116.1.3.3.1.6";
        }

        leaf cdxCmtsCmDMICMode {
          type enumeration {
            enum "notConfigured" {
              value "1";
            }
            enum "mark" {
              value "2";
            }
            enum "lock" {
              value "3";
            }
            enum "reject" {
              value "4";
            }
          }
          description
           "The Dynamic Shared Secret feature can operate in three 
            different modes, depending on what action should be taken 
            for cable modems that fail the CMTS MIC verification check:
            notConfigured(1): It indicates that the DMIC is not 
                              configured for this cable interface.
            mark(2): By default, the Dynamic Shared Secret feature 
                     is enabled on all cable interfaces using the 
                     mark option. In this mode, the CMTS allows 
                     cable modems to come online even if they fail 
                     the CMTS MIC validity check. However, for
                     this modem cdxCmtsCmStatusDMICMode will
                     be labeled as marked.
            lock(3): When the lock option is used, the CMTS assigns 
                     a restrictive QoS configuration to CMs that 
                     fail the MIC validity check twice in a row. A 
                     particular QoS profile to be used for locked 
                     cable modems can be specified by setting 
                     cdxCmtsCmDMICLockQos.
                     If a customer resets their CM, the CM will 
                     reregister but still uses the restricted QoS 
                     profile. A locked CM continues with the 
                     restricted QoS profile until it goes offline 
                     and remains offline for at least 24 hours, at 
                     which point it is allowed to reregister with a 
                     valid DOCSIS configuration file. A system 
                     operator can manually clear the lock on a CM by 
                     setting cdxCmtsCmStatusDMICUnLock object.
            reject(4):  In the reject mode, the CMTS refuses to allow 
                        CMs to come online if they fail the CMTS MIC 
                        validity check.";
          smiv2:defval "mark";
          smiv2:max-access "read-write";
          smiv2:oid "1.3.6.1.4.1.9.9.116.1.3.3.1.7";
        }

        leaf cdxCmtsCmDMICLockQos {
          type int32 {
            range "0..16383";
          }
          description
           "If cdxCmtsCmDMICMode is set to lockingMode(3), this object
            would contain the restrictive QoS profile number as 
            indicated by docsIfQosProfIndex if set and it will 
            have 0 if not applicable or not defined. In case,
            cdxCmtsCmDMICMode is set to lockingMode(3) and this
            object is not defined then the CMTS defaults to special
            QoS profile that limits the downstream and upstream 
            service flows to a maximum rate of 10 kbps. However,
            for this to happen the modems should have the 
            permission to create QoS profile.";
          smiv2:max-access "read-write";
          smiv2:oid "1.3.6.1.4.1.9.9.116.1.3.3.1.8";
        }
      }
    }

    container cdxCmtsCmChOverTable {
      description
       "A table of CMTS operation entries to instruct cable modems
        to move to a new downstream and/or upstream channel. 
        
        An entry in this table is an operation that has been 
        initiated from CMTS to generates downstream frequency and/or 
        upstream channel override fields in the RNG-RSP message sent 
        to a cable modem.  A RNG-RSP message is sent to a cable 
        modem during initial maintenance opportunity. 
        
        This operation causes the uBR to place an entry for the cable 
        modem specified into the override request queue.  The link is 
        then broken by deleting the modem from its polling list.  When 
        the modem attempts initial ranging, the override request 
        causes downstream frequency and upstream channel override 
        fields to be inserted into the RNG-RSP message.  ";
      smiv2:oid "1.3.6.1.4.1.9.9.116.1.3.5";

      list cdxCmtsCmChOverEntry {
        key "cdxCmtsCmChOverSerialNumber";
        description
         "A CMTS operation entry to instruct a cable modem to move to
          a new downstream and/or upstream channel.
          
          A CMTS operator can use this to initiate an operation
          in CMTS to instruct a cable modem to move to a new
          downstream, or upstream channel or both. 
          
          Each entry consists of the mac address of the cable modem
          to be moved, a new downstream frequency, a new upstream channel 
          id etc..  More than one entries could have for a cable modem,
          so there is a time stamp for each entry to show the time
          when this operation is initiated. 
          
          A management station wishing to create an entry should
          first generate a pseudo-random serial number to be used
          as the index to this sparse table.  The station should
          then create the associated instance of the row status
          object. It must also, either in the same or in successive
          PDUs, create the associated instance of the command and
          parameter objects. It should also modify the default values
          for any of the parameter objects if the defaults are not
          appropriate.
          
          Once the appropriate instances of all the command
          objects have been created, either by an explicit SNMP
          set request or by default, the row status should be set
          to active to initiate the operation. Note that this entire
          procedure may be initiated via a single set request which
          specifies a row status  of createAndGo as well as specifies
          valid values for the non-defaulted parameter objects.
          
          Once an operation has been activated, it cannot be stopped.
          That is, it will run until either the CMTS has generated 
          downstream frequency and/or upstream channel override fields 
          in the RNG-RSP message sent to a cable modem or time out. 
          In either case, the operation is completed.
          
          Once the operation is completed, the real result of the 
          operation to the cable modem cannot be known from this table.
          The result of the cable modem's downstream frequency and the 
          upstream channel id can be checked from other MIB tables.  
          For example, docsIfCmtsServiceTable from DOCS-IF-MIB can be 
          used to check whether the cable modem's downstream frequency
          and upstream channel id are changed.  Please note that even
          the CMTS has generated downstream frequency and/or upstream 
          channel override fields in the RNG-RSP message sent to a 
          cable modems, if the cable modem cannot lock the instructed 
          downstream frequency or no upstream channel id could be used, 
          it may reconnect back to the original downstream frequency
          and upstream channel id. 
          
          Once the operation completes, the management station should
          retrieve the values of the cdxCmtsCmChOverState 
          objects of interest, and should then delete the entry.  
          In order to prevent old entries from clogging the table, 
          entries will be aged out, but an entry will never be deleted 
          within 15 minutes of completing. ";
        reference
         "Data-Over-Cable Service Interface Specifications (DOCSIS)
          Radio Frequency Interface Specification (SP-RFI-I04-980724),
          6.3.2.5.3 Overriding Channels. ";
        smiv2:oid "1.3.6.1.4.1.9.9.116.1.3.5.1";

        leaf cdxCmtsCmChOverSerialNumber {
          type int32 {
            range "1..2147483647";
          }
          description
           "Object which specifies a unique entry in the
            table. A management station wishing to initiate a
            channel override operation should use a pseudo-random 
            value for this object when creating or modifying an 
            instance of a cdxCmtsCmChOverEntry.  ";
          smiv2:max-access "not-accessible";
          smiv2:oid "1.3.6.1.4.1.9.9.116.1.3.5.1.1";
        }

        leaf cdxCmtsCmChOverMacAddress {
          type yang:mac-address;
          description
           "The mac address of the cable modem that the CMTS instructs to
            move to a new downstream and/or upstream channel.  
            
            This column must be set to a valid Mac address currently in
            the CMTS in order for this entry's row status to be set to
            active successfully.";
          smiv2:max-access "read-write";
          smiv2:oid "1.3.6.1.4.1.9.9.116.1.3.5.1.2";
        }

        leaf cdxCmtsCmChOverDownFrequency {
          type int32 {
            range "0..1000000000";
          }
          units "hertz";
          description
           "The new downstream frequency which the cable modem is 
            instructed to move to.  The value 0 is to ask the CMTS not to
            override the downstream frequency. ";
          smiv2:defval "0";
          smiv2:max-access "read-write";
          smiv2:oid "1.3.6.1.4.1.9.9.116.1.3.5.1.3";
        }

        leaf cdxCmtsCmChOverUpChannelId {
          type int32 {
            range "-1..255";
          }
          description
           "The new channel Id which the cable modem is instructed to 
            move to.  The value -1 is to ask the CMTS not to override
            the upstream channel Id. ";
          smiv2:defval "-1";
          smiv2:max-access "read-write";
          smiv2:oid "1.3.6.1.4.1.9.9.116.1.3.5.1.4";
        }

        leaf cdxCmtsCmChOverTrapOnCompletion {
          type boolean;
          description
           "Specifies whether or not a cdxCmtsCmChOverNotification 
            should be issued on completion of the operation.  If such a 
            notification is desired, it is the responsibility of the 
            management entity to ensure that the SNMP administrative model 
            is configured in such a way as to allow the notification to be 
            delivered. ";
          smiv2:defval "false";
          smiv2:max-access "read-write";
          smiv2:oid "1.3.6.1.4.1.9.9.116.1.3.5.1.5";
        }

        leaf cdxCmtsCmChOverOpInitiatedTime {
          type yang:timestamp;
          description
           "The value of sysUpTime at which the operation was initiated.  
            Since it is possible to have more than one entry in this 
            table for a cable modem, this object can help to distinguish 
            the entries for the same cable modem. ";
          smiv2:max-access "read-only";
          smiv2:oid "1.3.6.1.4.1.9.9.116.1.3.5.1.6";
        }

        leaf cdxCmtsCmChOverState {
          type enumeration {
            enum "messageSent" {
              value "1";
            }
            enum "commandNotActive" {
              value "2";
            }
            enum "noOpNeeded" {
              value "3";
            }
            enum "modemNotFound" {
              value "4";
            }
            enum "waitToSendMessage" {
              value "5";
            }
            enum "timeOut" {
              value "6";
            }
          }
          description
           "The status of the specified channel override operation.
            The enumerations are:
              messageSent(1): the CMTS has sent a RNG-RSP message 
                          with channel override to the cable modem. 
              commandNotActive(2): the command is not in active mode
                                   due to this entry's row status is not
                                   in active yet.
              noOpNeed(3): The downstream frequency and the upstream 
                           channel Id in this entry are the same as 
                           original ones when this entry's row status
                           is set to active, so CMTS does not need to 
                           do any operation.  
              modemNotFound(4): The modem is not found in the CMTS
                                at the time when the command becomes
                                active.
              waitToSendMessage(5): specified the operation is active
                                    and CMTS is waiting to send
                                    a RNG-RSP message with channel 
                                    override to the cable modem.
              timeOut(6): specified the operation is timed out.
                          That is, the CMTS cannot send a RNG-RSP message 
                          with channel override to the cable modem within 
                          the time specified in the object of 
                          cdxCmtsCmChOverTimeExpiration. 
                          The possible reason is that the cable modem
                          does not repeat the initial ranging. 
            
               The possible state change diagram is as below: 
               [commandNotActive ->] waitToSendMessage -> 
                   messageSent or timeOut. 
               [commandNotActive ->] noOpNeeded or modemNotFound. ";
          reference
           "Data-Over-Cable Service Interface Specifications (DOCSIS)
            Radio Frequency Interface Specification (SP-RFI-I04-980724),
            6.3.2.5.3 Overriding Channels. ";
          smiv2:max-access "read-only";
          smiv2:oid "1.3.6.1.4.1.9.9.116.1.3.5.1.7";
        }

        leaf cdxCmtsCmChOverRowStatus {
          type snmpv2-tc:RowStatus;
          description
           "The status of this table entry.  
            
            This value for cdxCmtsCmChOverMacAddress must be valid Mac 
            address currently in the CMTS in order for the row 
            status to be set to active successfully. 
               
            Once the row status becomes active and state becomes 
            waitToSendMessage, the entry cannot not be changed except 
            to delete the entry by setting the row status to destroy(6) 
            and since the operation cannot be stopped, the destroy(6) 
            will just cause the SNMP agent to hide the entry from 
            application and the SNMP agent will delete the entry 
            right after the operation is completed. ";
          smiv2:max-access "read-write";
          smiv2:oid "1.3.6.1.4.1.9.9.116.1.3.5.1.8";
        }
      }
    }

    container cdxCmtsCmTable {
      description
       "This table contains attributes or configurable parameters 
        for cable modems from a CMTS. ";
      smiv2:oid "1.3.6.1.4.1.9.9.116.1.3.6";

      list cdxCmtsCmEntry {
        key "docsIfCmtsCmStatusIndex";
        description
         "The list contains a cable modem's attributes or 
          configurable parameters from a CMTS. ";
        smiv2:oid "1.3.6.1.4.1.9.9.116.1.3.6.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf cdxCmtsCmMaxCpeNumber {
          type int32 {
            range "-1..255";
          }
          description
           "The maximum number of permitted CPEs connecting to the
            modem. 
            
            The value -1 means to use the default value of maximum 
            hosts per modem in the CMTS cable interface which the modem 
            connects to and the value is defined in 
            cdxCmtsCmDefaultMaxCpes in the cdxCmtsMacExtTable. 
            
            The value 0 means no maximum limit.
            
            Setting the value will not affect the already connected
            CPEs to the modem. ";
          smiv2:max-access "read-write";
          smiv2:oid "1.3.6.1.4.1.9.9.116.1.3.6.1.1";
        }

        leaf cdxCmtsCmCurrCpeNumber {
          type int32 {
            range "0..255";
          }
          description
           "The current number of CPEs connecting to the modem.
            
            The value 0 means no hosts connecting to the modem.";
          smiv2:max-access "read-only";
          smiv2:oid "1.3.6.1.4.1.9.9.116.1.3.6.1.2";
        }

        leaf cdxCmtsCmQosProfile {
          type int32 {
            range "0..16383";
          }
          description
           "The index in docsIfQosProfileTable describing the quality
            of service attributes associated with this particular
            modem's primary SID. 
            
            When trying to change the value, if the new value is not 
            a valid index in the docsIfQosProfileTable, the modem will 
            retain the old docsIfQosProfileTable entry. If no associated 
            docsIfQosProfileTable entry exists for this modem, 
            this object returns a value of zero on read.
            
            This object has meaning only for DOCSIS1.0 cable modems.
            For cable modems in DOCSIS1.1 or above mode, this object will 
            report 0 and cannot be changed to any other values since 
            there is no QoS profile associated with cable modems in 
            DOCSIS1.1 or above mode.";
          smiv2:max-access "read-write";
          smiv2:oid "1.3.6.1.4.1.9.9.116.1.3.6.1.3";
        }
      }
    }

    container cdxCmtsCmStatusDMICTable {
      description
       "This table contains the list of modems which failed the CMTS
        Dynamic Message Integrity Check (DMIC). The modems are 
        either
        Marked: The modems failed the DMIC check but were still 
                allowed to come online.
        Locked: The modems failed the DMIC check and hence were 
                allowed to come online with a restrictive QoS 
                profile as defined in  cdxCmtsCmDMICLockQos.
        Rejected: The modems failed the DMIC check and hence
                  were not allowed to come online.
        Another objective of the objects in this table is to clear
        the lock on the modems.";
      smiv2:oid "1.3.6.1.4.1.9.9.116.1.3.7";

      list cdxCmtsCmStatusDMICEntry {
        key "docsIfCmtsCmStatusIndex";
        description
         "Additional DMIC objects for docsIfCmtsCmStatusTable 
          entry. ";
        smiv2:oid "1.3.6.1.4.1.9.9.116.1.3.7.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf cdxCmtsCmStatusDMICMode {
          type enumeration {
            enum "mark" {
              value "1";
            }
            enum "lock" {
              value "2";
            }
            enum "reject" {
              value "3";
            }
          }
          description
           "This shows all the cable modems that are online or offline
            and that had failed the Dynamic CMTS MIC verification
            check. The state is mentioned as follows:
            mark(1): The modem was allowed to come online.
            lock(2): The modem was allowed to come online but with
                       a restrictive QoS profile as defined by 
                       cdxCmtsCmDMICLockQos.
            reject(3): The modem was not allowed to come online.";
          smiv2:max-access "read-only";
          smiv2:oid "1.3.6.1.4.1.9.9.116.1.3.7.1.1";
        }

        leaf cdxCmtsCmStatusDMICUnLock {
          type boolean;
          description
           "When set to TRUE, it forces the cable modems to 
            reinitialize, and the cable modems must re-register
            with a valid DOCSIS configuration file before being
            allowed online. Otherwise, the cable modem is locked 
            in its current restricted QoS profile and cannot 
            reregister with a different profile until it has 
            been offline for at least 24 hours.
            If cdxCmtsCmStatusDMICUnLock is set to TRUE, and
            re-init succeeds, that modem row is removed from the
            cdxCmtsCmStatusDMICTable. And if re-init again fails,
            the row remains in that table, possibly with a new
            value for cdxCmtsCmStatusDMICMode
            When polled, it will always return FALSE.";
          smiv2:defval "false";
          smiv2:max-access "read-write";
          smiv2:oid "1.3.6.1.4.1.9.9.116.1.3.7.1.2";
        }
      }
    }

    container cdxCmToCpeTable {
      description
       "This table contains information about CPE connects behind
        cable modem. It will return IP address and IP address type
        of each CPE connect to a CM.
        
        It is not intended to walk the whole table. An application
        would need to query this table based on the specific indices.
        Otherwise, it will impact the CMTS performance due to the 
        huge size of this table.
        
        The agent creates/destroys/modifies an entry whenever there
        is a CPE connect to a cable modem or disconnect from a cable
        modem.";
      smiv2:oid "1.3.6.1.4.1.9.9.116.1.3.8";

      list cdxCmToCpeEntry {
        key "cdxCmToCpeCmMacAddress cdxCmToCpeInetAddressType cdxCmToCpeInetAddress";
        description
         "Represents an entry in the table. Each entry is created if
          there is CPE connects to a cable modem.
          
          The indices uniquely identify a CPE. It is never the intent
          for an application to perform a SNMP Get operation against
          a table of this nature, rather it is the intent to merely
          enumberate mappings. 
          
          An application would determine the CPEs behind all cable
          modems by performing a SNMP GetNext starting with the
          variable bindings:
          - cdxCmToCpeInetAddressType.0
          - cdxCmToCpeInetAddress.0
          
          It will return the IP address type and value tuple
          corresponding to the CPE with lowest IP address behind the
          cable modem with the lowest MAC address. An application can
          perform a SNMP GetNext operation with the following variable
          bindings:
          - cdxCmToCpeInetAddressType.x.y.z
          - cdxCmToCpeInetAddress.x.y.z
          where x is MAC address of cable modem, and y.z is IP address
          type and value tuple of the reported CPE.
          An application can repeat this process until it has
          traversed the entire table.
          
          If the application only wants to know the CPEs behind a
          given cable modem, it can perform a SNMP GetNext opertaion
          with the following:
          - cdxCmToCpeInetAddressType.x
          - cdxCmToCpeInetAddress.x
          where x is MAC address of cable modem.";
        reference
         "Data-Over-Cable Service Interface Specifications (DOCSIS)
          Radio Frequency Interface Specification
          (SP-RFI-I04-980724.) docsIfCmtsCmStatusTable,
          docsIfCmtsServiceTable in DOCS-IF-MIB.my.";
        smiv2:oid "1.3.6.1.4.1.9.9.116.1.3.8.1";

        leaf cdxCmToCpeCmMacAddress {
          type yang:mac-address;
          description
           "The MAC address that uniquely identifies a cable modem
            that CPEs connects to.";
          smiv2:max-access "not-accessible";
          smiv2:oid "1.3.6.1.4.1.9.9.116.1.3.8.1.1";
        }

        leaf cdxCmToCpeInetAddressType {
          type inet-address:InetAddressType;
          description
           "The type of Internet address of the cdxCmToCpeInetAddress.";
          smiv2:max-access "read-only";
          smiv2:oid "1.3.6.1.4.1.9.9.116.1.3.8.1.2";
        }

        leaf cdxCmToCpeInetAddress {
          type inet-address:InetAddress;
          description
           "This object identifies the address assigned to this CPE.";
          smiv2:max-access "read-only";
          smiv2:oid "1.3.6.1.4.1.9.9.116.1.3.8.1.3";
        }
      }
    }

    container cdxCpeToCmTable {
      description
       "This table contains information about cable modems with CPE
        connects to.
        
        It is not intended to walk the whole table. An application
        would need to query this table base on the specific index.
        Otherwise, it will impact the CMTS performance due to the
        huge size of this table.
        
        The agent creates/destroys/modifies an entry whenever there
        is update for the cable modem that CPE connects to.";
      smiv2:oid "1.3.6.1.4.1.9.9.116.1.3.9";

      list cdxCpeToCmEntry {
        key "cdxCpeToCmCpeMacAddress";
        description
         "An entry in cdxCpeToCmTable. Each entry contains information
          on the MAC address, IP Address, and status index for the 
          cable modem with a specific CPE connects to. Each entry is
          created if there is any cable modem with CPE connects to.
          Entries are ordered by cdxCpeToCmCpeMacAddress.";
        reference
         "Data-Over-Cable Service Interface Specifications (DOCSIS)
          Radio Frequency Interface Specification
          (SP-RFI-I04-980724.) docsIfCmtsCmStatusTable,
          docsIfCmtsServiceTable in DOCS-IF-MIB.my.";
        smiv2:oid "1.3.6.1.4.1.9.9.116.1.3.9.1";

        leaf cdxCpeToCmCpeMacAddress {
          type yang:mac-address;
          description
           "This object identifies the MAC address of the CPE.";
          smiv2:max-access "not-accessible";
          smiv2:oid "1.3.6.1.4.1.9.9.116.1.3.9.1.1";
        }

        leaf cdxCpeToCmMacAddress {
          type yang:mac-address;
          description
           "This object identifies the MAC address of the cable modem.";
          smiv2:max-access "read-only";
          smiv2:oid "1.3.6.1.4.1.9.9.116.1.3.9.1.2";
        }

        leaf cdxCpeToCmInetAddressType {
          type inet-address:InetAddressType;
          description
           "The type of Internet address of the cdxCpeToCmInetAddress
            object.";
          smiv2:max-access "read-only";
          smiv2:oid "1.3.6.1.4.1.9.9.116.1.3.9.1.3";
        }

        leaf cdxCpeToCmInetAddress {
          type inet-address:InetAddress;
          description
           "This object identifies the address assigned to this cable
            modem.";
          smiv2:max-access "read-only";
          smiv2:oid "1.3.6.1.4.1.9.9.116.1.3.9.1.4";
        }

        leaf cdxCpeToCmStatusIndex {
          type int32 {
            range "1..2147483647";
          }
          description
           "An entry in docsIfCmtsCmStatusTable identifying status
            index of the cable modem which the CPE connects to.";
          reference
           "docsIfCmtsCmStatusTable from DOCS-IF-MIB";
          smiv2:max-access "read-only";
          smiv2:oid "1.3.6.1.4.1.9.9.116.1.3.9.1.5";
        }
      }
    }

    container cdxCpeIpPrefixTable {
      description
       "The table contains a list CPE's IP Prefix management
        information.";
      smiv2:oid "1.3.6.1.4.1.9.9.116.1.3.10";

      list cdxCpeIpPrefixEntry {
        key "cdxCpeIpPrefixCmMacAddress cdxCpeIpPrefixType cdxCpeIpPrefixAddress cdxCpeIpPrefixLen";
        description
         "An entry contains information of CM's MAC,
          CPE's IP prefix type, CPE's IP prefix address,
          CPE's IP prefix length and CPE's MAC address.
          An entry is created if CPE is associated with a prefix.";
        smiv2:oid "1.3.6.1.4.1.9.9.116.1.3.10.1";

        leaf cdxCpeIpPrefixCmMacAddress {
          type yang:mac-address;
          description
           "This object indicates the MAC address of the cable modem.";
          smiv2:max-access "not-accessible";
          smiv2:oid "1.3.6.1.4.1.9.9.116.1.3.10.1.1";
        }

        leaf cdxCpeIpPrefixType {
          type inet-address:InetAddressType;
          description
           "This object indicates the IP prefix type of the CPE. This is
            the type of cdxCpeIpPrefixAddress object.";
          smiv2:max-access "not-accessible";
          smiv2:oid "1.3.6.1.4.1.9.9.116.1.3.10.1.2";
        }

        leaf cdxCpeIpPrefixAddress {
          type inet-address:InetAddress {
            length "1..96";
          }
          description
           "This object indicates the IP prefix address. The type of this
            address is determined by the value of 
            cdxCpeIpPrefixType object.";
          smiv2:max-access "not-accessible";
          smiv2:oid "1.3.6.1.4.1.9.9.116.1.3.10.1.3";
        }

        leaf cdxCpeIpPrefixLen {
          type inet-address:InetAddressPrefixLength;
          description
           "This object indicates the IP prefix length of the CPE. This is
            the length of cdxCpeIpPrefixAddress object.";
          smiv2:max-access "not-accessible";
          smiv2:oid "1.3.6.1.4.1.9.9.116.1.3.10.1.4";
        }

        leaf cdxCpeIpPrefixCpeMacAddress {
          type yang:mac-address;
          description
           "This object indicates the MAC address of CPE.";
          smiv2:max-access "read-only";
          smiv2:oid "1.3.6.1.4.1.9.9.116.1.3.10.1.5";
        }

        leaf cdxCpeIpPrefixCpeType {
          type snmp-framework:SnmpAdminString;
          description
           "This object indicates the type of CPE.
            Device Type: B - CM Bridge, R - CM Router
            IP Assignment Method: D - DHCP
            the format looks like 'R/D'.";
          smiv2:max-access "read-only";
          smiv2:oid "1.3.6.1.4.1.9.9.116.1.3.10.1.6";
        }
      }
    }

    container cdxIfUpstreamChannelExtTable {
      description
       "This table contains upstream channel attributes for  
        automated Spectrum management, in addition to the ones
        provided by docsIfUpstreamChannelEntry.
        It also contains upstream channel attributes to count 
        the number of active,registered and total number of cable 
        modems on this upstream. ";
      smiv2:oid "1.3.6.1.4.1.9.9.116.1.4.1";

      list cdxIfUpstreamChannelExtEntry {
        key "ifIndex";
        description
         "Additional objects for docsIfUpstreamChannelEntry,including 
          the secondary upstream channel modulation profile,the 
          lower bound for the channel width and the number of active,
          registered and total number of cable modems on this 
          upstream channel. ";
        reference
         "Data-Over-Cable Service Interface Specifications (DOCSIS)
          Radio Frequency Interface Specification (SP-RFI-I04-980724.)
          docsIfUpstreamChannelTable in DOCS-IF-MIB.my. ";
        smiv2:oid "1.3.6.1.4.1.9.9.116.1.4.1.1";

        leaf ifIndex {
          type leafref {
            path "/if-mib:IF-MIB/if-mib:ifTable/if-mib:ifEntry/if-mib:ifIndex";
          }
        }

        leaf cdxIfUpChannelWidth {
          type int32 {
            range "0..16000000";
          }
          units "hertz";
          description
           "The lower bound for the bandwidth of this upstream channel. 
            The bandwidth specified by docsIfUpChannelWidth is used as
            the upper bound of the upstream channel. The two objects,
            docsIfUpChannelWidth and cdxIfUpChannelWidth, in 
            conjunction, define the upstream channel width range to be
            used for the automated spectrum management.
            
            This object returns 0 if the channel width is undefined 
            or unknown.
            
            For those upstreams in the linecards which do not have the
            automated spectrum management feature, this channel width
            is undefined and always has value 0. ";
          smiv2:max-access "read-write";
          smiv2:oid "1.3.6.1.4.1.9.9.116.1.4.1.1.1";
        }

        leaf cdxIfUpChannelModulationProfile {
          type uint32;
          description
           "The secondary modulation profile for the upstream channel.
            This should be a QPSK modulation profile if the primary profile 
            is QAM-16. The CMTS will switch from primary profile (QAM16) to 
            secondary profile (QPSK) depending on the noise level of a 
            particular spectrum band.
            
            This is an entry identical to the docsIfModIndex in the 
            docsIfCmtsModulationTable that describes this channel.
            This channel is further instantiated there by a grouping
            of interval usage codes which together fully describe the
            channel modulation. This object returns 0 if the
            docsIfCmtsModulationTable does not exist or is empty. ";
          smiv2:max-access "read-write";
          smiv2:oid "1.3.6.1.4.1.9.9.116.1.4.1.1.2";
        }

        leaf cdxIfUpChannelCmTotal {
          type int32 {
            range "0..8191";
          }
          description
           "The total count of cable modems on this upstream channel
            since boot.";
          smiv2:max-access "read-only";
          smiv2:oid "1.3.6.1.4.1.9.9.116.1.4.1.1.3";
        }

        leaf cdxIfUpChannelCmActive {
          type int32 {
            range "0..8191";
          }
          description
           "The count of cable modems that are active.Active cable 
            modems are recognized by the cdxCmtsCmStatusValue other  
            than offline(1). ";
          smiv2:max-access "read-only";
          smiv2:oid "1.3.6.1.4.1.9.9.116.1.4.1.1.4";
        }

        leaf cdxIfUpChannelCmRegistered {
          type int32 {
            range "0..8191";
          }
          description
           "The count of cable modems that are registered and online
            on this upstream. Registered cable modems are those
            with one of the following values:
            registrationComplete(6) of docsIfCmtsCmStatusValue OR
            online(12), kekRejected(10), onlineKekAssigned(6),
            tekRejected(11),onlineTekAssigned(7) of 
            cdxCmtsCmStatusValue.";
          smiv2:max-access "read-only";
          smiv2:oid "1.3.6.1.4.1.9.9.116.1.4.1.1.5";
        }

        leaf cdxIfUpChannelInputPowerLevel {
          type docs-if:TenthdBmV {
            range "-100..250";
          }
          description
           "The Upstream Input power level at the CMTS interface.
            This is the expected power level and is different from the
            actual power received. If not configured the default value
            is 0 dBmV and is also the optimum setting power level for
            the upstream. For FPGA line cards, the valid range
            is <-10 to 10> dBmV and for ASIC Line cards, it is 
            <-10  to 25> dBmV. ";
          smiv2:max-access "read-write";
          smiv2:oid "1.3.6.1.4.1.9.9.116.1.4.1.1.6";
        }

        leaf cdxIfUpChannelAvgUtil {
          type int32 {
            range "0..100";
          }
          units "percent";
          description
           "The average percentage of upstream channel utilization. 
            This item indicates the running average of percent
            channel utilization in CMTS upstream Mac scheduler. ";
          smiv2:max-access "read-only";
          smiv2:oid "1.3.6.1.4.1.9.9.116.1.4.1.1.7";
        }

        leaf cdxIfUpChannelAvgContSlots {
          type int32 {
            range "0..100";
          }
          units "percent";
          description
           "The average percentage of contention mini-slots. This
            item indicates the running average of percent
            contention mini-slots in CMTS upstream Mac scheduler. ";
          smiv2:max-access "read-only";
          smiv2:oid "1.3.6.1.4.1.9.9.116.1.4.1.1.8";
        }

        leaf cdxIfUpChannelRangeSlots {
          type int32 {
            range "0..100";
          }
          units "percent";
          description
           "The average percentage of initial ranging mini-slots. 
            This item indicates the running average of percent
            initial ranging mini-slots in CMTS upstream Mac
            scheduler. ";
          smiv2:max-access "read-only";
          smiv2:oid "1.3.6.1.4.1.9.9.116.1.4.1.1.9";
        }

        leaf cdxIfUpChannelNumActiveUGS {
          type uint32;
          description
           "This object indicates the number of active 
            Unsolicited Grant Service (UGS) on a given upstream.
            This would be used for the user to evaluate traffic 
            load at any given time of the day.
            
            The Unsolicited Grant Service (UGS) is designed to 
            support real-time service flows that generate fixed
            size data packets on a periodic basis. ";
          smiv2:max-access "read-only";
          smiv2:oid "1.3.6.1.4.1.9.9.116.1.4.1.1.10";
        }

        leaf cdxIfUpChannelMaxUGSLastOneHour {
          type uint32;
          description
           "This object indicates the maximum number of 
            Unsolicited Grant Service (UGS) allocated on a
            given upstream in the last one hour. This would be
            used for the user to evaluate traffic load at any
            given time of the day.
            
            The Unsolicited Grant Service (UGS) is designed to
            support real-time service flows that generate fixed
            size data packets on a periodic basis. ";
          smiv2:max-access "read-only";
          smiv2:oid "1.3.6.1.4.1.9.9.116.1.4.1.1.11";
        }

        leaf cdxIfUpChannelMinUGSLastOneHour {
          type uint32;
          description
           "This object indicates the minimum number of 
            Unsolicited Grant Service (UGS) allocated on a
            given upstream in the last one hour. This would be
            used for the user to evaluate traffic load at any
            given time of the day.
            
            The Unsolicited Grant Service (UGS) is designed to
            support real-time service flows that generate fixed
            size data packets on a periodic basis. ";
          smiv2:max-access "read-only";
          smiv2:oid "1.3.6.1.4.1.9.9.116.1.4.1.1.12";
        }

        leaf cdxIfUpChannelAvgUGSLastOneHour {
          type uint32;
          description
           "This object indicates the average number of 
            Unsolicited Grant Service (UGS) allocated on a
            given upstream in the last one hour. This would be
            used for the user to evaluate traffic load at any
            given time of the day.
            
            The Unsolicited Grant Service (UGS) is designed to
            support real-time service flows that generate fixed
            size data packets on a periodic basis. ";
          smiv2:max-access "read-only";
          smiv2:oid "1.3.6.1.4.1.9.9.116.1.4.1.1.13";
        }

        leaf cdxIfUpChannelMaxUGSLastFiveMins {
          type uint32;
          description
           "This object indicates the maximum number of 
            Unsolicited Grant Service (UGS) allocated on a
            given upstream in the last five minutes. This would 
            be used for the user to evaluate traffic load at
            any given time of the day.
            
            The Unsolicited Grant Service (UGS) is designed to
            support real-time service flows that generate fixed
            size data packets on a periodic basis. ";
          smiv2:max-access "read-only";
          smiv2:oid "1.3.6.1.4.1.9.9.116.1.4.1.1.14";
        }

        leaf cdxIfUpChannelMinUGSLastFiveMins {
          type uint32;
          description
           "This object indicates the minimum number of 
            Unsolicited Grant Service (UGS) allocated on a
            given upstream in the last five minutes. This would 
            be used for the user to evaluate traffic load at
            any given time of the day.
            
            The Unsolicited Grant Service (UGS) is designed to
            support real-time service flows that generate fixed
            size data packets on a periodic basis. ";
          smiv2:max-access "read-only";
          smiv2:oid "1.3.6.1.4.1.9.9.116.1.4.1.1.15";
        }

        leaf cdxIfUpChannelAvgUGSLastFiveMins {
          type uint32;
          description
           "This object indicates the average number of 
            Unsolicited Grant Service (UGS) allocated on a
            given upstream in the last five minutes. This would 
            be used for the user to evaluate traffic load at
            any given time of the day.
            
            The Unsolicited Grant Service (UGS) is designed to
            support real-time service flows that generate fixed
            size data packets on a periodic basis. ";
          smiv2:max-access "read-only";
          smiv2:oid "1.3.6.1.4.1.9.9.116.1.4.1.1.16";
        }
      }
    }

    container cdxWBResilCmTable {
      description
       "This table contains information about partial service cable
        modems (CM), including both downstream and upstream partial
        service modems.";
      smiv2:oid "1.3.6.1.4.1.9.9.116.1.5.13";

      list cdxWBResilCmEntry {
        key "cdxWBResilCmIndex";
        description
         "The list contains information for a partial service cable modem
          (CM).
          
          Provided the following information for a partial service cable
          modem:
          How many downstream channels in total;
          How many upstream channels in total;
          How many active downstream channels;
          How many active upstream channels;
          Which downstream channels are in partial service mode;
          Which upstream channels are in partial service mode;";
        smiv2:oid "1.3.6.1.4.1.9.9.116.1.5.13.1";

        leaf cdxWBResilCmIndex {
          type uint32 {
            range "1..4294967295";
          }
          description
           "This attribute uniquely identifies a CM.  The CMTS
            must assign a single id value for each CM MAC address seen
            by the CMTS.  The CMTS should ensure that the association
            between an Id and MAC Address remains constant
            during CMTS uptime.";
          smiv2:max-access "not-accessible";
          smiv2:oid "1.3.6.1.4.1.9.9.116.1.5.13.1.1";
        }

        leaf cdxWBResilCmMacAddr {
          type yang:mac-address;
          description
           "This attribute represents the MAC address of the CM.
            If the CM has multiple MAC addresses, this is the MAC
            address associated with the MAC Domain interface.";
          smiv2:max-access "read-only";
          smiv2:oid "1.3.6.1.4.1.9.9.116.1.5.13.1.2";
        }

        leaf cdxWBResilCmTotalDsNum {
          type uint32;
          description
           "Total downstream channel number of the CM.";
          smiv2:max-access "read-only";
          smiv2:oid "1.3.6.1.4.1.9.9.116.1.5.13.1.3";
        }

        leaf cdxWBResilCmTotalUsNum {
          type uint32;
          description
           "Total upstream channel number of the CM.";
          smiv2:max-access "read-only";
          smiv2:oid "1.3.6.1.4.1.9.9.116.1.5.13.1.4";
        }

        leaf cdxWBResilCmCurrentDsNum {
          type uint32;
          description
           "Current active downstream channel number, it's the total
            downstream channel minus downstream partial service channel
            number.";
          smiv2:max-access "read-only";
          smiv2:oid "1.3.6.1.4.1.9.9.116.1.5.13.1.5";
        }

        leaf cdxWBResilCmCurrentUsNum {
          type uint32;
          description
           "Current active upstream channel number, it's the total upstream
            channel minus upstream partial service channel number.";
          smiv2:max-access "read-only";
          smiv2:oid "1.3.6.1.4.1.9.9.116.1.5.13.1.6";
        }

        leaf cdxWBResilCmImpairedDsChIndex {
          type snmp-target:SnmpTagList;
          description
           "Impaired downstream channel index list.
            The index in list is rf channel ifIndex.
            If there's no downstream channel impaired, return empty.
            The output looks like: '137000 137001 137002'.";
          smiv2:defval "";
          smiv2:max-access "read-only";
          smiv2:oid "1.3.6.1.4.1.9.9.116.1.5.13.1.7";
        }

        leaf cdxWBResilCmImpairedUsChIndex {
          type snmp-target:SnmpTagList;
          description
           "Impaired upstream channel index list.
            The index in list is upstream channel ifIndex.
            If there's no upstream channel impaired, return empty.
            The output looks like: '196408 196409 196410'.";
          smiv2:defval "";
          smiv2:max-access "read-only";
          smiv2:oid "1.3.6.1.4.1.9.9.116.1.5.13.1.8";
        }
      }
    }

    container cdxRFtoPrimaryChannelMappingTable {
      description
       "This table contains information of the mapping of
        the physical RF channels to the primary RF channels.";
      smiv2:oid "1.3.6.1.4.1.9.9.116.1.6.1";

      list cdxRFtoPrimaryChannelMappingEntry {
        key "ifIndex";
        description
         "An Entry provides the association between the physical
          RF channels and the primary RF Channels.";
        smiv2:oid "1.3.6.1.4.1.9.9.116.1.6.1.1";

        leaf ifIndex {
          type leafref {
            path "/if-mib:IF-MIB/if-mib:ifTable/if-mib:ifEntry/if-mib:ifIndex";
          }
        }

        leaf cdxPrimaryChannelIfIndex {
          type if-mib:InterfaceIndex;
          description
           "The ifIndex of the primary channel interface.";
          smiv2:max-access "read-only";
          smiv2:oid "1.3.6.1.4.1.9.9.116.1.6.1.1.1";
        }
      }
    }

    container cdxPrimaryChanneltoRFMappingTable {
      description
       "This table contains information of the mapping of
        the primary RF channels to the physical RF channels.";
      smiv2:oid "1.3.6.1.4.1.9.9.116.1.6.2";

      list cdxPrimaryChanneltoRFMappingEntry {
        key "ifIndex";
        description
         "An Entry provides the association between the primary
          RF channels and the physical RF Channels.";
        smiv2:oid "1.3.6.1.4.1.9.9.116.1.6.2.1";

        leaf ifIndex {
          type leafref {
            path "/if-mib:IF-MIB/if-mib:ifTable/if-mib:ifEntry/if-mib:ifIndex";
          }
        }

        leaf cdxPhysicalRFIfIndex {
          type if-mib:InterfaceIndex;
          description
           "The ifIndex of the physical RF channel interface.";
          smiv2:max-access "read-only";
          smiv2:oid "1.3.6.1.4.1.9.9.116.1.6.2.1.1";
        }
      }
    }

    container cdxCmtsMtcCmTable {
      description
       "This table contains CM management information of Transmit
        Channel Set(TCS) in the system.";
      smiv2:oid "1.3.6.1.4.1.9.9.116.1.7.1";

      list cdxCmtsMtcCmEntry {
        key "ifIndex cdxCmtsMtcTcsId";
        description
         "An entry provides the CM statistics and management
          information of a specific TCS. The interface populated in this
          table is of ifType = docsCableMaclayer(127).";
        smiv2:oid "1.3.6.1.4.1.9.9.116.1.7.1.1";

        leaf ifIndex {
          type leafref {
            path "/if-mib:IF-MIB/if-mib:ifTable/if-mib:ifEntry/if-mib:ifIndex";
          }
        }

        leaf cdxCmtsMtcTcsId {
          type docs-if3:ChSetId;
          description
           "This object indicates the Id of the Transmit Channel Set.";
          smiv2:max-access "not-accessible";
          smiv2:oid "1.3.6.1.4.1.9.9.116.1.7.1.1.1";
        }

        leaf cdxCmtsMtcCmTotal {
          type uint32;
          description
           "This object indicates the total number of cable modems
            which use this TCS in the MAC domain.";
          smiv2:max-access "read-only";
          smiv2:oid "1.3.6.1.4.1.9.9.116.1.7.1.1.2";
        }

        leaf cdxCMtsMtcCmOperational {
          type uint32;
          description
           "This object indicates the number of operational cable
            modems which uses this TCS in the MAC domain.";
          smiv2:max-access "read-only";
          smiv2:oid "1.3.6.1.4.1.9.9.116.1.7.1.1.3";
        }

        leaf cdxCmtsMtcCmRegistered {
          type uint32;
          description
           "This object indicates the number of registered cable
            modems which use this TCS in the MAC domain.";
          smiv2:max-access "read-only";
          smiv2:oid "1.3.6.1.4.1.9.9.116.1.7.1.1.4";
        }

        leaf cdxCmtsMtcCmUnregistered {
          type uint32;
          description
           "This object indicates the number of unregistered cable
            modem which use this TCS in the MAC domain.";
          smiv2:max-access "read-only";
          smiv2:oid "1.3.6.1.4.1.9.9.116.1.7.1.1.5";
        }

        leaf cdxCmtsMtcCmOffline {
          type uint32;
          description
           "This object indicates the number of offline cable modems
            which uses this TCS in the MAC domain.";
          smiv2:max-access "read-only";
          smiv2:oid "1.3.6.1.4.1.9.9.116.1.7.1.1.6";
        }

        leaf cdxCmtsMtcCmWideband {
          type uint32;
          description
           "This object indicates the number of operational cable
            modems which are in wideband state and use this TCS in
            the MAC domain.";
          smiv2:max-access "read-only";
          smiv2:oid "1.3.6.1.4.1.9.9.116.1.7.1.1.7";
        }

        leaf cdxCmtsMtcUpstreamBondGrp {
          type CISCO-DOCS-EXT-MIB:CdxUpstreamBondGrpList;
          description
           "This object specifies the upstream channel bonding group.";
          smiv2:max-access "read-only";
          smiv2:oid "1.3.6.1.4.1.9.9.116.1.7.1.1.8";
        }
      }
    }

    container cdxCmtsUscbSflowTable {
      description
       "This table contains the Upstream Channel Bonding
        Service Flow management information.";
      smiv2:oid "1.3.6.1.4.1.9.9.116.1.7.2";

      list cdxCmtsUscbSflowEntry {
        key "ifIndex cdxCmtsUsBondingGrpId";
        description
         "A entry contains the Service Flow statistics for a specific
          Upstream Channel Bonding group. The interface populated in this
          table is of ifType = docsCableMaclayer(127).";
        smiv2:oid "1.3.6.1.4.1.9.9.116.1.7.2.1";

        leaf ifIndex {
          type leafref {
            path "/if-mib:IF-MIB/if-mib:ifTable/if-mib:ifEntry/if-mib:ifIndex";
          }
        }

        leaf cdxCmtsUsBondingGrpId {
          type uint32 {
            range "1..4294967295";
          }
          description
           "This object indicates upstream bonding group
            identifier within the MAC Domain.";
          smiv2:max-access "not-accessible";
          smiv2:oid "1.3.6.1.4.1.9.9.116.1.7.2.1.1";
        }

        leaf cdxCmtsUscbSfTotal {
          type uint32;
          description
           "This object indicates the total number of service flows
            which use this upstream channel bonding group.";
          smiv2:max-access "read-only";
          smiv2:oid "1.3.6.1.4.1.9.9.116.1.7.2.1.2";
        }

        leaf cdxCmtsUscbSfPri {
          type uint32;
          description
           "This object indicates the total number of  primary
            service flows which use this upstream channel bonding group.";
          smiv2:max-access "read-only";
          smiv2:oid "1.3.6.1.4.1.9.9.116.1.7.2.1.3";
        }

        leaf cdxCmtsUscbStaticSfBe {
          type uint32;
          description
           "This object indicates the number of static BE service
            flows which use this upstream channel bonding group.";
          smiv2:max-access "read-only";
          smiv2:oid "1.3.6.1.4.1.9.9.116.1.7.2.1.4";
        }

        leaf cdxCmtsUscbStaticSfUgs {
          type uint32;
          description
           "This object indicates the number of static UGS service
            flows which use this upstream channel bonding group.";
          smiv2:max-access "read-only";
          smiv2:oid "1.3.6.1.4.1.9.9.116.1.7.2.1.5";
        }

        leaf cdxCmtsUscbStaticSfUgsad {
          type uint32;
          description
           "This object indicates the number of static UGS-AD service
            flows which use this upstream channel bonding group.";
          smiv2:max-access "read-only";
          smiv2:oid "1.3.6.1.4.1.9.9.116.1.7.2.1.6";
        }

        leaf cdxCmtsUscbStaticSfRtps {
          type uint32;
          description
           "This object indicates the number of static RTPS service
            flows which use this upstream channel bonding group.";
          smiv2:max-access "read-only";
          smiv2:oid "1.3.6.1.4.1.9.9.116.1.7.2.1.7";
        }

        leaf cdxCmtsUscbStaticSfNrtps {
          type uint32;
          description
           "This object indicates the number of static NRTPS service
            flows which use this upstream channel bonding group.";
          smiv2:max-access "read-only";
          smiv2:oid "1.3.6.1.4.1.9.9.116.1.7.2.1.8";
        }

        leaf cdxCmtsUscbDynSfBe {
          type uint32;
          description
           "This object indicates the number of dynamic BE service
            flows which use this upstream channel bonding group.";
          smiv2:max-access "read-only";
          smiv2:oid "1.3.6.1.4.1.9.9.116.1.7.2.1.9";
        }

        leaf cdxCmtsUscbDynSfUgs {
          type uint32;
          description
           "This object indicates the number of dynamic UGS service
            flows which use this upstream channel bonding group.";
          smiv2:max-access "read-only";
          smiv2:oid "1.3.6.1.4.1.9.9.116.1.7.2.1.10";
        }

        leaf cdxCmtsUscbDynSfUgsad {
          type uint32;
          description
           "This object indicates the number of dynamic UGS-Ad service
            flows which use this upstream channel bonding group.";
          smiv2:max-access "read-only";
          smiv2:oid "1.3.6.1.4.1.9.9.116.1.7.2.1.11";
        }

        leaf cdxCmtsUscbDynSfRtps {
          type uint32;
          description
           "This object indicates the number of dynamic RTPS service
            flows which use this upstream channel bonding group.";
          smiv2:max-access "read-only";
          smiv2:oid "1.3.6.1.4.1.9.9.116.1.7.2.1.12";
        }

        leaf cdxCmtsUscbDynSfNrtps {
          type uint32;
          description
           "This object indicates the number of dynamic NRTPS service
            flows which use this upstream channel bonding group.";
          smiv2:max-access "read-only";
          smiv2:oid "1.3.6.1.4.1.9.9.116.1.7.2.1.13";
        }

        leaf cdxCmtsUscbDescr {
          type snmp-framework:SnmpAdminString;
          description
           "This object indicates the description of upstream channel
            bonding group.";
          smiv2:max-access "read-write";
          smiv2:oid "1.3.6.1.4.1.9.9.116.1.7.2.1.14";
        }
      }
    }

    container cdxRPDGS7KTable {
      description
       "The cdxRPDGS7KTable contains the attributes of GS7K. 
        An Entry exists for each instance. 
        It is indexed by GS7K's MacAddress.";
      smiv2:oid "1.3.6.1.4.1.9.9.116.1.9.1";

      list cdxRPDGS7KEntry {
        key "cdxRPDGS7KMacAddress";
        description
         "The list of statistics for all the sensor, 
          such as volatage, the state of TriSwitch.";
        smiv2:oid "1.3.6.1.4.1.9.9.116.1.9.1.1";

        leaf cdxRPDGS7KMacAddress {
          type yang:mac-address;
          description
           "This is MacAddress of RPDGS7K which is used for index";
          smiv2:max-access "read-only";
          smiv2:oid "1.3.6.1.4.1.9.9.116.1.9.1.1.1";
        }

        leaf cdxRPDGS7KPS1p24v {
          type int32 {
            range "0..3000";
          }
          units "0.01VDC";
          description
           "This is the Object of RPDGS7KPS1p24v";
          smiv2:max-access "read-only";
          smiv2:oid "1.3.6.1.4.1.9.9.116.1.9.1.1.2";
        }

        leaf cdxRPDGS7KPS1p8v {
          type int32 {
            range "0..1000";
          }
          units "0.01VDC";
          description
           "This is the Object of RPDGS7KPS1p8v";
          smiv2:max-access "read-only";
          smiv2:oid "1.3.6.1.4.1.9.9.116.1.9.1.1.3";
        }

        leaf cdxRPDGS7KPS1p5v {
          type int32 {
            range "0..625";
          }
          units "0.01VDC";
          description
           "This is the Object of RPDGS7KPS1p5v";
          smiv2:max-access "read-only";
          smiv2:oid "1.3.6.1.4.1.9.9.116.1.9.1.1.4";
        }

        leaf cdxRPDGS7KPS1n6v {
          type int32 {
            range "0..800";
          }
          units "0.01VDC";
          description
           "This is the Object of RPDGS7KPS1n6v";
          smiv2:max-access "read-only";
          smiv2:oid "1.3.6.1.4.1.9.9.116.1.9.1.1.5";
        }

        leaf cdxRPDGS7KPS1AC {
          type int32 {
            range "300..2000";
          }
          units "0.1VAC";
          description
           "This is the Object of RPDGS7KPS1AC";
          smiv2:max-access "read-only";
          smiv2:oid "1.3.6.1.4.1.9.9.116.1.9.1.1.6";
        }

        leaf cdxRPDGS7KPS2p24v {
          type int32 {
            range "0..3000";
          }
          units "0.01VDC";
          description
           "RPDGS7KPS2p24v";
          smiv2:max-access "read-only";
          smiv2:oid "1.3.6.1.4.1.9.9.116.1.9.1.1.7";
        }

        leaf cdxRPDGS7KPS2p8v {
          type int32 {
            range "0..1000";
          }
          units "0.01VDC";
          description
           "This is the Object of RPDGS7KPS2p8v";
          smiv2:max-access "read-only";
          smiv2:oid "1.3.6.1.4.1.9.9.116.1.9.1.1.8";
        }

        leaf cdxRPDGS7KPS2p5v {
          type int32 {
            range "0..625";
          }
          units "0.01VDC";
          description
           "This is the Object of RPDGS7KPS2p5v";
          smiv2:max-access "read-only";
          smiv2:oid "1.3.6.1.4.1.9.9.116.1.9.1.1.9";
        }

        leaf cdxRPDGS7KPS2n6v {
          type int32 {
            range "0..800";
          }
          units "0.01VDC";
          description
           "This is the Object of RPDGS7KPS2n6v";
          smiv2:max-access "read-only";
          smiv2:oid "1.3.6.1.4.1.9.9.116.1.9.1.1.10";
        }

        leaf cdxRPDGS7KPS2AC {
          type int32 {
            range "300..2000";
          }
          units "0.1VAC";
          description
           "This is the Object of RPDGS7KPS2AC";
          smiv2:max-access "read-only";
          smiv2:oid "1.3.6.1.4.1.9.9.116.1.9.1.1.11";
        }

        leaf cdxRPDGS7KTx1OptPower {
          type int32 {
            range "0..300";
          }
          units "0.01mW";
          description
           "This is the Object of RPDGS7K Tx4 Opt Power";
          smiv2:max-access "read-only";
          smiv2:oid "1.3.6.1.4.1.9.9.116.1.9.1.1.12";
        }

        leaf cdxRPDGS7KRx1OptPower {
          type int32 {
            range "0..300";
          }
          units "0.01mW";
          description
           "This is the Object of RPDGS7K Rx4 Opt Power";
          smiv2:max-access "read-only";
          smiv2:oid "1.3.6.1.4.1.9.9.116.1.9.1.1.13";
        }

        leaf cdxRPDGS7KTriSwitch {
          type enumeration {
            enum "low" {
              value "1";
            }
            enum "high" {
              value "2";
            }
            enum "pad" {
              value "3";
            }
          }
          description
           "This is the Object of RPDGS7K TriSwitch,
            The relationship which the number indicates is   
            low(1) for -6dB
            high(2) for 0dB
            pad(3) for off";
          smiv2:max-access "read-write";
          smiv2:oid "1.3.6.1.4.1.9.9.116.1.9.1.1.14";
        }

        leaf cdxRPDGS7KTamp {
          type enumeration {
            enum "intact" {
              value "1";
            }
            enum "compromised" {
              value "2";
            }
          }
          description
           "This is the Object of RPDGS7K Tamp";
          smiv2:max-access "read-only";
          smiv2:oid "1.3.6.1.4.1.9.9.116.1.9.1.1.15";
        }
      }
    }

    container cdxBundleIpHelperTable {
      description
       "A list of cable helper entries on Bundle/Sub-Bundle interface.";
      smiv2:oid "1.3.6.1.4.1.9.9.116.1.10.1";

      list cdxBundleIpHelperEntry {
        key "ifIndex cdxBundleHelperAddr";
        description
         "The conceptual row of cdxBundleIpHelperEntry.
          An instance exists for Cable Bundle/Sub-Bundle Interface.";
        smiv2:oid "1.3.6.1.4.1.9.9.116.1.10.1.1";

        leaf ifIndex {
          type leafref {
            path "/if-mib:IF-MIB/if-mib:ifTable/if-mib:ifEntry/if-mib:ifIndex";
          }
        }

        leaf cdxBundleHelperAddr {
          type inet-address:InetAddress;
          description
           "Cable helper IP address";
          smiv2:max-access "not-accessible";
          smiv2:oid "1.3.6.1.4.1.9.9.116.1.10.1.1.1";
        }

        leaf cdxBundleHelperType {
          type bits {
            bit dva {
              position "0";
            }
            bit ps {
              position "2";
            }
            bit stb {
              position "3";
            }
            bit mta {
              position "4";
            }
            bit customized {
              position "5";
            }
            bit host {
              position "6";
            }
            bit cm {
              position "7";
            }
          }
          description
           "This object describes which kind of device will be associated
            to a cable helper. The entity may support more than one device 
            class. For example, the entity supports both host and mta.
            Therefore, bit 1 and bit 3 are set to 1 for this object. If 
            all bits are cleared, the entity supports all device types.
            Note that BITS are encoded most significant bit first.";
          smiv2:max-access "read-only";
          smiv2:oid "1.3.6.1.4.1.9.9.116.1.10.1.1.2";
        }
      }
    }

    container cdxBundleIPv6DHCPRelayTable {
      description
       "Ipv6 dhcp relay configurations on Bundle/Sub-Bundle interface.";
      smiv2:oid "1.3.6.1.4.1.9.9.116.1.11.1";

      list cdxBundleIPv6DHCPRelayEntry {
        key "ifIndex";
        description
         "The conceptual row of cdxBundleIPv6DHCPRelayTable.
          An instance exist for the Bundle/Sub-Bundle interface.";
        smiv2:oid "1.3.6.1.4.1.9.9.116.1.11.1.1";

        leaf ifIndex {
          type leafref {
            path "/if-mib:IF-MIB/if-mib:ifTable/if-mib:ifEntry/if-mib:ifIndex";
          }
        }

        leaf cdxBundleIPv6DHCPRelayInsertVSSOption {
          type boolean;
          description
           "Insert VSS option in Relay-Forward Messages";
          smiv2:defval "false";
          smiv2:max-access "read-only";
          smiv2:oid "1.3.6.1.4.1.9.9.116.1.11.1.1.1";
        }

        leaf cdxBundleIPv6DHCPRelayTrustToRelayReply {
          type boolean;
          description
           "Interface is trusted to process relay-replies";
          smiv2:defval "false";
          smiv2:max-access "read-only";
          smiv2:oid "1.3.6.1.4.1.9.9.116.1.11.1.1.2";
        }

        leaf cdxBundleIPv6DHDPRelaySourceIfname {
          type snmp-framework:SnmpAdminString;
          description
           "Source interface name for IPv6 DHCP relayed messages";
          smiv2:max-access "read-only";
          smiv2:oid "1.3.6.1.4.1.9.9.116.1.11.1.1.3";
        }
      }
    }

    container cdxBundleIPv6DHCPRelayDestTable {
      description
       " A list of IPv6 DHCP relay destination entries
        on Cable Bundle/Sub-Bundle interfaces.";
      smiv2:oid "1.3.6.1.4.1.9.9.116.1.11.2";

      list cdxBundleIPv6DHCPRelayDestEntry {
        key "ifIndex cdxBundleIPv6DHCPRelayDestOutIfVrfIndex cdxBundleIPv6DHCPRelayDestAddr cdxBundleIPv6DHCPRelayDestOutIfIndex";
        description
         "The conceptual row of cdxBundleIPv6DHCPRelayDestTable.
          An instance exists for the Cable Bundle/Sub-Bundle interface.";
        smiv2:oid "1.3.6.1.4.1.9.9.116.1.11.2.1";

        leaf ifIndex {
          type leafref {
            path "/if-mib:IF-MIB/if-mib:ifTable/if-mib:ifEntry/if-mib:ifIndex";
          }
        }

        leaf cdxBundleIPv6DHCPRelayDestOutIfVrfIndex {
          type uint32 {
            range "0..65535";
          }
          description
           "The vrf identifier that the cdxBundleIPv6DHCPRelayDestOutIfIndex
            belongs to, it is assigned to each VRF and is used to
            uniquely identify it, if it is zero, means in global vrf.";
          smiv2:max-access "not-accessible";
          smiv2:oid "1.3.6.1.4.1.9.9.116.1.11.2.1.1";
        }

        leaf cdxBundleIPv6DHCPRelayDestAddr {
          type inet-address:InetAddress;
          description
           "IPv6 DHCP relay destination address";
          smiv2:max-access "not-accessible";
          smiv2:oid "1.3.6.1.4.1.9.9.116.1.11.2.1.2";
        }

        leaf cdxBundleIPv6DHCPRelayDestOutIfIndex {
          type if-mib:InterfaceIndexOrZero;
          description
           "The snmp ifIndex of the IPv6 DHCP relay destination output interface.
            If the ifIndex is 0, it means there is no output interface specified";
          smiv2:max-access "not-accessible";
          smiv2:oid "1.3.6.1.4.1.9.9.116.1.11.2.1.3";
        }

        leaf cdxBundleIPv6DHCPRelayDestSourceAddress {
          type inet-address:InetAddressIPv6;
          description
           "IPv6 DHCP relay destination source address";
          smiv2:max-access "read-only";
          smiv2:oid "1.3.6.1.4.1.9.9.116.1.11.2.1.4";
        }

        leaf cdxBundleIPv6DHCPRelayDestLinkAddress {
          type inet-address:InetAddressIPv6;
          description
           "IPv6 DHCP relay destination link address";
          smiv2:max-access "read-only";
          smiv2:oid "1.3.6.1.4.1.9.9.116.1.11.2.1.5";
        }
      }
    }
  }

  notification cdxCmtsCmOnOffNotification {
    description
     "This notification indicates that the cable modem coming online
      and going offline. A notification will be sent from CMTS for 
      a cable modem status changing to online or offline
      within the interval specified in cdxCmtsCmOnOffTrapInterval. ";
    smiv2:oid "1.3.6.1.4.1.9.9.116.2.0.1";

    container object-1 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }

    container object-2 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusInetAddressType {
        type leafref {
          path "/docs-if:DOCS-IF-MIB/docs-if:docsIfCmtsCmStatusTable/docs-if:docsIfCmtsCmStatusEntry/docs-if:docsIfCmtsCmStatusInetAddressType";
        }
      }
    }

    container object-3 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusInetAddress {
        type leafref {
          path "/docs-if:DOCS-IF-MIB/docs-if:docsIfCmtsCmStatusTable/docs-if:docsIfCmtsCmStatusEntry/docs-if:docsIfCmtsCmStatusInetAddress";
        }
      }
    }

    container object-4 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusDownChannelIfIndex {
        type leafref {
          path "/docs-if:DOCS-IF-MIB/docs-if:docsIfCmtsCmStatusTable/docs-if:docsIfCmtsCmStatusEntry/docs-if:docsIfCmtsCmStatusDownChannelIfIndex";
        }
      }
    }

    container object-5 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusUpChannelIfIndex {
        type leafref {
          path "/docs-if:DOCS-IF-MIB/docs-if:docsIfCmtsCmStatusTable/docs-if:docsIfCmtsCmStatusEntry/docs-if:docsIfCmtsCmStatusUpChannelIfIndex";
        }
      }
    }

    container object-6 {

      leaf cdxCmCpeMacAddress {
        type leafref {
          path "/CISCO-DOCS-EXT-MIB:CISCO-DOCS-EXT-MIB/CISCO-DOCS-EXT-MIB:cdxCmCpeTable/CISCO-DOCS-EXT-MIB:cdxCmCpeEntry/CISCO-DOCS-EXT-MIB:cdxCmCpeMacAddress";
        }
      }

      leaf cdxCmCpeCmtsServiceId {
        type leafref {
          path "/CISCO-DOCS-EXT-MIB:CISCO-DOCS-EXT-MIB/CISCO-DOCS-EXT-MIB:cdxCmCpeTable/CISCO-DOCS-EXT-MIB:cdxCmCpeEntry/CISCO-DOCS-EXT-MIB:cdxCmCpeCmtsServiceId";
        }
      }
    }

    container object-7 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf cdxCmtsCmStatusValue {
        type leafref {
          path "/CISCO-DOCS-EXT-MIB:CISCO-DOCS-EXT-MIB/CISCO-DOCS-EXT-MIB:cdxCmtsCmStatusExtTable/CISCO-DOCS-EXT-MIB:cdxCmtsCmStatusExtEntry/CISCO-DOCS-EXT-MIB:cdxCmtsCmStatusValue";
        }
      }
    }
  }

  notification cdxCmtsCmChOverNotification {
    description
     "This notification is sent at the completion of a CMTS 
      channel override operation if 
      cdxCmtsCmChOverTrapOnCompletion is true in the
      original entry.
      
      Once a channel override operation has been activated, it 
      cannot be stopped.  That is, it will run until either the 
      CMTS has generated downstream frequency and/or upstream 
      channel override fields in the RNG-RSP message sent to a 
      cable modem or 
      cdxCmtsCmChOverTimeExpiration time expired.
      In either case, the operation is completed. State in the 
      cdxCmtsCmChOverState object will tell in which 
      condition the operation is completed. ";
    smiv2:oid "1.3.6.1.4.1.9.9.116.2.0.2";

    container object-1 {

      leaf cdxCmtsCmChOverSerialNumber {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverSerialNumber";
        }
      }

      leaf cdxCmtsCmChOverMacAddress {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverMacAddress";
        }
      }
    }

    container object-2 {

      leaf cdxCmtsCmChOverSerialNumber {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverSerialNumber";
        }
      }

      leaf cdxCmtsCmChOverDownFrequency {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverDownFrequency";
        }
      }
    }

    container object-3 {

      leaf cdxCmtsCmChOverSerialNumber {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverSerialNumber";
        }
      }

      leaf cdxCmtsCmChOverUpChannelId {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverUpChannelId";
        }
      }
    }

    container object-4 {

      leaf cdxCmtsCmChOverSerialNumber {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverSerialNumber";
        }
      }

      leaf cdxCmtsCmChOverOpInitiatedTime {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverOpInitiatedTime";
        }
      }
    }

    container object-5 {

      leaf cdxCmtsCmChOverSerialNumber {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverSerialNumber";
        }
      }

      leaf cdxCmtsCmChOverState {
        type leafref {
          path "/CISCO-DOCS-EXT-MIB:CISCO-DOCS-EXT-MIB/CISCO-DOCS-EXT-MIB:cdxCmtsCmChOverTable/CISCO-DOCS-EXT-MIB:cdxCmtsCmChOverEntry/CISCO-DOCS-EXT-MIB:cdxCmtsCmChOverState";
        }
      }
    }
  }

  notification cdxCmtsCmDMICLockNotification {
    description
     "This notification is sent whenever a modem is locked because
      it failed the Dynamic Message Integrity Check.";
    smiv2:oid "1.3.6.1.4.1.9.9.116.2.0.3";

    container object-1 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }
  }

  notification cdxWBResilRFDown {
    description
     "This notification indicates that a RF channel changed state to
      logical DOWN state.";
    smiv2:oid "1.3.6.1.4.1.9.9.116.2.0.4";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf ifDescr {
        type leafref {
          path "/if-mib:IF-MIB/if-mib:ifTable/if-mib:ifEntry/if-mib:ifDescr";
        }
      }
    }

    container object-3 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }
  }

  notification cdxWBResilRFUp {
    description
     "This notification indicates that a RF channel changed state to
      logical UP state.";
    smiv2:oid "1.3.6.1.4.1.9.9.116.2.0.5";

    container object-1 {

      leaf ifIndex {
        type leafref {
          path "/if-mib:IF-MIB/if-mib:ifTable/if-mib:ifEntry/if-mib:ifIndex";
        }
      }
    }

    container object-2 {

      leaf ifIndex {
        type leafref {
          path "/if-mib:IF-MIB/if-mib:ifTable/if-mib:ifEntry/if-mib:ifIndex";
        }
      }

      leaf ifDescr {
        type leafref {
          path "/if-mib:IF-MIB/if-mib:ifTable/if-mib:ifEntry/if-mib:ifDescr";
        }
      }
    }

    container object-3 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }
  }

  notification cdxWBResilCMPartialServiceNotif {
    description
     "This notification indicates that a Cable Modem  is in partial
      service. Object docsIfCmtsCmStatusDownChannelIfIndex 
      	     represents the target wideband/narrowband ifindex.";
    smiv2:oid "1.3.6.1.4.1.9.9.116.2.0.6";

    container object-1 {

      leaf ifIndex {
        type leafref {
          path "/if-mib:IF-MIB/if-mib:ifTable/if-mib:ifEntry/if-mib:ifIndex";
        }
      }
    }

    container object-2 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }

    container object-3 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusDownChannelIfIndex {
        type leafref {
          path "/docs-if:DOCS-IF-MIB/docs-if:docsIfCmtsCmStatusTable/docs-if:docsIfCmtsCmStatusEntry/docs-if:docsIfCmtsCmStatusDownChannelIfIndex";
        }
      }
    }

    container object-4 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }

    container object-5 {

      leaf cdxWBResilUpdateTime {
        type snmpv2-tc:DateAndTime;
        description
         "This object indicates the time when CMTS receives the
          latest wideband resiliency event.";
        smiv2:max-access "accessible-for-notify";
        smiv2:oid "1.3.6.1.4.1.9.9.116.1.5.9";
      }
    }

    container object-6 {

      leaf cdxWBResilCmIndex {
        type leafref {
          path "/CISCO-DOCS-EXT-MIB:CISCO-DOCS-EXT-MIB/CISCO-DOCS-EXT-MIB:cdxWBResilCmTable/CISCO-DOCS-EXT-MIB:cdxWBResilCmEntry/CISCO-DOCS-EXT-MIB:cdxWBResilCmIndex";
        }
      }

      leaf cdxWBResilCmImpairedDsChIndex {
        type leafref {
          path "/CISCO-DOCS-EXT-MIB:CISCO-DOCS-EXT-MIB/CISCO-DOCS-EXT-MIB:cdxWBResilCmTable/CISCO-DOCS-EXT-MIB:cdxWBResilCmEntry/CISCO-DOCS-EXT-MIB:cdxWBResilCmImpairedDsChIndex";
        }
      }
    }
  }

  notification cdxWBResilCMFullServiceNotif {
    description
     "This notification indicates that a Cable Modem  is recovered
      from partial service. Object docsIfCmtsCmStatusDownChannelIfIndex
      	     represents the target wideband/narrowband ifindex.";
    smiv2:oid "1.3.6.1.4.1.9.9.116.2.0.7";

    container object-1 {

      leaf ifIndex {
        type leafref {
          path "/if-mib:IF-MIB/if-mib:ifTable/if-mib:ifEntry/if-mib:ifIndex";
        }
      }
    }

    container object-2 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }

    container object-3 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusDownChannelIfIndex {
        type leafref {
          path "/docs-if:DOCS-IF-MIB/docs-if:docsIfCmtsCmStatusTable/docs-if:docsIfCmtsCmStatusEntry/docs-if:docsIfCmtsCmStatusDownChannelIfIndex";
        }
      }
    }

    container object-4 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }

    container object-5 {

      leaf cdxWBResilUpdateTime {
        type snmpv2-tc:DateAndTime;
        description
         "This object indicates the time when CMTS receives the
          latest wideband resiliency event.";
        smiv2:max-access "accessible-for-notify";
        smiv2:oid "1.3.6.1.4.1.9.9.116.1.5.9";
      }
    }
  }

  notification cdxWBResilEvent {
    description
     "This notification indicates that a wideband resiliency event is
      received by CMTS.";
    smiv2:oid "1.3.6.1.4.1.9.9.116.2.0.8";

    container object-1 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }

    container object-2 {

      leaf cdxWBResilEventType {
        type enumeration {
          enum "cmEventMddTimeout" {
            value "1";
          }
          enum "cmEventQamFecFailure" {
            value "2";
          }
          enum "cmEventMddRecovery" {
            value "3";
          }
          enum "cmEventQamFecRecovery" {
            value "4";
          }
        }
        description
         "This object indicates the type of the event 
          received by CMTS.";
        smiv2:max-access "accessible-for-notify";
        smiv2:oid "1.3.6.1.4.1.9.9.116.1.5.8";
      }
    }

    container object-3 {

      leaf cdxWBResilUpdateTime {
        type snmpv2-tc:DateAndTime;
        description
         "This object indicates the time when CMTS receives the
          latest wideband resiliency event.";
        smiv2:max-access "accessible-for-notify";
        smiv2:oid "1.3.6.1.4.1.9.9.116.1.5.9";
      }
    }

    container object-4 {

      leaf cdxWBResilEventTotalCount {
        type yang:counter32;
        description
         "The object denotes the count of event CMTS received.";
        smiv2:max-access "accessible-for-notify";
        smiv2:oid "1.3.6.1.4.1.9.9.116.1.5.10";
      }
    }

    container object-5 {

      leaf cdxWBResilEventTotalDupCount {
        type yang:counter32;
        description
         "The object denotes the duplicate count of event CMTS 
          received.";
        smiv2:max-access "accessible-for-notify";
        smiv2:oid "1.3.6.1.4.1.9.9.116.1.5.11";
      }
    }

    container object-6 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }
  }

  notification cdxWBResilUsPartialServiceNotif {
    description
     "This notification indicates that a Cable Modem  
      is inenters upstream partial service. 
      Object docsIfCmtsCmStatusUpChannelIfIndex 
      represents the target upstream channel ifindex.";
    smiv2:oid "1.3.6.1.4.1.9.9.116.2.0.9";

    container object-1 {

      leaf ifIndex {
        type leafref {
          path "/if-mib:IF-MIB/if-mib:ifTable/if-mib:ifEntry/if-mib:ifIndex";
        }
      }
    }

    container object-2 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }

    container object-3 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusUpChannelIfIndex {
        type leafref {
          path "/docs-if:DOCS-IF-MIB/docs-if:docsIfCmtsCmStatusTable/docs-if:docsIfCmtsCmStatusEntry/docs-if:docsIfCmtsCmStatusUpChannelIfIndex";
        }
      }
    }

    container object-4 {

      leaf cdxUsResilEventType {
        type enumeration {
          enum "other" {
            value "1";
          }
          enum "ranging" {
            value "2";
          }
          enum "dataBurst" {
            value "3";
          }
        }
        description
         "The object denotes the type of upstream partial service event.";
        smiv2:max-access "accessible-for-notify";
        smiv2:oid "1.3.6.1.4.1.9.9.116.1.5.12";
      }
    }

    container object-5 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }

    container object-6 {

      leaf cdxWBResilUpdateTime {
        type snmpv2-tc:DateAndTime;
        description
         "This object indicates the time when CMTS receives the
          latest wideband resiliency event.";
        smiv2:max-access "accessible-for-notify";
        smiv2:oid "1.3.6.1.4.1.9.9.116.1.5.9";
      }
    }
  }

  notification cdxWBResilUsFullServiceNotif {
    description
     "This notification indicates that a Cable Modem upstream
      channel is recovered from upstream partial
      service to full service mode.
      Object docsIfCmtsCmStatusUpChannelIfIndex represents
      the target upstream channel ifindex.";
    smiv2:oid "1.3.6.1.4.1.9.9.116.2.0.10";

    container object-1 {

      leaf ifIndex {
        type leafref {
          path "/if-mib:IF-MIB/if-mib:ifTable/if-mib:ifEntry/if-mib:ifIndex";
        }
      }
    }

    container object-2 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusMacAddress {
        type leafref {
          path "/docs-if:DOCS-IF-MIB/docs-if:docsIfCmtsCmStatusTable/docs-if:docsIfCmtsCmStatusEntry/docs-if:docsIfCmtsCmStatusMacAddress";
        }
      }
    }

    container object-3 {

      leaf docsIfCmtsCmStatusIndex {
        type leafref {
          path "/docs-if:DOCS-IF-MIB/docs-if:docsIfCmtsCmStatusTable/docs-if:docsIfCmtsCmStatusEntry/docs-if:docsIfCmtsCmStatusIndex";
        }
      }

      leaf docsIfCmtsCmStatusUpChannelIfIndex {
        type leafref {
          path "/docs-if:DOCS-IF-MIB/docs-if:docsIfCmtsCmStatusTable/docs-if:docsIfCmtsCmStatusEntry/docs-if:docsIfCmtsCmStatusUpChannelIfIndex";
        }
      }
    }

    container object-4 {

      leaf cdxUsResilEventType {
        type enumeration {
          enum "other" {
            value "1";
          }
          enum "ranging" {
            value "2";
          }
          enum "dataBurst" {
            value "3";
          }
        }
        description
         "The object denotes the type of upstream partial service event.";
        smiv2:max-access "accessible-for-notify";
        smiv2:oid "1.3.6.1.4.1.9.9.116.1.5.12";
      }
    }

    container object-5 {

      leaf cdxWBResilEventLevel {
        type enumeration {
          enum "info" {
            value "1";
          }
          enum "warning" {
            value "2";
          }
          enum "error" {
            value "3";
          }
        }
        description
         "This object indicates the priority level of the event.";
        smiv2:max-access "accessible-for-notify";
        smiv2:oid "1.3.6.1.4.1.9.9.116.1.5.7";
      }
    }

    container object-6 {

      leaf cdxWBResilUpdateTime {
        type snmpv2-tc:DateAndTime;
        description
         "This object indicates the time when CMTS receives the
          latest wideband resiliency event.";
        smiv2:max-access "accessible-for-notify";
        smiv2:oid "1.3.6.1.4.1.9.9.116.1.5.9";
      }
    }
  }

  smiv2:alias "ciscoDocsExtMIB" {
    smiv2:oid "1.3.6.1.4.1.9.9.116";
  }

  smiv2:alias "ciscoDocsExtMIBObjects" {
    smiv2:oid "1.3.6.1.4.1.9.9.116.1";
  }

  smiv2:alias "cdxQosCtrlObjects" {
    smiv2:oid "1.3.6.1.4.1.9.9.116.1.1";
  }

  smiv2:alias "cdxQosQueueObjects" {
    smiv2:oid "1.3.6.1.4.1.9.9.116.1.2";
  }

  smiv2:alias "cdxCmtsCmCpeObjects" {
    smiv2:oid "1.3.6.1.4.1.9.9.116.1.3";
  }

  smiv2:alias "cdxSpecMgmtObjects" {
    smiv2:oid "1.3.6.1.4.1.9.9.116.1.4";
  }

  smiv2:alias "cdxWBResilObjects" {
    smiv2:oid "1.3.6.1.4.1.9.9.116.1.5";
  }

  smiv2:alias "cdxDownstreamObjects" {
    smiv2:oid "1.3.6.1.4.1.9.9.116.1.6";
  }

  smiv2:alias "cdxCmtsMtcCmSfObjects" {
    smiv2:oid "1.3.6.1.4.1.9.9.116.1.7";
  }

  smiv2:alias "cdxCmtsDocsisLBObjects" {
    smiv2:oid "1.3.6.1.4.1.9.9.116.1.8";
  }

  smiv2:alias "cdxRPDGS7KObjects" {
    smiv2:oid "1.3.6.1.4.1.9.9.116.1.9";
  }

  smiv2:alias "cdxCmtsDHCPRelayObjects" {
    smiv2:oid "1.3.6.1.4.1.9.9.116.1.10";
  }

  smiv2:alias "cdxCmtsIPv6DHCPRelayObjects" {
    smiv2:oid "1.3.6.1.4.1.9.9.116.1.11";
  }

  smiv2:alias "ciscoDocsExtNotificationsPrefix" {
    smiv2:oid "1.3.6.1.4.1.9.9.116.2";
  }

  smiv2:alias "ciscoDocsExtNotifications" {
    smiv2:oid "1.3.6.1.4.1.9.9.116.2.0";
  }

  smiv2:alias "ciscoDocsExtConformance" {
    smiv2:oid "1.3.6.1.4.1.9.9.116.3";
  }

  smiv2:alias "cdxDocsExtCompliances" {
    smiv2:oid "1.3.6.1.4.1.9.9.116.3.1";
  }

  smiv2:alias "cdxDocsExtGroups" {
    smiv2:oid "1.3.6.1.4.1.9.9.116.3.2";
  }

}
