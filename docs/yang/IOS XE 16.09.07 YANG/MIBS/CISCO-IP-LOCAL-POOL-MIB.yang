/*
 * Generated by confdc --mib2yang-std
 * Source: mgmt/dmi/model/mib/src/CISCO-IP-LOCAL-POOL-MIB.mib
 */
/*
 * This YANG module has been generated by smidump 0.5.0:
 *
 *      smidump -f yang CISCO-IP-LOCAL-POOL-MIB
 *
 * Do not edit. Edit the source file instead!
 */

module CISCO-IP-LOCAL-POOL-MIB {

  namespace "urn:ietf:params:xml:ns:yang:smiv2:CISCO-IP-LOCAL-POOL-MIB";
  prefix CISCO-IP-LOCAL-POOL-MIB;

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-snmp@cisco.com";

  description
   "This MIB defines the configuration and monitoring capabilities
    relating to local IP pools.
    
    Local IP pools have the following characteristics:
    
    - An IP local pool consists of one or more IP address ranges.
    
    - An IP pool group consists of one or more IP local pools.
    
    - An IP local pool can only belong to one IP pool group.
    
    - IP local pools that belong to different groups can have
      overlapping addresses.
    
    - IP local pool names are unique even when they belong to
      different groups.
    
    - Addresses within an IP pool group can not overlap.
    
    - IP local pools without an explicit group name are considered
      members of the base system group.  In this MIB, the base
      system group is represented by a null IP pool group name.
    
    This MIB defines objects that expose the relationship between
    IP pool groups and IP local pools.  There exist other objects
    that maintain statistics about the address usage of IP local
    pools.";

  revision 2007-11-12 {
    description
     "Added one object to the cIpLocalPoolConfigTable:
      - cIpLocalPoolPriority
      
      Added ciscoIpLocalPoolMIBCompliance2 MODULE-COMPLIANCE 
      Added ciscoIpLocalPoolPriorityGroup OBJECT-GROUP";
  }

  revision 2005-01-11 {
    description
     "Added two objects to the cIpLocalPoolStatsTable:
      - cIpLocalPoolPercentAddrThldLo
      - cIpLocalPoolPercentAddrThldHi
      
      Added two notifications:
      - cilpPercentAddrUsedHiNotif
      - cilpPercentAddrUsedLoNotif";
  }

  revision 2003-04-03 {
    description
     "Initial version of this MIB module.";
  }

  typedef CIpLocalPoolName {
    type binary {
      length "1..48";
    }
    description
     "A non-empty string that uniquely identifies an IP local pool.";
  }

  typedef CIpLocalPoolGroupNameOrNull {
    type binary {
      length "0..48";
    }
    description
     "A string that uniquely identifies an IP pool group. The value
      of null is object-specific and must therefore be defined as part
      of the description of any object which uses this syntax.";
  }

  typedef CIpLocalPoolPercentage {
    type yang:gauge32 {
      range "0..100";
    }
    description
     "A percentage associated with the addresses used in a IP local
      pool.";
    smiv2:display-hint "d-2";
  }


  container CISCO-IP-LOCAL-POOL-MIB {
    config false;

    container cIpLocalPoolConfig {
      smiv2:oid "1.3.6.1.4.1.9.9.326.1.1";

      leaf cIpLocalPoolNotificationsEnable {
        type boolean;
        description
         "An indication of whether the notifications defined by the
          ciscoIpLocalPoolNotifGroup are enabled.";
        smiv2:max-access "read-write";
        smiv2:oid "1.3.6.1.4.1.9.9.326.1.1.1";
      }
    }

    container cIpLocalPoolConfigTable {
      description
       "This table manages the creation, modification, and deletion
        of IP local pools using the RowStatus textual convention.  An
        entry in this table defines an IP address range that is
        associated with an IP local pool.
        
        A conceptual row in this table can not be modified while
        cIpLocalPoolRowStatus is set to 'active'.
        
        Since IP local pool names are unique even when they belong to
        different groups, and addresses within a group can not overlap,
        a row in this table is uniquely indexed by the pool name, and by
        the low address of the IP local pool together with its address
        type.";
      smiv2:oid "1.3.6.1.4.1.9.9.326.1.1.2";

      list cIpLocalPoolConfigEntry {
        key "cIpLocalPoolName cIpLocalPoolAddrType cIpLocalPoolAddressLo";
        description
         "Each entry provides information about a particular IP local
          pool, including the number of free and used addresses and its priority.";
        smiv2:oid "1.3.6.1.4.1.9.9.326.1.1.2.1";

        leaf cIpLocalPoolName {
          type CISCO-IP-LOCAL-POOL-MIB:CIpLocalPoolName;
          description
           "An arbitrary non-empty string that uniquely identifies the IP
            local pool.  This name must be unique among all the local IP
            pools even when they belong to different pool groups.";
          smiv2:max-access "not-accessible";
          smiv2:oid "1.3.6.1.4.1.9.9.326.1.1.2.1.1";
        }

        leaf cIpLocalPoolAddrType {
          type inet-address:InetAddressType;
          description
           "This object specifies the address type of cIpLocalPoolAddressLo
            and cIpLocalPoolAddressHi.";
          smiv2:max-access "not-accessible";
          smiv2:oid "1.3.6.1.4.1.9.9.326.1.1.2.1.2";
        }

        leaf cIpLocalPoolAddressLo {
          type inet-address:InetAddress;
          description
           "This object specifies the first IP address of the range of IP
            addresses contained by this pool entry.  The address type of
            this object is described by cIpLocalPoolAddrType.
            
            This address must be less than or equal to the address in
            cIpLocalPoolAddressHi.";
          smiv2:max-access "not-accessible";
          smiv2:oid "1.3.6.1.4.1.9.9.326.1.1.2.1.3";
        }

        leaf cIpLocalPoolAddressHi {
          type inet-address:InetAddress;
          description
           "This object specifies the last IP address of the range of IP
            addresses mapped by this pool entry.  The address type of this
            object is described by cIpLocalPoolAddrType.  If only a single
            address is being mapped, the value of this object is equal to
            the value of cIpLocalPoolAddressLo.";
          smiv2:max-access "read-write";
          smiv2:oid "1.3.6.1.4.1.9.9.326.1.1.2.1.4";
        }

        leaf cIpLocalPoolFreeAddrs {
          type yang:gauge32;
          description
           "The number of IP addresses available for use in the range of
            IP addresses.";
          smiv2:max-access "read-only";
          smiv2:oid "1.3.6.1.4.1.9.9.326.1.1.2.1.5";
        }

        leaf cIpLocalPoolInUseAddrs {
          type yang:gauge32;
          description
           "The number of IP addresses being used in the range of IP
            addresses.";
          smiv2:max-access "read-only";
          smiv2:oid "1.3.6.1.4.1.9.9.326.1.1.2.1.6";
        }

        leaf cIpLocalPoolGroupContainedIn {
          type CISCO-IP-LOCAL-POOL-MIB:CIpLocalPoolGroupNameOrNull;
          description
           "This object relates an IP local pool to its IP pool group.
            
            A null string indicates this IP local pool is not contained in a
            named IP pool group, but that it is contained in the base IP
            pool group.  An IP local pool can only belong to one IP pool
            group.";
          smiv2:defval "";
          smiv2:max-access "read-write";
          smiv2:oid "1.3.6.1.4.1.9.9.326.1.1.2.1.7";
        }

        leaf cIpLocalPoolRowStatus {
          type snmpv2-tc:RowStatus;
          description
           "This object facilitates the creation, or deletion of a
            conceptual row in this table.";
          smiv2:max-access "read-write";
          smiv2:oid "1.3.6.1.4.1.9.9.326.1.1.2.1.8";
        }

        leaf cIpLocalPoolPriority {
          type uint32 {
            range "1..255";
          }
          description
           "This object specifies priority of the IP local pool,
            where smaller value indicates the lower priority.
            The priority value is used in assigning IP Address 
            from local pools.";
          smiv2:defval "1";
          smiv2:max-access "read-write";
          smiv2:oid "1.3.6.1.4.1.9.9.326.1.1.2.1.9";
        }
      }
    }

    container cIpLocalPoolGroupContainsTable {
      description
       "A table which exposes the container/'containee' relationships
        between local IP pools and IP pool groups.
        
        Entries in this table are created or deleted as a by-product of
        creating or deleting entries in the cIpLocalPoolConfigTable.
        
        When an entry is created and activated in the
        cIpLocalPoolConfigTable table, an entry in this table will come
        into existence if it does not already exist.
        
        When an entry is deleted in the cIpLocalPoolConfigTable table,
        if there is no other entry existing in that table with the same
        cIpLocalPoolGroupContainedIn and cIpLocalPoolName, the entry in
        this table with the respective cIpLocalPoolGroupName and
        cIpLocalPoolName indices will be removed.";
      smiv2:oid "1.3.6.1.4.1.9.9.326.1.2.1";

      list cIpLocalPoolGroupContainsEntry {
        key "cIpLocalPoolGroupName cIpLocalPoolChildIndex";
        description
         "Each entry describes single container/'containee'
          relationship.
          
          Pool names can only be associated with one group.  Pools carry
          implicit group identifiers because pool names can only be
          associated with one group.  An entry in this table describes
          such an association.";
        smiv2:oid "1.3.6.1.4.1.9.9.326.1.2.1.1";

        leaf cIpLocalPoolGroupName {
          type CISCO-IP-LOCAL-POOL-MIB:CIpLocalPoolGroupNameOrNull;
          description
           "A unique group name that identifies the IP pool group.  The
            null string represents the base IP pool group.";
          smiv2:max-access "not-accessible";
          smiv2:oid "1.3.6.1.4.1.9.9.326.1.2.1.1.1";
        }

        leaf cIpLocalPoolChildIndex {
          type CISCO-IP-LOCAL-POOL-MIB:CIpLocalPoolName;
          description
           "The value of cIpLocalPoolName for the contained IP local pool.";
          smiv2:max-access "read-only";
          smiv2:oid "1.3.6.1.4.1.9.9.326.1.2.1.1.2";
        }
      }
    }

    container cIpLocalPoolGroupTable {
      description
       "This table provides statistics for configured IP pool groups.
        
        Entries in this table are created as the result of adding a new
        IP pool group to the cIpLocalPoolConfigTable.
        
        Entries in this table are deleted as the result of removing all
        IP local pools that are contained in an IP pool group in the
        cIpLocalPoolConfigTable.
        
        An entry in this table is uniquely indexed by IP pool group
        name.";
      smiv2:oid "1.3.6.1.4.1.9.9.326.1.2.2";

      list cIpLocalPoolGroupEntry {
        key "cIpLocalPoolGroupName";
        description
         "Each entry provides information about a particular IP pool
          group and the number of free and used addresses in an IP pool
          group.";
        smiv2:oid "1.3.6.1.4.1.9.9.326.1.2.2.1";

        leaf cIpLocalPoolGroupName {
          type leafref {
            path "/CISCO-IP-LOCAL-POOL-MIB:CISCO-IP-LOCAL-POOL-MIB/CISCO-IP-LOCAL-POOL-MIB:cIpLocalPoolGroupContainsTable/CISCO-IP-LOCAL-POOL-MIB:cIpLocalPoolGroupContainsEntry/CISCO-IP-LOCAL-POOL-MIB:cIpLocalPoolGroupName";
          }
        }

        leaf cIpLocalPoolGroupFreeAddrs {
          type yang:gauge32;
          description
           "The number of IP addresses available for use in the IP pool
            group.";
          smiv2:max-access "read-only";
          smiv2:oid "1.3.6.1.4.1.9.9.326.1.2.2.1.1";
        }

        leaf cIpLocalPoolGroupInUseAddrs {
          type yang:gauge32;
          description
           "The number of IP addresses that have been allocated from the
            IP pool group.";
          smiv2:max-access "read-only";
          smiv2:oid "1.3.6.1.4.1.9.9.326.1.2.2.1.2";
        }
      }
    }

    container cIpLocalPoolStatsTable {
      description
       "A table providing statistics for each IP local pool.
        
        Entries in this table are created as the result of adding a new
        IP local pool to the cIpLocalPoolConfigTable.
        
        Entries in this table are deleted as the result of removing all
        the address ranges that are contained in an IP local pool in the
        cIpLocalPoolConfigTable.
        
        Entries in this table are uniquely indexed by the name of the IP
        local pool.";
      smiv2:oid "1.3.6.1.4.1.9.9.326.1.3.1";

      list cIpLocalPoolStatsEntry {
        key "cIpLocalPoolName";
        description
         "Each entry provides statistical information about a particular
          IP local pool, and the total number of free and used addresses
          of all the ranges in an IP local pool.";
        smiv2:oid "1.3.6.1.4.1.9.9.326.1.3.1.1";

        leaf cIpLocalPoolName {
          type leafref {
            path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
          }
        }

        leaf cIpLocalPoolStatFreeAddrs {
          type yang:gauge32;
          description
           "The number of IP addresses available for use in this IP local
            pool.";
          smiv2:max-access "read-only";
          smiv2:oid "1.3.6.1.4.1.9.9.326.1.3.1.1.1";
        }

        leaf cIpLocalPoolStatInUseAddrs {
          type yang:gauge32;
          description
           "The number of IP addresses being used in this IP local pool.";
          smiv2:max-access "read-only";
          smiv2:oid "1.3.6.1.4.1.9.9.326.1.3.1.1.2";
        }

        leaf cIpLocalPoolStatHiWaterUsedAddrs {
          type uint32;
          description
           "This object contains the high water mark of used addresses
            in an IP local pool since pool creation, since the system was
            restarted, or since this object was reset, whichever occurred
            last.  This object can only be set to zero, and by doing so, it
            is reset to the value of cIpLocalPoolStatInUseAddrs.
            
            Since the number of addresses in a pool can be reduced (e.g. by
            deleting one of its ranges), the value of this object may be
            greater than the sum of cIpLocalPoolStatFreeAddrs and
            cIpLocalPoolStatInUseAddrs.";
          smiv2:max-access "read-write";
          smiv2:oid "1.3.6.1.4.1.9.9.326.1.3.1.1.3";
        }

        leaf cIpLocalPoolStatInUseAddrThldLo {
          type uint32 {
            range "0..4294967295";
          }
          description
           "When the number of used addresses in an IP local pool falls
            below this threshold value, the ciscoIpLocalPoolInUseAddrNoti
            notification will be rearmed.
            
            The value of this object should never be greater than the value
            of cIpLocalPoolStatInUseAddrThldHi.";
          smiv2:defval "0";
          smiv2:max-access "read-write";
          smiv2:oid "1.3.6.1.4.1.9.9.326.1.3.1.1.4";
        }

        leaf cIpLocalPoolStatInUseAddrThldHi {
          type uint32 {
            range "0..4294967295";
          }
          description
           "When the number of used addresses in an IP local pool
            is equal or exceeds this threshold value, a
            ciscoIpLocalPoolInUseAddrNoti notification will be generated.
            Once this notification is generated, it will be disarmed and it
            will not be generated again until the number of used address
            falls below the value indicated by
            cIpLocalPoolStatInUseAddrThldLo.
            
            The value of this object should never be smaller than the value
            of cIpLocalPoolStatInUseAddrThldLo.";
          smiv2:defval "4294967295";
          smiv2:max-access "read-write";
          smiv2:oid "1.3.6.1.4.1.9.9.326.1.3.1.1.5";
        }

        leaf cIpLocalPoolPercentAddrThldLo {
          type CISCO-IP-LOCAL-POOL-MIB:CIpLocalPoolPercentage;
          description
           "When the percentage of used addresses in an IP local pool
            falls below this threshold value, a cilpPercentAddrUsedLoNotif
            notification will be generated.  Once the notification is
            generated, it will be disarmed and it will not be generated
            again until the number of used addresses equals or exceeds the
            value indicated by cIpLocalPoolPercentAddrThldHi.
            
            The value of this object should never be greater than the value
            of cIpLocalPoolPercentAddrThldHi.";
          smiv2:defval "0";
          smiv2:max-access "read-write";
          smiv2:oid "1.3.6.1.4.1.9.9.326.1.3.1.1.6";
        }

        leaf cIpLocalPoolPercentAddrThldHi {
          type CISCO-IP-LOCAL-POOL-MIB:CIpLocalPoolPercentage;
          description
           "When the percentage of used addresses in an IP local pool
            is equal or exceeds this threshold value, a
            cilpPercentAddrUsedHiNotif notification will be generated. Once
            the notification is generated, it will be disarmed and it will
            not be generated again until the number of used addresses falls
            below the value indicated by cIpLocalPoolPercentAddrThldLo.
            
            The value of this object should never be smaller than the value
            of cIpLocalPoolPercentAddrThldLo.";
          smiv2:defval "100";
          smiv2:max-access "read-write";
          smiv2:oid "1.3.6.1.4.1.9.9.326.1.3.1.1.7";
        }
      }
    }

    container cIpLocalPoolAllocTable {
      description
       "This table lists all addresses that have been allocated out of
        an IP local pool.
        
        Entries in this table are created when a remote peer allocates
        an address from one of the IP local pools in the
        cIpLocalPoolConfigTable.
        
        Entries in this table are deleted when a remote peer deallocates
        an address from one of the IP local pool in the
        cIpLocalPoolConfigTable.
        
        Entries in this table are uniquely indexed by the name of the IP
        local pool, and the allocated address, together with its address
        type.";
      smiv2:oid "1.3.6.1.4.1.9.9.326.1.3.2";

      list cIpLocalPoolAllocEntry {
        key "cIpLocalPoolName cIpLocalPoolAllocAddrType cIpLocalPoolAllocAddr";
        description
         "Each entry refers to conceptual row that associates an IP
          addresses with the interface where the request was received, and
          the user that requested the address.";
        smiv2:oid "1.3.6.1.4.1.9.9.326.1.3.2.1";

        leaf cIpLocalPoolName {
          type leafref {
            path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
          }
        }

        leaf cIpLocalPoolAllocAddrType {
          type inet-address:InetAddressType;
          description
           "This object specifies the address type of
            cIpLocalPoolAllocAddr.";
          smiv2:max-access "not-accessible";
          smiv2:oid "1.3.6.1.4.1.9.9.326.1.3.2.1.1";
        }

        leaf cIpLocalPoolAllocAddr {
          type inet-address:InetAddress;
          description
           "This object specifies the allocated IP address.  The address
            type of this object is described by cIpLocalPoolAllocAddrType.";
          smiv2:max-access "not-accessible";
          smiv2:oid "1.3.6.1.4.1.9.9.326.1.3.2.1.2";
        }

        leaf cIpLocalPoolAllocIfIndex {
          type if-mib:InterfaceIndexOrZero;
          description
           "This object indicates the interface from which the allocation
            message was sent.
            
            In the case that the interface can not be determined, the value
            of this object will be zero.";
          smiv2:max-access "read-only";
          smiv2:oid "1.3.6.1.4.1.9.9.326.1.3.2.1.3";
        }

        leaf cIpLocalPoolAllocUser {
          type snmp-framework:SnmpAdminString;
          description
           "This object indicates the user name of the person from whom the
            allocation message was sent.
            
            In the case that the user name can not be determined, the value
            of this object will the null string.";
          smiv2:max-access "read-only";
          smiv2:oid "1.3.6.1.4.1.9.9.326.1.3.2.1.4";
        }
      }
    }
  }

  notification ciscoIpLocalPoolInUseAddrNoti {
    description
     "A notification indicating that number of used addresses of an
      IP local pool exceeded the threshold value indicated by
      cIpLocalPoolStatInUseAddrThldHi.";
    smiv2:oid "1.3.6.1.4.1.9.9.326.0.1";

    container object-1 {

      leaf cIpLocalPoolName {
        type leafref {
          path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
        }
      }

      leaf cIpLocalPoolStatFreeAddrs {
        type leafref {
          path "/CISCO-IP-LOCAL-POOL-MIB:CISCO-IP-LOCAL-POOL-MIB/CISCO-IP-LOCAL-POOL-MIB:cIpLocalPoolStatsTable/CISCO-IP-LOCAL-POOL-MIB:cIpLocalPoolStatsEntry/CISCO-IP-LOCAL-POOL-MIB:cIpLocalPoolStatFreeAddrs";
        }
      }
    }

    container object-2 {

      leaf cIpLocalPoolName {
        type leafref {
          path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
        }
      }

      leaf cIpLocalPoolStatInUseAddrs {
        type leafref {
          path "/CISCO-IP-LOCAL-POOL-MIB:CISCO-IP-LOCAL-POOL-MIB/CISCO-IP-LOCAL-POOL-MIB:cIpLocalPoolStatsTable/CISCO-IP-LOCAL-POOL-MIB:cIpLocalPoolStatsEntry/CISCO-IP-LOCAL-POOL-MIB:cIpLocalPoolStatInUseAddrs";
        }
      }
    }
  }

  notification cilpPercentAddrUsedLoNotif {
    description
     "A notification indicating that the percentage of used addresses
      of an IP local pool went below the threshold value indicated by
      cIpLocalPoolPercentAddrThldLo.";
    smiv2:oid "1.3.6.1.4.1.9.9.326.0.2";

    container object-1 {

      leaf cIpLocalPoolName {
        type leafref {
          path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
        }
      }

      leaf cIpLocalPoolStatFreeAddrs {
        type leafref {
          path "/CISCO-IP-LOCAL-POOL-MIB:CISCO-IP-LOCAL-POOL-MIB/CISCO-IP-LOCAL-POOL-MIB:cIpLocalPoolStatsTable/CISCO-IP-LOCAL-POOL-MIB:cIpLocalPoolStatsEntry/CISCO-IP-LOCAL-POOL-MIB:cIpLocalPoolStatFreeAddrs";
        }
      }
    }

    container object-2 {

      leaf cIpLocalPoolName {
        type leafref {
          path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
        }
      }

      leaf cIpLocalPoolStatInUseAddrs {
        type leafref {
          path "/CISCO-IP-LOCAL-POOL-MIB:CISCO-IP-LOCAL-POOL-MIB/CISCO-IP-LOCAL-POOL-MIB:cIpLocalPoolStatsTable/CISCO-IP-LOCAL-POOL-MIB:cIpLocalPoolStatsEntry/CISCO-IP-LOCAL-POOL-MIB:cIpLocalPoolStatInUseAddrs";
        }
      }
    }
  }

  notification cilpPercentAddrUsedHiNotif {
    description
     "A notification indicating that the percentage of used addresses
      of an IP local pool is equal to or exceeds the threshold value
      indicated by cIpLocalPoolPercentAddrThldHi.";
    smiv2:oid "1.3.6.1.4.1.9.9.326.0.3";

    container object-1 {

      leaf cIpLocalPoolName {
        type leafref {
          path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
        }
      }

      leaf cIpLocalPoolStatFreeAddrs {
        type leafref {
          path "/CISCO-IP-LOCAL-POOL-MIB:CISCO-IP-LOCAL-POOL-MIB/CISCO-IP-LOCAL-POOL-MIB:cIpLocalPoolStatsTable/CISCO-IP-LOCAL-POOL-MIB:cIpLocalPoolStatsEntry/CISCO-IP-LOCAL-POOL-MIB:cIpLocalPoolStatFreeAddrs";
        }
      }
    }

    container object-2 {

      leaf cIpLocalPoolName {
        type leafref {
          path "/CISCO-IP-LOCAL-POOL-MIB:CISCO-IP-LOCAL-POOL-MIB/CISCO-IP-LOCAL-POOL-MIB:cIpLocalPoolConfigTable/CISCO-IP-LOCAL-POOL-MIB:cIpLocalPoolConfigEntry/CISCO-IP-LOCAL-POOL-MIB:cIpLocalPoolName";
        }
      }

      leaf cIpLocalPoolStatInUseAddrs {
        type leafref {
          path "/CISCO-IP-LOCAL-POOL-MIB:CISCO-IP-LOCAL-POOL-MIB/CISCO-IP-LOCAL-POOL-MIB:cIpLocalPoolStatsTable/CISCO-IP-LOCAL-POOL-MIB:cIpLocalPoolStatsEntry/CISCO-IP-LOCAL-POOL-MIB:cIpLocalPoolStatInUseAddrs";
        }
      }
    }
  }

  smiv2:alias "ciscoIpLocalPoolMIB" {
    smiv2:oid "1.3.6.1.4.1.9.9.326";
  }

  smiv2:alias "ciscoIpLocalPoolMIBNotifs" {
    smiv2:oid "1.3.6.1.4.1.9.9.326.0";
  }

  smiv2:alias "ciscoIpLocalPoolMIBObjects" {
    smiv2:oid "1.3.6.1.4.1.9.9.326.1";
  }

  smiv2:alias "cIpLocalPoolConfig" {
    smiv2:oid "1.3.6.1.4.1.9.9.326.1.1";
  }

  smiv2:alias "cIpLocalPoolGroup" {
    smiv2:oid "1.3.6.1.4.1.9.9.326.1.2";
  }

  smiv2:alias "cIpLocalPoolStats" {
    smiv2:oid "1.3.6.1.4.1.9.9.326.1.3";
  }

  smiv2:alias "ciscoIpLocalPoolMIBConform" {
    smiv2:oid "1.3.6.1.4.1.9.9.326.2";
  }

  smiv2:alias "ciscoIpLocalPoolMIBCompliances" {
    smiv2:oid "1.3.6.1.4.1.9.9.326.2.1";
  }

  smiv2:alias "ciscoIpLocalPoolMIBGroups" {
    smiv2:oid "1.3.6.1.4.1.9.9.326.2.2";
  }

}
