/*
 * Generated by confdc --mib2yang-std
 * Source: mgmt/dmi/model/mib/src/CISCO-VOICE-DIAL-CONTROL-MIB.mib
 */
/*
 * This YANG module has been generated by smidump 0.5.0:
 *
 *      smidump -f yang CISCO-VOICE-DIAL-CONTROL-MIB
 *
 * Do not edit. Edit the source file instead!
 */

module CISCO-VOICE-DIAL-CONTROL-MIB {

  namespace "urn:ietf:params:xml:ns:yang:smiv2:CISCO-VOICE-DIAL-CONTROL-MIB";
  prefix CISCO-VOICE-DIAL-CONTROL-MIB;

  import CISCO-DIAL-CONTROL-MIB {
    prefix "cisco-dial";
  }

  import CISCO-VOICE-COMMON-DIAL-CONTROL-MIB {
    prefix "cisco-voice";
  }

  import CISCO-VOICE-DNIS-MIB {
    prefix "cisco-voice-dnis";
  }

  import DIAL-CONTROL-MIB {
    prefix "dial-control";
  }

  import IF-MIB {
    prefix "if-mib";
  }

  import INET-ADDRESS-MIB {
    prefix "inet-address";
  }

  import INT-SERV-MIB {
    prefix "int-serv";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    Postal: 170 W. Tasman Drive
    San Jose, CA  95134
    USA
    
    Tel: +1 800 553-NETS
    
    E-mail: cs-voice@cisco.com";

  description
   "This MIB module enhances the IETF Dial Control MIB
    (RFC2128) by providing management of voice telephony
    peers on both a circuit-switched telephony network,
    and an IP data network.
    
    *** ABBREVIATIONS, ACRONYMS AND SYMBOLS ***
    
    GSM    - Global System for Mobile Communication
    
    AMR-NB - Adaptive Multi Rate - Narrow Band 
    
    iLBC   - internet Low Bitrate Codec 
    
    KPML   - Key Press Markup Language
    
    MGCP   - Media Gateway Control Protocol.
    
    SIP    - Session Initiation Protocol.
    
    H323   - One of the voip signalling protocol.
    
    SCCP   - Skinny Client Control Protocol.
    
    dialpeer - This represents a configured interface that 
               carries the dial map.  A dialpeer maps the 
               called and calling numbers with the port or 
               IP interface to be used.
    
    License call capacity - This represents the licensed 
                            maximum call capacity of 
                            the gateway.
    
    iSAC    -  Internet Speech Audio Codec
    
    RPH    - Resource Priority Header
    
    DSCP   - Diffserv Code Points";

  revision 2012-05-15 {
    description
     "[1] Added New OBJECT-GROUP cvCallVolumeStatsHistory
      in cvGatewayCallHistory.
      [2] Added following tables
       cvCallRateStatsTable,
       cvCallLegRateStatsTable,
       cvActiveCallStatsTable,
       cvCallDurationStatsTable,
       cvSipMsgRateStatsTable under cvCallVolumeStatsHistory
      [3] Added following tables
       cvCallRateWMTable,
       cvCallLegRateWMTable,
       cvActiveCallWMTable,
       cvSipMsgRateWMTable under cvCallVolumeStatsHistory
      [4] Added following textual conversation 
       CvCallVolumeStatsIntvlType &
       CvCallVolumeWMIntvlType         
      [5] Added new cvdcCallVolumeStatsHistory conformance group 
       in cvdcMIBGroups. 
      [6] Added cvdcMIBComplianceRev22 depricating cvdcMIBComplianceRev21";
  }

  revision 2011-07-11 {
    description
     "[1] Added cvVoIPCallActiveSessionId in cvVoIPCallActiveEntry and
      cvVoIPCallHistorySessionId in cvVoIPCallHistoryEntry
      [2] Added cvVoIPCallActiveSessionId and
      cvVoIPCallHistorySessionId to cvVoIPCallGroupSup3
      [3] Deprecated cvVoIPCallGroupSup2 and superceded it with
      cvVoIPCallGroupSup3
      [4] Deprecated cvdcMIBComplianceRev20 and superceded it with
      with cvdcMIBComplianceRev21";
  }

  revision 2011-05-31 {
    description
     "The following changes is done for RPH to DSCP mapping and Media
      policy feature.
      1) Added two new objects in the cvVoIPCallActiveEntry 
         ccVoIPCallActivePolicyName
         cvVoIPCallActiveReversedDirectionPeerAddress
      2) Added one new notification object
         cvdcPolicyViolationNotification
      3) Imported two objects from DIAL-CONTROL-MIB
         callActivePeerId
         callActivePeerAddress
      4) Added four objects as part of new Notification
      cvdcPolicyViolationNotification
         ccVoIPCallActiveViolationReason
         cvVoIPCallActiveCalledNumber
         callActivePeerId
         callActivePeerAddress
      5) Added new notification group cvdcNotificationGroupRev4 and
      changed the status of cvdcNotificationGroupRev3 to depricated.
      6) Added new conformance group cvVoIPCallGroupSup2 and changed
      the status of cvVoIPCallGroupSup1 to deprecated.
      7) Modified cvdcMIBComplianceRev20 to add new groups and remove
      the deprecated one
      8) Added the following objects in CvVoIPPeerCfgEntry            
         cvVoIPPeerCfgDSCPPolicyNotificationEnable 
         cvVoIPPeerCfgMediaPolicyNotificationEnable
      9) Added the following objects in cvdcGeneralCfgGroupRev6 
         cvGeneralDSCPPolicyNotificationEnable
         cvGeneralMediaPolicyNotificationEnable";
  }

  revision 2010-07-26 {
    description
     "[1] Modified MAX-ACCESS for cvVoIPPeerCfgFrameSize from read-only to read-write.
      [2] Added a call reference ID to associate the video call entry and
      voice call entry of the same endpoint.";
  }

  revision 2009-05-07 {
    description
     "[1] Added Abbreviation for iSAC
      [2] Added the following objects to cvVoIPPeerCfgTable for iSAC
      codec support.
         - cvVoIPPeerCfgCodingMode
         - cvVoIPPeerCfgBitRate
         - cvVoIPPeerCfgFramesize
      [3] Added a new OBJECT-GROUP cvdcVoIPCfgISACGroup.
      [4] Added a new MODULE-COMPLIANCE cvdcMIBComplianceRev19 which
      deprecates cvdcMIBComplianceRev18.";
  }

  revision 2009-04-20 {
    description
     "The following changes have been made.
      
      [1] Added new CvCallConnectionType TEXTUAL-CONVENTION.
      [2] Added the following new OBJECT IDENTIFIERs: 
          cvCallVolume, 
          cvCallRateMonitor
      [3] Added the following objects to cvCallVolume: 
          cvCallVolConnTable,
          cvCallVolConnTotalActiveConnections,
          cvCallVolConnMaxCallConnectionLicenese,
          cvCallVolPeerTable,
          cvCallVolIfTable.
      [4] Added the following objects to new cvCallVolConnTable:
          cvCallVolConnIndex,
          cvCallVolConnActiveConnection.
      [5] Added the following objects to new cvCallVolPeerTable:
          cvCallVolPeerIncomingCalls,
          cvCallVolPeerOutgoingCalls.
      [6] Added the following objects to new cvCallVolIfTable:
          cvCallVolMediaIncomingCalls,
          cvCallVolMediaOutgoingCalls.
      [7] Added the following objects to cvCallRateMonitor: 
          cvCallRateMonitorEnable,
          cvCallRateMonitorTime,
          cvCallRate,
          cvCallRateHiWaterMark.
      [8] Add the following OBJECT-GROUPs:
          cvCallVolumeGroup,
          cvCallRateMonitorGroup.
      [9] Deprecated MODULE-COMPLIANCE cvdcMIBComplianceRev17.
      [10] Added MODULE-COMPLIANCE cvdcMIBComplianceRev18.";
  }

  revision 2009-01-12 {
    description
     "The following changes have been made.
      
      [1] The descriptions of the following objects have   
          been modified to replace the term 'call identifier'
          with 'connection identifier'.  
          cvCallActiveConnectionId  
          cvVoIPCallActiveConnectionId  
          cvCallHistoryConnectionId  
          cvVoIPCallHistoryConnectionId.  
      [2] The object cvCallActiveCallId has been added  
          to cvCallActiveTable.  
      [3] The object cvVoIPCallActiveCallId has been added  
          to cvVoIPCallActiveTable.  
      [4] The object cvCallHistoryCallId has been added  
          to cvCallHistoryTable.  
      [5] The object cvVoIPCallHistoryCallId has been added  
          to cvVoIPCallHistoryTable.
      [6] 'sipKpml' has been added to the object
          cvVoIPPeerCfgDigitRelay.
      [7] Added following OBJECT-GROUPs
          cvCallGroupSup1,
          cvVoIPCallGroupSup1
      [8] Deprecated MODULE-COMPLIANCE
          cvdcMIBComplianceRev16 and is superceded by
          cvdcMIBComplianceRev17.";
  }

  revision 2006-03-12 {
    description
     "[1] Added Abbreviations for GSM, AMR-NB and iLBC
      [2] Added cvVoIPPeerCfgCoderMode object to 
          cvVoIPPeerCfgTable for iLBC codec support.
      [3] Added cvVoIPCallActiveCoderMode object to 
          cvVoIPCallActiveTable for iLBC codec support.
      [4] Added cvVoIPCallHistoryCoderMode object to 
          cvVoIPCallHistoryTable for iLBC codec support.
      [5] Created CvIlbcFrameMode textual convention.
      [6] Added REFERENCE clause to all new MIB objects and 
          textual conventions added.
      [7] Created cvVoIPCallIlbcGroup and cvdcVoIPCfgIlbcGroup 
          groups for iLBC specific objects.
      [8] Created module-compliance cvdcMIBComplianceRev16 and
          made cvVoIPCallIlbcGroup and cvdcVoIPCfgIlbcGroup
          as non mandatory.
      [9] Changed the default value for cvVoIPPeerCfgBitRates to
          all 8 bitrates as all 8 bitrates are supported.";
  }

  revision 2005-09-29 {
    description
     "Modified DESCRIPTION of cvPeerCfgPeerType object.";
  }

  revision 2005-07-25 {
    description
     "[1] Add new objects to cvVoIPCallActiveTable and
      cvVoIPCallHistoryTable for GSM AMR-NB codec support:
      Frame type, Bit rates, Mode change period,
      Mode change neighbor, Max payload time, CRC,
      Robust sorting, Encapsulation, Payload time
      channels, for call active and history table.
      [2] Add new objects to cvVoIPPeerCfgTable for GSM AMR-NB
      codec support:
      Frame type, Bit rates and CRC.
      [3] Created groups cvVoIPCallAmrNbGroup and
      cvdcVoIPCfgAmrNbGroup, for GSM AMR-NB
      specific objects.
      [4] Created a module-compliance cvdcMIBComplianceRev13
      and made cvVoIPCallAmrNbGroup and cvdcVoIPCfgAmrNbGroup
      as non mandatory.
      [5] Created following textual conventions:
      CvAmrNbBitRateMode and CvAmrNbRtpEncap.";
  }

  revision 2005-03-02 {
    description
     "The following values were added to the
      cvVoicePeerCfgEchoCancellerTest object:
      echoCancellerG168Test5,
      echoCancellerG168Test7";
  }

  revision 2005-03-01 {
    description
     "Modified DESCRIPTION of cvVoIPCallHistoryFallbackLoss
      object.";
  }

  revision 2004-04-30 {
    description
     "Added object
      Added cvVoIPCallHistoryRemSigIPAddrT and
      cvVoIPCallHistoryRemSigIPAddr to the 
      cvdcFallbackNotification .";
  }

  revision 2004-04-16 {
    description
     "Added object cvVoIPCallHistoryFallbackIcpif,
      cvVoIPCallHistoryFallbackLoss and 
      cvVoIPCallHistoryFallbackDelay
      to the cvVoIPCallHistoryTable.
      Added cvdcFallbackNotification for the 
      fallback notification.
      Added cvGeneralFallbackNotificationEnable to
      enable/disable cvdcFallbackNotification.";
  }

  revision 2004-03-09 {
    description
     "Added new objects for handling the following features:
      [1] The number of DS0s with voice calls up.
          cvCallActiveDS0s
      [2] The threshold number of DS0s above which a
          Notification will be triggered.
          cvCallActiveDS0sHighThreshold
      [3] The threshold number of DS0s below which a
          Notification will be triggered.
          cvCallActiveDS0sLowThreshold
      [4] Objects to enable the above two notifications.
          cvCallActiveDS0sHighNotifyEnable, 
          cvCallActiveDS0sLowNotifyEnable.
      [5] Notifications for the above two thresholds.
          cvdcActiveDS0sHighNotification, 
          cvdcActiveDS0sLowNotification.";
  }

  revision 2004-01-20 {
    description
     "Added object cvVoIPCallActiveSRTPEnable to
      cvVoIPCallActiveTable and cvVoIPCallHistorySRTPEnable 
      to cvVoIPCallHistoryTable to indicate whether SRTP is 
      enabled on a call.";
  }

  revision 2003-06-26 {
    description
     "Modified the DEVAL definition of
      cvVoIPPeerCfgDigitRelay object based on 
      no bit field was enabled when the object
      was created.";
  }

  revision 2003-04-14 {
    description
     "The DESCRIPTION of the following objects was
      modified to specify the allowable characters
      cvPeerCommonCfgSourceTrunkGrpLabel
      cvPeerCommonCfgTargetTrunkGrpLabel
      cvPeerCommonCfgSourceCarrierId
      cvPeerCommonCfgTargetCarrierId.";
  }

  revision 2002-12-31 {
    description
     "The following values were added to the
      cvVoicePeerCfgEchoCancellerTest object:
      echoCancellerG168Test4,
      echoCancellerG168Test6,
      echoCancellerG168Test9";
  }

  revision 2002-12-02 {
    description
     "The range of the following objects was changed:
      cvCallActiveNoiseLevel
      cvCallActiveACOMLevel
      cvCallActiveOutSignalLevel
      cvCallActiveInSignalLevel
      cvVoIPCallHistoryIcpif";
  }

  revision 2002-10-31 {
    description
     "Add object cvVoIPPeerCfgMediaSetting to the table.
      This object defines whether IP-IP media streams will
      flow-through or flow-around the Gateway.
      Add two new objects cvVoIPPeerCfgDesiredQoSVideo and
      cvVoIPPeerCfgMinAcceptableQoSVideo to the table
      cvVoIPPeerCfgTable. Also added objects
      cvCallActiveAccountCode and cvCallHistoryAccountCode.
      Depreciating element cvCallActiveERLLevel 
      Adding New element cvCallActiveERLLevelRev1
      Adding New type sipNotify in cvVoIPPeerCfgDigitRelay
      Adding New element cvVoIPPeerCfgRedirectip2ip  in
      CvVoIPPeerCfgEntry";
  }

  revision 2002-07-12 {
    description
     "* Add a new cvPeerCfgPeerType object to define the
      peer type
      * Added rtpNte, a new value for the
      cvVoIPPeerCfgDigitRelay object.";
  }

  revision 2001-08-20 {
    description
     "Addition of the following objects:
      cvVoIPCallActiveUsername
      cvVoIPCallActiveProtocolCallId
      cvVoIPCallActiveRemSigIPAddrT
      cvVoIPCallActiveRemSigIPAddr
      cvVoIPCallActiveRemSigPort
      cvVoIPCallActiveRemMediaIPAddrT
      cvVoIPCallActiveRemMediaIPAddr
      cvVoIPCallActiveRemMediaPort
      cvVoIPCallHistoryUsername
      cvVoIPCallHistoryProtocolCallId
      cvVoIPCallHistoryRemSigIPAddrT
      cvVoIPCallHistoryRemSigIPAddr
      cvVoIPCallHistoryRemSigPort
      cvVoIPCallHistoryRemMediaIPAddrT
      cvVoIPCallHistoryRemMediaIPAddr
      cvVoIPCallHistoryRemMediaPort
      cvdcPoorQoVNotificationRev1
      Deprecation of the following objects:
      cvVoIPCallActiveRemoteIPAddress
      cvVoIPCallActiveRemoteUDPPort
      cvVoIPCallHistoryRemoteIPAddress
      cvVoIPCallHistoryRemoteUDPPort
      cvdcPoorQoVNotification";
  }

  revision 2001-07-02 {
    description
     "Add two new objects cvPeerCommonCfgSourceTrunkGrpLabel and
      cvPeerCommonCfgTargetTrunkGrpLabel.";
  }

  revision 2001-04-10 {
    description
     "[1] Add a new object for handling the following feature:
      Location in milliseconds of largest amplitude reflector
      detected by echo canceller in call active table.
      Add new object for specifying an echo canceller test to
      to be run when a call using a dial peer so configured is
      connected.
      [2] Change QosService import from INT-SERV-MIB to
      INTEGRATED-SERVICES-MIB, since INTEGRATED-SERVICES-MIB
      (RFC2213) is where QosService is defined.";
  }

  revision 2001-03-25 {
    description
     "Add two new objects cvPeerCommonCfgSourceCarrierId and
      cvPeerCommonCfgTargetCarrierId. Add a enum definition to 
      cvVoIPPeerCfgSessionTarget object.";
  }

  revision 2000-05-04 {
    description
     "Add new objects for handling the following features:
      [1] Calling Name display for call active and history table.
      [2] Caller ID Block, which indicates whether the Caller ID
          feature is in using,  for call active and history table.";
  }

  revision 2000-04-19 {
    description
     "Changed VoIP dialpeer default values for
      Icpif to 20
      ExpectFactor to 0";
  }

  revision 2000-03-13 {
    description
     "Adding a new object cvPeerCommonCfgDnisMappingName.";
  }

  revision 1999-06-28 {
    description
     "Moved common Textual Conventions and the following items in
      the VoIP Call Active and Call History tables to the
      CISCO-VOICE-COMMON-DIAL-CONTROL-MIB, as these items apply to
      multiple network encapsulations.
      
          CoderTypeRate
          VADEnable
      
      Added new objects for handling the following features:
      [1] Gatekeeper registration configuration for voice peer
          destination pattern.
      [2] Dialpeer huntstop configuration.
      [3] Voip configuration support for Coder Bytes, Fax Bytes,
          settlement server and inband signaling.
      
      Added the following objects to the cvdcPoorQoVNotification.
          cvVoIPCallHistoryRemoteIPAddress,
          cCallHistoryCallOrigin,
          cvCommonDcCallHistoryCoderTypeRate";
  }

  revision 1999-01-29 {
    description
     "Add new enums in cvVoIPPeerCfgDigitRelay object for
      handling the transmission of dtmf digits across an
      H.245 channel via the signal and alphanumeric fields.";
  }

  revision 1998-09-11 {
    description
     "Add new objects for handling the following features:
      [1] FAX page count for call active and history table.
      [2] Peer Preference for peer configuration.
      [3] Add FAX rate 12000 bps, G723.1 Annex A codec support.
      [4] Technology prefix for VoIP encapsulated peer
          configuration.
      [5] Modify cvCallActiveACOMLeve, cvCallActiveERLLevel and
          cvCallHistoryACOMLevel to support undeterminable state.
      [6] Add digit relay configuration feature.";
  }

  revision 1998-02-22 {
    description
     "Add new objects for handling the following:
      [1] DNIS number matching.
      [2] Maximum connection to/from peer.
      [3] DID call treatment enable/disable.
      [4] Dial peer association to lower layer interfaces with
          CAS group.
      [5] Lost/Ealy/Late voice packets object in both call active
          and call history tables.
      [6] Update compliance statements.";
  }

  typedef CvCallVolumeWMIntvlType {
    type enumeration {
      enum "secondStats" {
        value "1";
      }
      enum "minuteStats" {
        value "2";
      }
      enum "hourStats" {
        value "3";
      }
      enum "fromReloadStats" {
        value "4";
      }
    }
    description
     "Represents the Id of the watermark table.
      Here is what different values represent
      
      1 : Seconds Table: Here the entries are among last 60 second
      2 : Minutes Table: Here the entries are among last 60 minutes
      3 : Hours Table: Here the entries are among last 72 Hours
      4 : Uptime Table: Here the entries are from last reload/reboot";
  }

  typedef CvCallVolumeStatsIntvlType {
    type enumeration {
      enum "secondStats" {
        value "1";
      }
      enum "minuteStats" {
        value "2";
      }
      enum "hourStats" {
        value "3";
      }
    }
    description
     "Represents the ids of the stats vlolume table
      Here is what each entry corresponds.
      1 : Seconds Table: Here each entry corresponds to a second
      2 : Minutes Table: Here each entry corresponds to a minute
      3 : Hours Table: Here each entry corresponds to an hour";
  }

  typedef CvSessionProtocol {
    type enumeration {
      enum "other" {
        value "1";
      }
      enum "cisco" {
        value "2";
      }
      enum "sdp" {
        value "3";
      }
      enum "sip" {
        value "4";
      }
      enum "multicast" {
        value "5";
      }
      enum "sccp" {
        value "6";
      }
    }
    description
     "Represents a Session Protocol used by Voice calls between a
      local and remote router via the IP backbone.
      
      other - none of the following.
      cisco - cisco proprietary H.323 Lite session protocol.
      sdp   - Session Description Protocol.
      sip   - Session Initiation Protocol.
      sccp  - Skinny Call Control Protocol.";
  }

  typedef CvCasGroup {
    type int32 {
      range "-1..30";
    }
    description
     "The Channel Associated Signalling Group of a
      T1/E1. The valid CAS group range is from 0 to 23 for T1
      and from 0 to 30 for E1. The value -1 indicates CAS group is
      disabled.";
    smiv2:display-hint "d";
  }

  typedef CvAmrNbBitRateMode {
    type bits {
      bit amrBitRateMode0 {
        position "0";
      }
      bit amrBitRateMode1 {
        position "1";
      }
      bit amrBitRateMode2 {
        position "2";
      }
      bit amrBitRateMode3 {
        position "3";
      }
      bit amrBitRateMode4 {
        position "4";
      }
      bit amrBitRateMode5 {
        position "5";
      }
      bit amrBitRateMode6 {
        position "6";
      }
      bit amrBitRateMode7 {
        position "7";
      }
    }
    description
     "Represents GSM AMR-NB bit rate modes.
      
      CodecMode             Bit-rate (kbps)
      0                     4.75
      1                     5.15
      2                     5.90
      3                     6.70
      4                     7.40
      5                     7.95
      6                     10.2
      7                     12.2";
  }

  typedef CvAmrNbRtpEncap {
    type enumeration {
      enum "rfc3267" {
        value "1";
      }
    }
    description
     "Represents GSM AMR-NB codec RTP encapsulation type.";
  }

  typedef CvIlbcFrameMode {
    type enumeration {
      enum "frameMode20" {
        value "20";
      }
      enum "frameMode30" {
        value "30";
      }
    }
    description
     "This Texatual Convention represents the iLBC codec
      frame modes.  
      The possible values are :
      frameMode20: This mode operates at 15.2 kbps and each 
                   frame is packetized in 38 bytes. 
      frameMode30: This mode operates at 13.33 kbps and each 
                   frame is packetized in 50 bytes.";
    reference
     "RFC 3952: Section 4.2 for details about iLBC mode";
  }

  typedef CvCallConnectionType {
    type enumeration {
      enum "h323" {
        value "1";
      }
      enum "sip" {
        value "2";
      }
      enum "mgcp" {
        value "3";
      }
      enum "sccp" {
        value "4";
      }
      enum "multicast" {
        value "5";
      }
      enum "cacontrol" {
        value "6";
      }
      enum "telephony" {
        value "7";
      }
    }
    description
     "Call connection represents the connection/association/session
      between two media call end points. Following are the different
      connection types.
      
      h323       - h323 protocol.
      sip        - Session Initiation Protocol.
      mgcp       - Media Gateway Control Protocol.
      sccp       - Cisco proprietary Skinny Call Control Protocol.
      multicast  - multicast call connections.
      cacontrol  - Call Agent Control.
      telephony  - telephony signal call connections.";
  }


  container CISCO-VOICE-DIAL-CONTROL-MIB {
    config false;

    container cvGeneralConfiguration {
      smiv2:oid "1.3.6.1.4.1.9.9.63.1.1";

      leaf cvGeneralPoorQoVNotificationEnable {
        type boolean;
        description
         "This object indicates whether cvdcPoorQoVNotification (or
          the newer cvdcPoorQoVNotificationRev1) traps should be
          generated for a poor quality of voice calls.
          
          If the value of this object is 'true',
          cvdcPoorQoVNotification (or the newer
          cvdcPoorQoVNotificationRev1) traps will be generated
          for all voice over IP peers when a poor quality of voice
          call condition is detected after the voice gateway call
          disconnection.  If the value of this object is 'false',
          cvdcPoorQoVNotification (or the newer
          cvdcPoorQoVNotificationRev1) traps will be generated only
          for calls for which the
          cvVoIPPeerCfgPoorQoVNotificationEnable object of voice
          over IP peers having set to 'true'.";
        smiv2:defval "false";
        smiv2:max-access "read-write";
        smiv2:oid "1.3.6.1.4.1.9.9.63.1.1.1";
      }

      leaf cvGeneralFallbackNotificationEnable {
        type boolean;
        description
         "This object indicates whether cvdcFallbackNotification
          traps should be generated for fallback.
          If the value of this object is 'true',
          cvdcFallbackNotification traps will be generated
          for all voice over IP peers.";
        smiv2:defval "false";
        smiv2:max-access "read-write";
        smiv2:oid "1.3.6.1.4.1.9.9.63.1.1.2";
      }

      leaf cvGeneralDSCPPolicyNotificationEnable {
        type boolean;
        description
         "This object indicates whether cvdcPolicyViolationNotification
          traps should be generated for a RPH to DSCP mapping violation
          for SIP voice calls.
          
          If the value of this object is 'true',
          cvdcPolicyViolationNotification traps will be generated for SIP
          voice over IP peers when a RPH to DSCP violation condition is
          detected .  If the value of this object is 'false',
          cvdcPolicyViolationNotification traps will be generated only
          for calls for which the 
          cvVoIPPeerCfgDSCPPolicyNotificationEnable object of voice
          over IP peers having set to 'true'.";
        smiv2:defval "false";
        smiv2:max-access "read-write";
        smiv2:oid "1.3.6.1.4.1.9.9.63.1.1.3";
      }

      leaf cvGeneralMediaPolicyNotificationEnable {
        type boolean;
        description
         "This object indicates whether cvdcPolicyViolationNotification
          traps should be generated for Media violation
          for SIP voice calls.
          
          If the value of this object is 'true',
          cvdcPolicyViolationNotification traps will be generated for SIP
          voice over IP peers when media violation condition is
          detected .  If the value of this object is 'false',
          cvdcPolicyViolationNotification traps will be generated only
          for calls for which the 
          cvVoIPPeerCfgMediaPolicyNotificationEnable object of voice
          over IP peers having set to 'true'.";
        smiv2:defval "false";
        smiv2:max-access "read-write";
        smiv2:oid "1.3.6.1.4.1.9.9.63.1.1.4";
      }
    }

    container cvGatewayCallActive {
      smiv2:oid "1.3.6.1.4.1.9.9.63.1.3";

      leaf cvCallActiveDS0s {
        type yang:gauge32;
        units "interfaces";
        description
         "The current number of DS0 interfaces used for the
          active calls.";
        smiv2:max-access "read-only";
        smiv2:oid "1.3.6.1.4.1.9.9.63.1.3.3";
      }

      leaf cvCallActiveDS0sHighThreshold {
        type uint32 {
          range "0..100";
        }
        units "percent";
        description
         "A high threshold used to determine when to generate the
          cvdcActiveDS0sHighNotification. This object 
          represents the percentage of active DS0s in total number 
          of DS0s.";
        smiv2:defval "100";
        smiv2:max-access "read-write";
        smiv2:oid "1.3.6.1.4.1.9.9.63.1.3.4";
      }

      leaf cvCallActiveDS0sLowThreshold {
        type uint32 {
          range "0..100";
        }
        units "percent";
        description
         "A low threshold used to determine when to generate the
          cvdcActiveDS0sLowNotification notification. This object 
          represents the percentage of active DS0s in total number 
          of DS0s.";
        smiv2:defval "0";
        smiv2:max-access "read-write";
        smiv2:oid "1.3.6.1.4.1.9.9.63.1.3.5";
      }

      leaf cvCallActiveDS0sHighNotifyEnable {
        type boolean;
        description
         "Specifies whether or not cvdcActiveDS0sHighNotification
          should be generated.
          
          'true' : Indicates that the cvdcActiveDS0sHighNotification
                   generation is enabled.
          
          'false': Indicates that cvdcActiveDS0sHighNotification
                   generation is disabled.";
        smiv2:defval "false";
        smiv2:max-access "read-write";
        smiv2:oid "1.3.6.1.4.1.9.9.63.1.3.6";
      }

      leaf cvCallActiveDS0sLowNotifyEnable {
        type boolean;
        description
         "Specifies whether or not cvdcActiveDS0sLowNotification
          should be generated.
          
          'true' : Indicates that the cvdcActiveDS0sLowNotification
                   generation is enabled.
          
          'false': Indicates that cvdcActiveDS0sLowNotification
                   generation is disabled.";
        smiv2:defval "false";
        smiv2:max-access "read-write";
        smiv2:oid "1.3.6.1.4.1.9.9.63.1.3.7";
      }
    }

    container cvCallVolume {
      smiv2:oid "1.3.6.1.4.1.9.9.63.1.3.8";

      leaf cvCallVolConnTotalActiveConnections {
        type yang:gauge32 {
          range "0..65535";
        }
        description
         "This object represents the total number of
          active call legs in the voice gateway.";
        smiv2:max-access "read-only";
        smiv2:oid "1.3.6.1.4.1.9.9.63.1.3.8.2";
      }

      leaf cvCallVolConnMaxCallConnectionLicenese {
        type uint32 {
          range "0..65535";
        }
        description
         "This object represents the licensed call capacity
          for a voice gateway.  If the value is 0, no 
          licensing is done and the gateway can be 
          accomodate as many calls depending on its capability.";
        smiv2:max-access "read-only";
        smiv2:oid "1.3.6.1.4.1.9.9.63.1.3.8.3";
      }
    }

    container cvCallRateMonitor {
      smiv2:oid "1.3.6.1.4.1.9.9.63.1.3.11";

      leaf cvCallRateMonitorEnable {
        type boolean;
        description
         "This object represents the state of call-monitoring.
          A value of 'true' indicates that call-monitoring 
          is enabled.  A value of 'false' indicates that 
          call-monitoring is disabled.";
        smiv2:defval "true";
        smiv2:max-access "read-write";
        smiv2:oid "1.3.6.1.4.1.9.9.63.1.3.11.1";
      }

      leaf cvCallRateMonitorTime {
        type uint32 {
          range "1..12";
        }
        units "five seconds";
        description
         "This object represents the interval for
          which the gateway monitors the call-rate.";
        smiv2:defval "1";
        smiv2:max-access "read-write";
        smiv2:oid "1.3.6.1.4.1.9.9.63.1.3.11.2";
      }

      leaf cvCallRate {
        type yang:gauge32 {
          range "0..65535";
        }
        description
         "This object represents the total number of
          calls handled by the gateway during the 
          monitored time.";
        smiv2:max-access "read-only";
        smiv2:oid "1.3.6.1.4.1.9.9.63.1.3.11.3";
      }

      leaf cvCallRateHiWaterMark {
        type uint32 {
          range "0..65535";
        }
        description
         "This object represents the high water mark
          for the number of calls handled by the 
          gateway in an unit interval of 
          cvCallRateMonitorTime, from the time 
          the call-monitoring is enabled.";
        smiv2:max-access "read-only";
        smiv2:oid "1.3.6.1.4.1.9.9.63.1.3.11.4";
      }
    }

    container cvCallVolumeStatsHistory {
      smiv2:oid "1.3.6.1.4.1.9.9.63.1.4.3";

      leaf cvCallDurationStatsThreshold {
        type uint32 {
          range "1..3600";
        }
        units "seconds";
        description
         "This Object specifies the thresold duration in seconds.
          cvCallDurationStatsTable will monitor all the calls below this 
          threshold.
          
          Decresing the value of the threshold will reset this table.";
        smiv2:defval "5";
        smiv2:max-access "read-write";
        smiv2:oid "1.3.6.1.4.1.9.9.63.1.4.3.10";
      }

      leaf cvCallVolumeWMTableSize {
        type uint32 {
          range "3..10";
        }
        description
         "This Object specifies the number of entries the watermark table
          will maintain.
          
          This value will decide the number of elements in
          cvCallRateWMTable,
          cvCallLegRateWMTable, cvActiveCallWMTable and
          cvSipMsgRateWMTable.";
        smiv2:defval "5";
        smiv2:max-access "read-write";
        smiv2:oid "1.3.6.1.4.1.9.9.63.1.4.3.11";
      }
    }

    container cvPeerCfgTable {
      description
       "The table contains the Voice Generic Peer information that
        is used to create an ifIndexed row with an appropriate
        ifType that is associated with the cvPeerCfgType and
        cvPeerCfgPeerType objects.";
      smiv2:oid "1.3.6.1.4.1.9.9.63.1.2.1";

      list cvPeerCfgEntry {
        key "cvPeerCfgIndex";
        description
         "A single voice generic Peer. The creation of this
          entry will create an associated ifEntry with an ifType
          that is associated with cvPeerCfgType, i.e., for
          'voiceEncap' encapsulation, an ifEntry will contain an
          ifType voiceEncap(103); for 'voiceOverIp' encapsulation,
          an ifEntry will contain an ifType voiceOverIp(104). The
          ifAdminStatus of the newly created ifEntry is set to 'up'
          and ifOperStatus is set to 'down'. In addition, an
          associated voiceEncap/voiceOverIp Peer configuration
          entry is created after the successful ifEntry creation.
          Then ifIndex of the newly created ifEntry must be used by
          the network manager to create a peer configuration entry
          of IETF Dial Control MIB (Refer to RFC 2128 section
          2.2.3.1 and the description of dialCtlPeerCfgEntry for the
          detailed information).
          In summary, the voice dial peer creation steps are as
          follows:
          [1] create this entry (voice/data generic peer entry).
          [2] read the cvPeerCfgIfIndex of this entry for the
              ifIndex of newly created voice/data generic peer.
          [3] create the dialCtlPeerCfgEntry of RFC 2128 with the
              indices of dialCtlPeerCfgId and the ifIndex of newly
              created voice generic peer.
          
          For each VoIP peer, it uses IP address and UDP port with
          RTP protocol to transfer voice packet. Therefore, it does
          not have its lower layer interface. The
          dialCtlPeerCfgIfType object of IETF Dial Control MIB must
          set to 'other' and the dialCtlPeerCfgLowerIf must set to
          '0'.
          
          After the successful creation of peer configuration entry
          of IETF Dial Control MIB, the dial plan software in
          managed device will set the ifOperStatus of the newly
          created voiceEncap/voiceOverIp ifEntry to 'up' for
          enabling the peer function if the peer configuration is
          completed.
          When this entry is deleted, its associated ifEntry,
          voiceEncap/voiceOverIp specific peer entry and the peer
          entry of IETF Dial Control MIB are deleted.";
        smiv2:oid "1.3.6.1.4.1.9.9.63.1.2.1.1";

        leaf cvPeerCfgIndex {
          type int32 {
            range "1..2147483647";
          }
          description
           "An arbitrary index that uniquely identifies a generic
            voice peer.";
          smiv2:max-access "not-accessible";
          smiv2:oid "1.3.6.1.4.1.9.9.63.1.2.1.1.1";
        }

        leaf cvPeerCfgIfIndex {
          type if-mib:InterfaceIndexOrZero;
          description
           "The ifIndex of the peer associated ifEntry. The ifIndex
            appears after the associated ifEntry is created
            successfully.
            This ifIndex will be used to access the objects in the
            Voice over Telephony or Voice over IP peer specific table.
            In addition, the ifIndex is also used to access the
            associated peer configuration entry of the IETF Dial
            Control MIB. If the peer associated ifEntry had not been
            created, then this object has a value of zero.";
          smiv2:max-access "read-only";
          smiv2:oid "1.3.6.1.4.1.9.9.63.1.2.1.1.2";
        }

        leaf cvPeerCfgType {
          type enumeration {
            enum "voice" {
              value "1";
            }
            enum "voip" {
              value "2";
            }
            enum "mmail" {
              value "3";
            }
            enum "voatm" {
              value "4";
            }
            enum "vofr" {
              value "5";
            }
          }
          description
           "Specifies the type of voice related encapsulation.
            voice - voice encapsulation (voiceEncap ifType) on the
                    telephony network.
            voip  - VoIP encapsulation (voiceOverIp ifType) on the IP
                    network.
            mmail - Media Mail over IP encapsulation (mediaMailOverIp
                    ifType) on the IP network.
            voatm - VoATM encapsulation (voiceOverATM ifType) on the
                    ATM network.
            vofr  - VoFR encapsulation (voiceOverFR ifType) on the
                    Frame Relay network.";
          smiv2:defval "voice";
          smiv2:max-access "read-write";
          smiv2:oid "1.3.6.1.4.1.9.9.63.1.2.1.1.3";
        }

        leaf cvPeerCfgRowStatus {
          type snmpv2-tc:RowStatus;
          description
           "This object is used to create a new row or modify or
            delete an existing row in this table.";
          smiv2:max-access "read-write";
          smiv2:oid "1.3.6.1.4.1.9.9.63.1.2.1.1.4";
        }

        leaf cvPeerCfgPeerType {
          type enumeration {
            enum "voice" {
              value "1";
            }
            enum "data" {
              value "2";
            }
          }
          description
           "Specifies the type of a peer.
            voice - peer in voice type to be defined in a voice
                    gateway for voice calls. 
            data  - peer in data type to be defined in gateway
                    that supports universal ports for modem/data
                    calls and integrated ports for data calls.";
          smiv2:defval "voice";
          smiv2:max-access "read-write";
          smiv2:oid "1.3.6.1.4.1.9.9.63.1.2.1.1.5";
        }
      }
    }

    container cvVoicePeerCfgTable {
      description
       "The table contains the Voice over Telephony peer specific
        information that is required to accept voice calls or to
        which it will place them or perform various loopback tests
        via interface.";
      smiv2:oid "1.3.6.1.4.1.9.9.63.1.2.2";

      list cvVoicePeerCfgEntry {
        key "ifIndex";
        description
         "A single Voice specific Peer. One entry per voice
          encapsulation.
          The entry is created when its associated 'voiceEncap(103)'
          encapsulation ifEntry is created.
          This entry is deleted when its associated ifEntry is
          deleted.";
        smiv2:oid "1.3.6.1.4.1.9.9.63.1.2.2.1";

        leaf ifIndex {
          type leafref {
            path "/if-mib:IF-MIB/if-mib:ifTable/if-mib:ifEntry/if-mib:ifIndex";
          }
        }

        leaf cvVoicePeerCfgSessionTarget {
          type snmpv2-tc:DisplayString {
            length "0..64";
          }
          description
           "The object specifies the session target of the peer.
            Session Targets definitions:
            The session target has the syntax used by the IETF service
            location protocol. The syntax is as follows:
            
            mapping-type:type-specific-syntax
            
            the mapping-type specifies a scheme for mapping the
            matching dial string to a session target.
            
            The valid Mapping type definitions for the peer are as
            follows:
            loopback - Syntax: loopback:where
               'where' string is defined as follows:
               compressed - loopback is performed on compressed voice
                            as close to the CODEC which processes the
                            data as possible.
               uncompressed - loopback is performed on the PCM or
                            analog voice as close to the telephony
                            endpoint as possible.
            
            Local loopback case:
            uncompressed - the PCM voice coming into the DSP is simply
                turned around and sent back out, allowing testing of
                the transmit--> receive paths in the telephony
                endpoint.
            compressed - the compressed voice coming out of the CODEC is
                turned around on the DSP module and fed back into the
                decompressor through the jitter buffer. In addition to
                the telephony endpoint, this tests both the encode and
                decode paths without involving data paths or packet
                handling on the host router.
            
            Remote loopback case:
            compressed - RTP packets received from the network are
                decapsulated and passed to the DSP board. Instead of
                feeding these into the CODEC for decompression, they
                are immediately sent back to the session application
                as if they had originated locally and been compressed.
            uncompressed - In addition to the above, the voice samples
                are sent all the way through the CODEC and then turned
                around instead of being sent to the telephony
                endpoint";
          smiv2:defval "";
          smiv2:max-access "read-write";
          smiv2:oid "1.3.6.1.4.1.9.9.63.1.2.2.1.1";
        }

        leaf cvVoicePeerCfgDialDigitsPrefix {
          type snmpv2-tc:DisplayString {
            length "0..32";
          }
          description
           "The object specifies the prefix of the dial digits for the
            peer. The dial digits prefix is sent to telephony
            interface before the real phone number when the system
            places the outgoing call to the voice encapsulation peer
            over telephony interface.";
          smiv2:defval "";
          smiv2:max-access "read-write";
          smiv2:oid "1.3.6.1.4.1.9.9.63.1.2.2.1.2";
        }

        leaf cvVoicePeerCfgDIDCallEnable {
          type boolean;
          description
           "The object enables/disables the DID call treatment for
            incoming DNIS digits.
            true  - treat the incoming DNIS digits as if the digits
                    are received from DID trunk.
            false - Disable DID call treatment for incoming DNIS
                    digits.";
          smiv2:defval "false";
          smiv2:max-access "read-write";
          smiv2:oid "1.3.6.1.4.1.9.9.63.1.2.2.1.3";
        }

        leaf cvVoicePeerCfgCasGroup {
          type CISCO-VOICE-DIAL-CONTROL-MIB:CvCasGroup;
          description
           "The object specifies the CAS group number of a CAS
            capable T1/E1  that is in the dialCtlPeerCfgLowerIf object
            of RFC2128.
            This object can be set to a valid CAS group number only if
            the dialCtlPeerCfgLowerIf contains a valid ifIndex for a
            CAS capable T1/E1. The object must set to -1 before the
            value of the  dialCtlPeerCfgLowerIf object of RFC2128 can
            be changed.";
          smiv2:defval "-1";
          smiv2:max-access "read-write";
          smiv2:oid "1.3.6.1.4.1.9.9.63.1.2.2.1.4";
        }

        leaf cvVoicePeerCfgRegisterE164 {
          type boolean;
          description
           "This object specifies that the E.164 number specified in
            the dialCtlPeerCfgOriginateAddress field of the associated
            dialCtlPeerCfgTable entry be registered as an extension 
            phone number of this gateway for H323 gatekeeper and/or 
            SIP registrar.";
          smiv2:defval "false";
          smiv2:max-access "read-write";
          smiv2:oid "1.3.6.1.4.1.9.9.63.1.2.2.1.5";
        }

        leaf cvVoicePeerCfgForwardDigits {
          type int32 {
            range "-3..32";
          }
          description
           "This object specifies the number of dialed digits to
            forward to the remote destination in the setup message.
            The object can take the value:
                0-32 number of right justified digits to forward
                -1 default
                -2 forward extra digits i.e those over and above
                   those needed to match to the destination pattern
                -3 forward all digits";
          smiv2:defval "0";
          smiv2:max-access "read-write";
          smiv2:oid "1.3.6.1.4.1.9.9.63.1.2.2.1.6";
        }

        leaf cvVoicePeerCfgEchoCancellerTest {
          type enumeration {
            enum "echoCancellerTestNone" {
              value "1";
            }
            enum "echoCancellerG168Test2A" {
              value "2";
            }
            enum "echoCancellerG168Test2B" {
              value "3";
            }
            enum "echoCancellerG168Test2Ca" {
              value "4";
            }
            enum "echoCancellerG168Test2Cb" {
              value "5";
            }
            enum "echoCancellerG168Test3A" {
              value "6";
            }
            enum "echoCancellerG168Test3B" {
              value "7";
            }
            enum "echoCancellerG168Test3C" {
              value "8";
            }
            enum "echoCancellerG168Test4" {
              value "9";
            }
            enum "echoCancellerG168Test6" {
              value "10";
            }
            enum "echoCancellerG168Test9" {
              value "11";
            }
            enum "echoCancellerG168Test5" {
              value "12";
            }
            enum "echoCancellerG168Test7" {
              value "13";
            }
          }
          description
           "This object specifies which, if any, test to run in the
            echo canceller when a call from the network is connected.
            echoCancellerTestNone    - do not run a test.
            echoCancellerG168Test2A  - run ITU-T G.168 Test 2A.
            echoCancellerG168Test2B  - run ITU-T G.168 Test 2B.
            echoCancellerG168Test2Ca - run ITU-T G.168 Test 2C(a).
            echoCancellerG168Test2Cb - run ITU-T G.168 Test 2C(b).
            echoCancellerG168Test3A  - run ITU-T G.168 Test 3A.
            echoCancellerG168Test3B  - run ITU-T G.168 Test 3B.
            echoCancellerG168Test3C  - run ITU-T G.168 Test 3C.
            echoCancellerG168Test4   - run ITU-T G.168 Test 4.
            echoCancellerG168Test5   - run ITU-T G.168 Test 5.
            echoCancellerG168Test6   - run ITU-T G.168 Test 6.
            echoCancellerG168Test7   - run ITU-T G.168 Test 7.
            echoCancellerG168Test9   - run ITU-T G.168 Test 9.";
          reference
           "ITU-T G.168(04/2000): Section 6.4 Tests and requirements
            for performance with input signals applied to the send and
            receive paths.";
          smiv2:defval "echoCancellerTestNone";
          smiv2:max-access "read-write";
          smiv2:oid "1.3.6.1.4.1.9.9.63.1.2.2.1.7";
        }
      }
    }

    container cvVoIPPeerCfgTable {
      description
       "The table contains the Voice over IP (VoIP) peer specific
        information that is required to accept voice calls or to
        which it will place them via IP backbone with the
        specified session protocol in cvVoIPPeerCfgSessionProtocol.";
      smiv2:oid "1.3.6.1.4.1.9.9.63.1.2.3";

      list cvVoIPPeerCfgEntry {
        key "ifIndex";
        description
         "A single VoIP specific Peer. One entry per VoIP
          encapsulation.
          The entry is created when its associated 'voiceOverIp(104)'
          encapsulation ifEntry is created.
          This entry is deleted when its associated ifEntry is
          deleted.";
        smiv2:oid "1.3.6.1.4.1.9.9.63.1.2.3.1";

        leaf ifIndex {
          type leafref {
            path "/if-mib:IF-MIB/if-mib:ifTable/if-mib:ifEntry/if-mib:ifIndex";
          }
        }

        leaf cvVoIPPeerCfgSessionProtocol {
          type CISCO-VOICE-DIAL-CONTROL-MIB:CvSessionProtocol;
          description
           "The object specifies the session protocol to be used
            for Internet call between local and remote router via
            IP backbone.";
          smiv2:defval "cisco";
          smiv2:max-access "read-write";
          smiv2:oid "1.3.6.1.4.1.9.9.63.1.2.3.1.1";
        }

        leaf cvVoIPPeerCfgDesiredQoS {
          type int-serv:QosService;
          description
           "The object specifies the user requested Quality of Service
            for the call.";
          smiv2:defval "bestEffort";
          smiv2:max-access "read-write";
          smiv2:oid "1.3.6.1.4.1.9.9.63.1.2.3.1.2";
        }

        leaf cvVoIPPeerCfgMinAcceptableQoS {
          type int-serv:QosService;
          description
           "The object specifies the minimally acceptable Quality of
            Service for the call.";
          smiv2:defval "bestEffort";
          smiv2:max-access "read-write";
          smiv2:oid "1.3.6.1.4.1.9.9.63.1.2.3.1.3";
        }

        leaf cvVoIPPeerCfgSessionTarget {
          type snmpv2-tc:DisplayString;
          description
           "The object specifies the session target of the peer.
            Session Targets definitions:
            The session target has the syntax used by the IETF service
            location protocol. The syntax is as follows:
            
            mapping-type:type-specific-syntax
            
            the mapping-type specifies a scheme for mapping the
            matching dial string to a session target. The
            type-specific-syntax is exactly that, something that the
            particular mapping scheme can understand.
            For example,
            Session target           Meaning
            ipv4:171.68.13.55:1006   The session target is the IP
                                     version 4 address of 171.68.13.55
                                     and port 1006.
            dns:pots.cisco.com:1661  The session target is the IP host
                                     with dns name pots.cisco.com, and
                                     port 1661.
            ras                      The session target is the
                                     gatekeeper with RAS (Registration
                                     , Admission,  Status protocol).
            settlement               The session target is the
                                     settlement server.
            enum:1                   The session target is the enum 
                                     profile match table 1.
            
            The valid Mapping type definitions for the peer are as
            follows:
            ipv4       - Syntax: ipv4:w.x.y.z:port or  ipv4:w.x.y.z
            dns        - Syntax: dns:host.domain:port or
                                 dns:host.domain
            ras        - Syntax: ras
            settlement - Syntax: settlement
            enum       - Syntax: enum:
            
            loopback - Syntax: loopback:where
               'where' string is defined as follows:
               rtp - loopback is performed at the transport protocol
                     level.
            
            Local loopback case:
            rtp - the session application sets up an RTP stream to
                itself (i.e. actually allocates a port pair and opens
                the appropriate UDP sockets). It then does the full
                RTP encapsulation, sends the packets to the loopback
                IP address, receives the RTP packets, and hands the
                compressed voice back to the CODEC. This tests the
                entire local processing path, both transmit and
                receive, in the router, as well as all of the above
                paths.
            
            Remote loopback case:
            rtp: RTP packets received from the network are decapsulated and
                 immediately re-encapsulated in the outbound RTP
                 stream, using the same media clock (i.e. timestamp)
                 as the received packet. They are then sent back to
                 the remote source router as if the voice had
                 originated on a telephony port on the local router.";
          smiv2:defval "";
          smiv2:max-access "read-write";
          smiv2:oid "1.3.6.1.4.1.9.9.63.1.2.3.1.4";
        }

        leaf cvVoIPPeerCfgCoderRate {
          type cisco-voice:CvcSpeechCoderRate;
          description
           "This object specifies the most desirable codec of speech
            for the VoIP peer.";
          smiv2:defval "g729IETFr8000";
          smiv2:max-access "read-write";
          smiv2:oid "1.3.6.1.4.1.9.9.63.1.2.3.1.5";
        }

        leaf cvVoIPPeerCfgFaxRate {
          type cisco-voice:CvcFaxTransmitRate;
          description
           "This object specifies the default transmit rate of FAX
            the VoIP peer. If the value of this object is 'none',
            then the Fax relay feature is disabled; otherwise the Fax
            relay feature is enabled.";
          smiv2:defval "voiceRate";
          smiv2:max-access "read-write";
          smiv2:oid "1.3.6.1.4.1.9.9.63.1.2.3.1.6";
        }

        leaf cvVoIPPeerCfgVADEnable {
          type boolean;
          description
           "This object specifies whether or not the VAD (Voice
            Activity Detection) voice data is continuously transmitted
            to IP backbone.";
          smiv2:defval "true";
          smiv2:max-access "read-write";
          smiv2:oid "1.3.6.1.4.1.9.9.63.1.2.3.1.7";
        }

        leaf cvVoIPPeerCfgExpectFactor {
          type int32 {
            range "0..20";
          }
          units "equipment impairment factor (eif)";
          description
           "This object specifies the user requested Expectation
            Factor of voice quality for the call via this peer.";
          reference
           "ITU G.113: Sections 8 Considerations Concerning the
            Expectation Factor A.";
          smiv2:defval "0";
          smiv2:max-access "read-write";
          smiv2:oid "1.3.6.1.4.1.9.9.63.1.2.3.1.8";
        }

        leaf cvVoIPPeerCfgIcpif {
          type int32 {
            range "0..55";
          }
          units "equipment impairment factor (eif)";
          description
           "This object specifies the user requested Calculated
            Planning Impairment Factor (Icpif) for the call via this
            peer.";
          reference
           "ITU G.113: Sections 9 Considerations associated with the
            Calculated Planning Impairment Factor (Icpif)";
          smiv2:defval "20";
          smiv2:max-access "read-write";
          smiv2:oid "1.3.6.1.4.1.9.9.63.1.2.3.1.9";
        }

        leaf cvVoIPPeerCfgPoorQoVNotificationEnable {
          type boolean;
          description
           "This object specifies whether cvdcPoorQoVNotification (or
            the newer cvdcPoorQoVNotificationRev1) traps should be
            generated for the call that is associated with this
            peer.";
          smiv2:defval "false";
          smiv2:max-access "read-write";
          smiv2:oid "1.3.6.1.4.1.9.9.63.1.2.3.1.10";
        }

        leaf cvVoIPPeerCfgUDPChecksumEnable {
          type boolean;
          description
           "This object specifies whether the outgoing voice related
            UDP packet contains a valid checksum value.
            true  - enable the checksum of outgoing voice UDP packets
            false - disable the checksum of outgoing voice UDP packets";
          smiv2:defval "false";
          smiv2:max-access "read-write";
          smiv2:oid "1.3.6.1.4.1.9.9.63.1.2.3.1.11";
        }

        leaf cvVoIPPeerCfgIPPrecedence {
          type int32 {
            range "0..7";
          }
          description
           "This object specifies the value to be stored in the IP
            Precedence field of voice packets, with values ranging
            from 0 (normal precedence) through 7 (network control),
            allowing the managed system to set the importance of each
            voice packet for delivering them to the destination peer.";
          reference
           "RFC 791: Section 3.1.  Internet Header Format; Type of
            Service.";
          smiv2:defval "0";
          smiv2:max-access "read-write";
          smiv2:oid "1.3.6.1.4.1.9.9.63.1.2.3.1.12";
        }

        leaf cvVoIPPeerCfgTechPrefix {
          type snmpv2-tc:DisplayString {
            length "0..128";
          }
          description
           "This object specifies the technology prefix of the peer,
            The technology prefix and the called party address
            are passed in Admission Request (ARQ) to gatekeeper
            for the called party address resolution during call setup.";
          reference
           "ITU-T H.225.0: Section 7.6 Common Message Elements.";
          smiv2:defval "";
          smiv2:max-access "read-write";
          smiv2:oid "1.3.6.1.4.1.9.9.63.1.2.3.1.13";
        }

        leaf cvVoIPPeerCfgDigitRelay {
          type bits {
            bit rtpCisco {
              position "0";
            }
            bit h245Signal {
              position "1";
            }
            bit h245Alphanumeric {
              position "2";
            }
            bit rtpNte {
              position "3";
            }
            bit sipNotify {
              position "4";
            }
            bit sipKpml {
              position "5";
            }
          }
          description
           "This object specifies the methods to transmit dial digits
            (DTMF or MF digits) via IP network.
            rtpCisco       - Enable capability to transmit dial digits
                             with Cisco proprietary RTP payload type.
            h245Signal     - Enable capability to transmit dtmf digits
                             across the H.245 channel, via the signal
                             field of the UserInputIndication message
            h245Alphanumeric - Enable capability to transmit dtmf
                             digit across the H.245 channel, via the
                             string or alphanumeric fields of the
                             UserInputIndication message
            rtpNte         - Enable capability to transmit dial digits
                             using Named Telephony Event per RFC 2833
                             section 3.
            sipNotify      - Enable capability to transmit dtmf
                             digits using unsolicited SIP NOTIFY
                             messages. This mechanism is only available
                             for SIP dialpeers.
            sipKpml        - Enable capability to transmit dtmf
                             digits using KPML over SIP SUBSCRIBE
                             and NOTIFY messages. This mechanism is
                             only available for SIP dialpeers.
            
            
            Modifying the value of cvVoIPPeerCfgSessionProtocol
            can reset the digit-relay method associated bits value in
            this object if the modified session protocol does not
            support  these digit-relay methods.";
          reference
           "[1] ITU H.245: Section 6.
            [2] RFC 2833 : Section 3.";
          smiv2:defval "{}";
          smiv2:max-access "read-write";
          smiv2:oid "1.3.6.1.4.1.9.9.63.1.2.3.1.14";
        }

        leaf cvVoIPPeerCfgCoderBytes {
          type int32 {
            range "0|10..240";
          }
          units "bytes";
          description
           "This object specifies the size of the voice payload sample
            to be produced by the coder specified in
            cvVoIPPeerCfgCoderRate.
            Each coder sample produces 10 bytes of voice payload. The
            specified value will be rounded down to the nearest valid
            size.
            
            A value of 0, specifies that the coder defined by
            cvVoIPPeerCfgCoderRate should produce its default payload
            size.";
          smiv2:defval "0";
          smiv2:max-access "read-write";
          smiv2:oid "1.3.6.1.4.1.9.9.63.1.2.3.1.15";
        }

        leaf cvVoIPPeerCfgFaxBytes {
          type int32 {
            range "0|10..255";
          }
          units "bytes";
          description
           "This object specifies the payload size to be produced by
            the coder when it is generating fax data. A value of 0,
            specifies that the coder specified in
            cvVoIPCfgPeerCoderRate should produce its default fax
            payload size.";
          smiv2:defval "0";
          smiv2:max-access "read-write";
          smiv2:oid "1.3.6.1.4.1.9.9.63.1.2.3.1.16";
        }

        leaf cvVoIPPeerCfgInBandSignaling {
          type cisco-voice:CvcInBandSignaling;
          description
           "This object specifies the type of in-band signaling that
            will be used between the end points of the call. It is
            used by the router to determine how to interpret ABCD
            signaling bits sent as part of voice payload data.";
          smiv2:defval "cas";
          smiv2:max-access "read-write";
          smiv2:oid "1.3.6.1.4.1.9.9.63.1.2.3.1.17";
        }

        leaf cvVoIPPeerCfgMediaSetting {
          type enumeration {
            enum "flowThrough" {
              value "1";
            }
            enum "flowAround" {
              value "2";
            }
          }
          description
           "This object specifies how the media is to be setup on
            an IP-IP Gateway. Two choices are valid: flow-through
            and flow-around. When in flow-through mode, which is the
            default setting, the IP-IP Gateway will terminate and 
            then re-originate the media stream. When flow-around
            is configured the Gateway will not be involved with the
            media, since it will flow-around the Gateway and will
            be established directly between the endpoints.";
          smiv2:defval "flowThrough";
          smiv2:max-access "read-write";
          smiv2:oid "1.3.6.1.4.1.9.9.63.1.2.3.1.23";
        }

        leaf cvVoIPPeerCfgDesiredQoSVideo {
          type int-serv:QosService;
          description
           "The object specifies the user requested Quality of Service
            for the video portion of the call.";
          smiv2:defval "bestEffort";
          smiv2:max-access "read-write";
          smiv2:oid "1.3.6.1.4.1.9.9.63.1.2.3.1.24";
        }

        leaf cvVoIPPeerCfgMinAcceptableQoSVideo {
          type int-serv:QosService;
          description
           "The object specifies the minimally acceptable Quality of
            Service for the video portion of the call.";
          smiv2:defval "bestEffort";
          smiv2:max-access "read-write";
          smiv2:oid "1.3.6.1.4.1.9.9.63.1.2.3.1.25";
        }

        leaf cvVoIPPeerCfgRedirectip2ip {
          type boolean;
          description
           "This object specifies the Inbound VoIP calls that match
            an outbound VoIP dialpeer will be responded with a SIP 
            redirect(for inbound SIP) or H.450.3 call-forward(for 
            inbound H.323).";
          smiv2:defval "false";
          smiv2:max-access "read-write";
          smiv2:oid "1.3.6.1.4.1.9.9.63.1.2.3.1.26";
        }

        leaf cvVoIPPeerCfgOctetAligned {
          type boolean;
          description
           "If the object has a value true(1) octet align operation
            is used, and if the value is false(2), bandwidth efficient
            operation is used. This object is not instantiated when
            the object cvVoIPPeerCfgCoderRate is not equal to
            gsmAmrNb enum.";
          smiv2:defval "true";
          smiv2:max-access "read-write";
          smiv2:oid "1.3.6.1.4.1.9.9.63.1.2.3.1.27";
        }

        leaf cvVoIPPeerCfgBitRates {
          type CISCO-VOICE-DIAL-CONTROL-MIB:CvAmrNbBitRateMode;
          description
           "This object indicates modes of Bit rates. One or more
            upto four modes can be configured at the same time as
            bit rates can be changed dynamically for AMR-NB codec.
            This object is not instantiated when the object
            cvVoIPPeerCfgCoderRate is not equal to gsmAmrNb enum.";
          smiv2:defval "{}";
          smiv2:max-access "read-write";
          smiv2:oid "1.3.6.1.4.1.9.9.63.1.2.3.1.28";
        }

        leaf cvVoIPPeerCfgCRC {
          type boolean;
          description
           "If the object has a value of true(1), frame CRC will be
            included in the payload and if the value is false(2),
            frame CRC will not be included in the payload.
            This object is applicable only when RTP frame type
            is octet aligned. This object is not instantiated when
            the object cvVoIPPeerCfgCoderRate is not equal to
            gsmAmrNb enum.";
          smiv2:defval "false";
          smiv2:max-access "read-write";
          smiv2:oid "1.3.6.1.4.1.9.9.63.1.2.3.1.29";
        }

        leaf cvVoIPPeerCfgCoderMode {
          type CISCO-VOICE-DIAL-CONTROL-MIB:CvIlbcFrameMode;
          description
           "This object indicates the iLBC codec mode to be used.
            The value of this object is valid only if 
            cvVoIPPeerCfgCoderRate is equal to 'iLBC'.";
          reference
           "RFC 3952: Section 4.2 -  MIME Registration of iLBC";
          smiv2:defval "frameMode20";
          smiv2:max-access "read-write";
          smiv2:oid "1.3.6.1.4.1.9.9.63.1.2.3.1.30";
        }

        leaf cvVoIPPeerCfgCodingMode {
          type enumeration {
            enum "adaptive" {
              value "1";
            }
            enum "independent" {
              value "2";
            }
          }
          description
           "This object specifies the coding mode to be used. The object is
            instantiated only if cvVoIPPeerCfgCoderRate is 'iSAC'. Following
            coding modes are supported:
            adaptive    (1) - adaptive mode where iSAC performs bandwidth  
                              estimation and adapts to the available channel
            
                              bandwidth.
            independent (2) - independent mode in which no bandwidth
            estimation 
                              is performed.";
          smiv2:defval "independent";
          smiv2:max-access "read-write";
          smiv2:oid "1.3.6.1.4.1.9.9.63.1.2.3.1.31";
        }

        leaf cvVoIPPeerCfgBitRate {
          type uint32 {
            range "10000..32000";
          }
          description
           "This object specifies the target bit rate. The object is
            instantiated only if cvVoIPPeerCfgCoderRate is 'iSAC'.";
          smiv2:defval "32000";
          smiv2:max-access "read-write";
          smiv2:oid "1.3.6.1.4.1.9.9.63.1.2.3.1.32";
        }

        leaf cvVoIPPeerCfgFrameSize {
          type enumeration {
            enum "frameSize30" {
              value "1";
            }
            enum "frameSize60" {
              value "2";
            }
            enum "frameSize30fixed" {
              value "3";
            }
            enum "frameSize60fixed" {
              value "4";
            }
          }
          description
           "This object specifies the frame size used. The object is
            instantiated only if cvVoIPPeerCfgCoderRate is 'iSAC'.
            The frame size can be 30 ms or 60 ms, and it can be fixed for
            all packets or vary depending on the configuration and bandwidth
            estimation. Thus it can have the following values:
            frameSize30      - initial frame size of 30 ms
            frameSize60      - initial frame size of 60 ms
            frameSize30fixed - fixed frame size 30 ms
            frameSize60fixed - fixed frame size 60 ms";
          smiv2:defval "frameSize30";
          smiv2:max-access "read-write";
          smiv2:oid "1.3.6.1.4.1.9.9.63.1.2.3.1.33";
        }

        leaf cvVoIPPeerCfgDSCPPolicyNotificationEnable {
          type boolean;
          description
           "This object specifies whether cvdcPolicyViolationNotification
            traps should be generated for the call that is associated with
            this peer for RPH to DSCP mapping and policing feature.";
          smiv2:defval "false";
          smiv2:max-access "read-write";
          smiv2:oid "1.3.6.1.4.1.9.9.63.1.2.3.1.34";
        }

        leaf cvVoIPPeerCfgMediaPolicyNotificationEnable {
          type boolean;
          description
           "This object specifies whether cvdcPolicyViolationNotification
            traps should be generated for the call that is associated with
            this peer for Media policing feature..";
          smiv2:defval "false";
          smiv2:max-access "read-write";
          smiv2:oid "1.3.6.1.4.1.9.9.63.1.2.3.1.35";
        }
      }
    }

    container cvPeerCommonCfgTable {
      description
       "The table contains the Voice specific peer common
        configuration information that is required to accept voice
        calls or to which it will place them or process the
        incoming calls.";
      smiv2:oid "1.3.6.1.4.1.9.9.63.1.2.4";

      list cvPeerCommonCfgEntry {
        key "ifIndex";
        description
         "A single Voice specific Peer. One entry per voice related
          encapsulation.
          The entry is created when a voice related encapsulation
          ifEntry is created.
          This entry is deleted when its associated ifEntry is
          deleted.";
        smiv2:oid "1.3.6.1.4.1.9.9.63.1.2.4.1";

        leaf ifIndex {
          type leafref {
            path "/if-mib:IF-MIB/if-mib:ifTable/if-mib:ifEntry/if-mib:ifIndex";
          }
        }

        leaf cvPeerCommonCfgIncomingDnisDigits {
          type snmpv2-tc:DisplayString {
            length "0..32";
          }
          description
           "The object specifies the prefix of the incoming Dialed
            Number Identification Service (DNIS) digits for the peer.
            The DNIS digits prefix is used to match with the incoming
            DNIS number for incoming call discrimination. If the
            digits in this object are matched with incoming DNIS
            number, the  associated dialCtlPeerCfgInfoType in RFC 2128
            will be used as a call discriminator for differentiating
            speech, data, fax, video or modem calls.";
          smiv2:defval "";
          smiv2:max-access "read-write";
          smiv2:oid "1.3.6.1.4.1.9.9.63.1.2.4.1.1";
        }

        leaf cvPeerCommonCfgMaxConnections {
          type int32 {
            range "-1|1..2147483647";
          }
          units "connections";
          description
           "The object specifies the maximum allowed connection
            to/from the peer. A value of -1 disables the limit of
            maximum connections.";
          smiv2:defval "-1";
          smiv2:max-access "read-write";
          smiv2:oid "1.3.6.1.4.1.9.9.63.1.2.4.1.2";
        }

        leaf cvPeerCommonCfgApplicationName {
          type snmpv2-tc:DisplayString;
          description
           "The object specifies the application to handle the incoming
            call after the peer is selected.
            If no application name is specified, then the default
            session application will take care of the incoming call.";
          smiv2:defval "";
          smiv2:max-access "read-write";
          smiv2:oid "1.3.6.1.4.1.9.9.63.1.2.4.1.3";
        }

        leaf cvPeerCommonCfgPreference {
          type int32 {
            range "0..10";
          }
          description
           "This object specifies the selection preference of a peer
            when multiple peers are matched to the selection criteria.
            The value of 0 has the lowest preference for peer
            selection.";
          smiv2:defval "0";
          smiv2:max-access "read-write";
          smiv2:oid "1.3.6.1.4.1.9.9.63.1.2.4.1.4";
        }

        leaf cvPeerCommonCfgHuntStop {
          type boolean;
          description
           "This object specifies whether dialpeer hunting should stop
            when this peer is reached.";
          smiv2:defval "false";
          smiv2:max-access "read-write";
          smiv2:oid "1.3.6.1.4.1.9.9.63.1.2.4.1.5";
        }

        leaf cvPeerCommonCfgDnisMappingName {
          type cisco-voice-dnis:DnisMapname;
          description
           "The object specifies a Dialer Number Identification
            Service (DNIS) map name for the Voice specific peer
            entry specified in this row. A DNIS is a called party
            number and they can be grouped and identified by DNIS
            map.";
          smiv2:defval "";
          smiv2:max-access "read-write";
          smiv2:oid "1.3.6.1.4.1.9.9.63.1.2.4.1.6";
        }

        leaf cvPeerCommonCfgSourceCarrierId {
          type snmp-framework:SnmpAdminString;
          description
           "The object specifies the Source Carrier Id for the peer.
            The Source Carrier Id is used to match with the Source
            Carrier Id of a call. If the Source Carrier Id in this
            object is matched with the Source Carrier Id of a call,
            then the associated peer will be used to handle the call. 
            Only alphanumeric characters, '-' and '_' are allowed in
            the string.";
          smiv2:defval "";
          smiv2:max-access "read-write";
          smiv2:oid "1.3.6.1.4.1.9.9.63.1.2.4.1.7";
        }

        leaf cvPeerCommonCfgTargetCarrierId {
          type snmp-framework:SnmpAdminString;
          description
           "The object specifies the Target Carrier Id for the peer.
            The Target Carrier Id is used to match with the Target
            Carrier Id of a call. If the Target Carrier Id in this
            object is matched with the Target Carrier Id of a call,
            then the associated peer will be used to handle the call.
            Only alphanumeric characters, '-' and '_' are allowed in
            the string.";
          smiv2:defval "";
          smiv2:max-access "read-write";
          smiv2:oid "1.3.6.1.4.1.9.9.63.1.2.4.1.8";
        }

        leaf cvPeerCommonCfgSourceTrunkGrpLabel {
          type snmp-framework:SnmpAdminString;
          description
           "The object specifies the Source Trunk Group Label for the
            peer. The Source Trunk Group Label is used to match with
            the Source Trunk Group Label of a call. If the Source
            Trunk Group Label in this object is matched with the
            Source Trunk Group Label of a call, then the associated
            peer will be used to handle the call. 
            Only alphanumeric characters, '-' and '_' are allowed in
            the string.";
          smiv2:defval "";
          smiv2:max-access "read-write";
          smiv2:oid "1.3.6.1.4.1.9.9.63.1.2.4.1.9";
        }

        leaf cvPeerCommonCfgTargetTrunkGrpLabel {
          type snmp-framework:SnmpAdminString;
          description
           "The object specifies the Target Trunk Group Label for the
            peer. The Target Trunk Group Label is used to match with
            the Target Trunk Group Label of a call. If the Target
            Trunk Group Label in this object is matched with the
            Target Trunk Group Label of a call, then the associated
            peer will be used to handle the call.
            Only alphanumeric characters, '-' and '_' are allowed in
            the string.";
          smiv2:defval "";
          smiv2:max-access "read-write";
          smiv2:oid "1.3.6.1.4.1.9.9.63.1.2.4.1.10";
        }
      }
    }

    container cvCallActiveTable {
      description
       "This table is the voice extension to the call active table
        of IETF Dial Control MIB. It contains voice encapsulation
        call leg information that is derived from the statistics
        of lower layer telephony interface.";
      smiv2:oid "1.3.6.1.4.1.9.9.63.1.3.1";

      list cvCallActiveEntry {
        key "callActiveSetupTime callActiveIndex";
        description
         "The information regarding a single voice encapsulation
          call leg.
          The call leg entry is identified by using the same index
          objects that are used by Call Active table of IETF Dial
          Control MIB to identify the call.
          An entry of this table is created when its associated call
          active entry in the IETF Dial Control MIB is created and
          call active entry contains the call establishment to a
          voice over telephony network peer.
          The entry is deleted when its associated call active entry
          in the IETF Dial Control MIB is deleted.";
        smiv2:oid "1.3.6.1.4.1.9.9.63.1.3.1.1";

        leaf callActiveSetupTime {
          type leafref {
            path "/dial-control:DIAL-CONTROL-MIB/dial-control:callActiveTable/dial-control:callActiveEntry/dial-control:callActiveSetupTime";
          }
        }

        leaf callActiveIndex {
          type leafref {
            path "/dial-control:DIAL-CONTROL-MIB/dial-control:callActiveTable/dial-control:callActiveEntry/dial-control:callActiveIndex";
          }
        }

        leaf cvCallActiveConnectionId {
          type cisco-voice:CvcGUid;
          description
           "The global connection identifier for the
            active telephony leg of the call.";
          smiv2:max-access "read-only";
          smiv2:oid "1.3.6.1.4.1.9.9.63.1.3.1.1.1";
        }

        leaf cvCallActiveTxDuration {
          type dial-control:AbsoluteCounter32;
          units "milliseconds";
          description
           "Duration of Transmit path open from this peer to the
            voice gateway for the call leg. This counter object will
            lock at the maximum value which is approximately two
            days.";
          smiv2:max-access "read-only";
          smiv2:oid "1.3.6.1.4.1.9.9.63.1.3.1.1.2";
        }

        leaf cvCallActiveVoiceTxDuration {
          type dial-control:AbsoluteCounter32;
          units "milliseconds";
          description
           "Duration of voice transmitted from this peer to voice
            gateway for this call leg. The Voice Utilization Rate can
            be obtained by dividing this by cvCallActiveTXDuration
            object. This counter object will lock at the maximum
            value which is approximately two days.";
          smiv2:max-access "read-only";
          smiv2:oid "1.3.6.1.4.1.9.9.63.1.3.1.1.3";
        }

        leaf cvCallActiveFaxTxDuration {
          type dial-control:AbsoluteCounter32;
          units "milliseconds";
          description
           "Duration of fax transmitted from this peer to voice gateway
            for this call leg. The FAX Utilization Rate can be
            obtained by dividing this by cvCallActiveTXDuration
            object. This counter object will lock at the maximum
            value which is approximately two days.";
          smiv2:max-access "read-only";
          smiv2:oid "1.3.6.1.4.1.9.9.63.1.3.1.1.4";
        }

        leaf cvCallActiveCoderTypeRate {
          type cisco-voice:CvcCoderTypeRate;
          description
           "The negotiated coder rate. It specifies the transmit rate of
            voice/fax compression to its associated call leg for the
            call.";
          smiv2:max-access "read-only";
          smiv2:oid "1.3.6.1.4.1.9.9.63.1.3.1.1.5";
        }

        leaf cvCallActiveNoiseLevel {
          type int32 {
            range "-128..8";
          }
          units "dBm";
          description
           "The object contains the active noise level for the call
            leg.";
          smiv2:max-access "read-only";
          smiv2:oid "1.3.6.1.4.1.9.9.63.1.3.1.1.6";
        }

        leaf cvCallActiveACOMLevel {
          type int32 {
            range "-1..127";
          }
          units "dB";
          description
           "The object contains the sum of Echo Return Loss (ERL),
            cancellation loss (Echo Return Loss Enhancement) and
            nonlinear processing loss for the call leg.
            The value -1 indicates the level can not be determined or
            level detection is disabled.";
          smiv2:max-access "read-only";
          smiv2:oid "1.3.6.1.4.1.9.9.63.1.3.1.1.7";
        }

        leaf cvCallActiveOutSignalLevel {
          type int32 {
            range "-128..8";
          }
          units "dBm";
          description
           "The object contains the active output signal level to
            telephony interface that is used by the call leg.";
          smiv2:max-access "read-only";
          smiv2:oid "1.3.6.1.4.1.9.9.63.1.3.1.1.8";
        }

        leaf cvCallActiveInSignalLevel {
          type int32 {
            range "-128..8";
          }
          units "dBm";
          description
           "The object contains the active input signal level from
            telephony interface that is used by the call leg.";
          smiv2:max-access "read-only";
          smiv2:oid "1.3.6.1.4.1.9.9.63.1.3.1.1.9";
        }

        leaf cvCallActiveERLLevel {
          type int32 {
            range "-1..45";
          }
          units "dB";
          status deprecated;
          description
           "The object contains the current Echo Return Loss (ERL)
            level for the call leg.
            The value -1 indicates the level can not be determined or
            level detection is disabled.";
          smiv2:max-access "read-only";
          smiv2:oid "1.3.6.1.4.1.9.9.63.1.3.1.1.10";
        }

        leaf cvCallActiveSessionTarget {
          type snmpv2-tc:DisplayString {
            length "0..64";
          }
          description
           "The object specifies the session target of the peer that
            is used for the call leg. This object is set with the
            information in the call associated
            cvVoicePeerCfgSessionTarget object when the call is
            connected.";
          smiv2:max-access "read-only";
          smiv2:oid "1.3.6.1.4.1.9.9.63.1.3.1.1.11";
        }

        leaf cvCallActiveImgPageCount {
          type dial-control:AbsoluteCounter32;
          units "pages";
          description
           "The number of FAX related image pages are received or
            transmitted via the peer for the call leg.";
          smiv2:max-access "read-only";
          smiv2:oid "1.3.6.1.4.1.9.9.63.1.3.1.1.12";
        }

        leaf cvCallActiveCallingName {
          type snmp-framework:SnmpAdminString;
          description
           "The calling party name of the call. If the name is
            not available, then it will have a length of zero.";
          smiv2:max-access "read-only";
          smiv2:oid "1.3.6.1.4.1.9.9.63.1.3.1.1.13";
        }

        leaf cvCallActiveCallerIDBlock {
          type boolean;
          description
           "The object indicates whether or not the caller ID feature
            is blocked for this call.";
          smiv2:max-access "read-only";
          smiv2:oid "1.3.6.1.4.1.9.9.63.1.3.1.1.14";
        }

        leaf cvCallActiveEcanReflectorLocation {
          type int32 {
            range "0..128";
          }
          description
           "The location in milliseconds of the largest amplitude
            reflector detected by the echo canceller for this call. 
            The value 0 indicates there is no reflector or the 
            information is not available.";
          smiv2:max-access "read-only";
          smiv2:oid "1.3.6.1.4.1.9.9.63.1.3.1.1.15";
        }

        leaf cvCallActiveAccountCode {
          type snmp-framework:SnmpAdminString {
            length "0..50";
          }
          description
           "The object indicates the account code input to the call.
            It could be used for call screen or by down stream server
            for billing purpose.
            The value of empty string indicates no account code input.";
          smiv2:defval "";
          smiv2:max-access "read-only";
          smiv2:oid "1.3.6.1.4.1.9.9.63.1.3.1.1.16";
        }

        leaf cvCallActiveERLLevelRev1 {
          type int32 {
            range "-1..200";
          }
          units "dB";
          description
           "The object contains the current Echo Return Loss (ERL)
            level for the call leg.
            The value -1 indicates the level can not be determined or
            level detection is disabled.";
          smiv2:max-access "read-only";
          smiv2:oid "1.3.6.1.4.1.9.9.63.1.3.1.1.17";
        }

        leaf cvCallActiveCallId {
          type uint32 {
            range "1..4294967295";
          }
          description
           "This object represents the call identifier
            for the active telephony leg of the call.";
          smiv2:max-access "read-only";
          smiv2:oid "1.3.6.1.4.1.9.9.63.1.3.1.1.18";
        }
      }
    }

    container cvVoIPCallActiveTable {
      description
       "This table is the VoIP extension to the call active table of
        IETF Dial Control MIB. It contains VoIP call leg
        information about specific VoIP call destination and the
        selected QoS for the call leg.";
      smiv2:oid "1.3.6.1.4.1.9.9.63.1.3.2";

      list cvVoIPCallActiveEntry {
        key "callActiveSetupTime callActiveIndex";
        description
         "The information regarding a single VoIP call leg.
          The call leg entry is identified by using the same index
          objects that are used by Call Active table of IETF Dial
          Control MIB to identify the call.
          An entry of this table is created when its associated call
          active entry in the IETF Dial Control MIB is created and
          the call active entry contains information for the call
          establishment to the peer on the IP backbone via a voice
          over  IP peer.
          The entry is deleted when its associated call active entry
          in the IETF Dial Control MIB is deleted.";
        smiv2:oid "1.3.6.1.4.1.9.9.63.1.3.2.1";

        leaf callActiveSetupTime {
          type leafref {
            path "/dial-control:DIAL-CONTROL-MIB/dial-control:callActiveTable/dial-control:callActiveEntry/dial-control:callActiveSetupTime";
          }
        }

        leaf callActiveIndex {
          type leafref {
            path "/dial-control:DIAL-CONTROL-MIB/dial-control:callActiveTable/dial-control:callActiveEntry/dial-control:callActiveIndex";
          }
        }

        leaf cvVoIPCallActiveConnectionId {
          type cisco-voice:CvcGUid;
          description
           "The global connection identifier for
            the active VoIP leg of the call.";
          smiv2:max-access "read-only";
          smiv2:oid "1.3.6.1.4.1.9.9.63.1.3.2.1.1";
        }

        leaf cvVoIPCallActiveRemoteIPAddress {
          type inet:ipv4-address;
          status deprecated;
          description
           "Remote system IP address for the VoIP call.";
          smiv2:max-access "read-only";
          smiv2:oid "1.3.6.1.4.1.9.9.63.1.3.2.1.2";
        }

        leaf cvVoIPCallActiveRemoteUDPPort {
          type int32 {
            range "0..65535";
          }
          status deprecated;
          description
           "Remote system UDP listener port to which to transmit voice
            packets.";
          smiv2:max-access "read-only";
          smiv2:oid "1.3.6.1.4.1.9.9.63.1.3.2.1.3";
        }

        leaf cvVoIPCallActiveRoundTripDelay {
          type yang:gauge32;
          units "milliseconds";
          description
           "The voice packet round trip delay between local and
            the remote system on the IP backbone during the call.";
          smiv2:max-access "read-only";
          smiv2:oid "1.3.6.1.4.1.9.9.63.1.3.2.1.4";
        }

        leaf cvVoIPCallActiveSelectedQoS {
          type int-serv:QosService;
          description
           "The selected RSVP QoS for the voice call.";
          smiv2:max-access "read-only";
          smiv2:oid "1.3.6.1.4.1.9.9.63.1.3.2.1.5";
        }

        leaf cvVoIPCallActiveSessionProtocol {
          type CISCO-VOICE-DIAL-CONTROL-MIB:CvSessionProtocol;
          description
           "The object specifies the session protocol to be used
            for Internet call between local and remote router via
            IP backbone.";
          smiv2:max-access "read-only";
          smiv2:oid "1.3.6.1.4.1.9.9.63.1.3.2.1.6";
        }

        leaf cvVoIPCallActiveSessionTarget {
          type snmpv2-tc:DisplayString;
          description
           "The object specifies the session target of the peer that
            is used for the call. This object is set with the
            information in the call associated
            cvVoIPPeerCfgSessionTarget object when the voice over IP
            call is connected.";
          smiv2:max-access "read-only";
          smiv2:oid "1.3.6.1.4.1.9.9.63.1.3.2.1.7";
        }

        leaf cvVoIPCallActiveOnTimeRvPlayout {
          type dial-control:AbsoluteCounter32;
          units "milliseconds";
          description
           "Duration of voice playout from data received on time for
            this call. This plus the durations for the GapFills in the
            following entries gives the Total Voice Playout Duration
            for Active Voice.
            This does not include duration for which no data was sent by the
            Transmit end as voice signal, e.g., silence suppression
            and fax signal. The On Time Playout Rate can be computed
            by dividing this entry by the Total Voice Playout Duration.
            This counter object will lock at the maximum value which
            is approximately two days.";
          smiv2:max-access "read-only";
          smiv2:oid "1.3.6.1.4.1.9.9.63.1.3.2.1.8";
        }

        leaf cvVoIPCallActiveGapFillWithSilence {
          type dial-control:AbsoluteCounter32;
          units "milliseconds";
          description
           "Duration of voice signal replaced with signal played out
            during silence due to voice data not received on time
            (or lost) from voice gateway this call. This counter
            object will lock at the maximum value which is
            approximately two days.";
          smiv2:max-access "read-only";
          smiv2:oid "1.3.6.1.4.1.9.9.63.1.3.2.1.9";
        }

        leaf cvVoIPCallActiveGapFillWithPrediction {
          type dial-control:AbsoluteCounter32;
          units "milliseconds";
          description
           "Duration of voice signal played out with signal synthesized
            from parameters or samples of data preceding in time due
            to voice data not received on time (or lost) from voice
            gateway for this call. An example of such playout is
            frame-erasure or frame-concealment strategies in G.729 and
            G.723.1 compression algorithms. This counter object will
            lock at the maximum value which is approximately two days.";
          smiv2:max-access "read-only";
          smiv2:oid "1.3.6.1.4.1.9.9.63.1.3.2.1.10";
        }

        leaf cvVoIPCallActiveGapFillWithInterpolation {
          type dial-control:AbsoluteCounter32;
          units "milliseconds";
          description
           "Duration of voice signal played out with signal synthesized
            from parameters or samples of data preceding and following
            in time due to voice data not received on time (or lost)
            from voice gateway for this call. This counter object
            will lock at the maximum value which is approximately two
            days.";
          smiv2:max-access "read-only";
          smiv2:oid "1.3.6.1.4.1.9.9.63.1.3.2.1.11";
        }

        leaf cvVoIPCallActiveGapFillWithRedundancy {
          type dial-control:AbsoluteCounter32;
          units "milliseconds";
          description
           "Duration of voice signal played out with signal synthesized
            from redundancy parameters available due to voice data not
            received on time (or lost) from voice gateway for this call.
            This counter object will lock at the maximum value which
            is approximately two days.";
          smiv2:max-access "read-only";
          smiv2:oid "1.3.6.1.4.1.9.9.63.1.3.2.1.12";
        }

        leaf cvVoIPCallActiveHiWaterPlayoutDelay {
          type dial-control:AbsoluteCounter32;
          units "milliseconds";
          description
           "The high water mark Voice Playout FIFO Delay during
            the voice call. This counter object will lock at the
            maximum value which is approximately two days.";
          smiv2:max-access "read-only";
          smiv2:oid "1.3.6.1.4.1.9.9.63.1.3.2.1.13";
        }

        leaf cvVoIPCallActiveLoWaterPlayoutDelay {
          type yang:gauge32;
          units "milliseconds";
          description
           "The low water mark Voice Playout FIFO Delay during
            the voice call.";
          smiv2:max-access "read-only";
          smiv2:oid "1.3.6.1.4.1.9.9.63.1.3.2.1.14";
        }

        leaf cvVoIPCallActiveReceiveDelay {
          type yang:gauge32;
          description
           "The average Playout FIFO Delay plus the decoder delay
            during the voice call.";
          smiv2:max-access "read-only";
          smiv2:oid "1.3.6.1.4.1.9.9.63.1.3.2.1.15";
        }

        leaf cvVoIPCallActiveVADEnable {
          type boolean;
          status deprecated;
          description
           "The object indicates whether or not the VAD (Voice Activity
            Detection) was enabled for the voice call.";
          smiv2:max-access "read-only";
          smiv2:oid "1.3.6.1.4.1.9.9.63.1.3.2.1.16";
        }

        leaf cvVoIPCallActiveCoderTypeRate {
          type cisco-voice:CvcCoderTypeRate;
          status deprecated;
          description
           "The negotiated coder rate. It specifies the transmit rate of
            voice/fax compression to its associated call leg for the
            call. This rate is different from the configuration rate
            because of rate negotiation during the call.";
          smiv2:max-access "read-only";
          smiv2:oid "1.3.6.1.4.1.9.9.63.1.3.2.1.17";
        }

        leaf cvVoIPCallActiveLostPackets {
          type dial-control:AbsoluteCounter32;
          units "packets";
          description
           "The number of lost voice packets during the call.";
          smiv2:max-access "read-only";
          smiv2:oid "1.3.6.1.4.1.9.9.63.1.3.2.1.18";
        }

        leaf cvVoIPCallActiveEarlyPackets {
          type dial-control:AbsoluteCounter32;
          units "packets";
          description
           "The number of received voice packets that
            arrived too early to store in jitter buffer
            during the call.";
          smiv2:max-access "read-only";
          smiv2:oid "1.3.6.1.4.1.9.9.63.1.3.2.1.19";
        }

        leaf cvVoIPCallActiveLatePackets {
          type dial-control:AbsoluteCounter32;
          units "packets";
          description
           "The number of received voice packets that
            arrived too late to playout with CODEC (Coder/Decoder)
            during the call.";
          smiv2:max-access "read-only";
          smiv2:oid "1.3.6.1.4.1.9.9.63.1.3.2.1.20";
        }

        leaf cvVoIPCallActiveUsername {
          type snmp-framework:SnmpAdminString {
            length "0..16";
          }
          description
           "The textual identifier of the calling party (user) of the
            call. If the username is not available, then the value of
            this object will have a length of zero.";
          smiv2:max-access "read-only";
          smiv2:oid "1.3.6.1.4.1.9.9.63.1.3.2.1.21";
        }

        leaf cvVoIPCallActiveProtocolCallId {
          type binary {
            length "0..255";
          }
          description
           "The protocol-specific call identifier for the VoIP call.";
          smiv2:max-access "read-only";
          smiv2:oid "1.3.6.1.4.1.9.9.63.1.3.2.1.22";
        }

        leaf cvVoIPCallActiveRemSigIPAddrT {
          type inet-address:InetAddressType;
          description
           "This object specifies the type of address contained in
            the associated instance of cvVoIPCallActiveRemSigIPAddr.";
          smiv2:max-access "read-only";
          smiv2:oid "1.3.6.1.4.1.9.9.63.1.3.2.1.23";
        }

        leaf cvVoIPCallActiveRemSigIPAddr {
          type inet-address:InetAddress;
          description
           "Remote signalling IP address for the VoIP call.";
          smiv2:max-access "read-only";
          smiv2:oid "1.3.6.1.4.1.9.9.63.1.3.2.1.24";
        }

        leaf cvVoIPCallActiveRemSigPort {
          type int32 {
            range "0..65535";
          }
          description
           "Remote signalling listener port to which to transmit
            voice packets.";
          smiv2:max-access "read-only";
          smiv2:oid "1.3.6.1.4.1.9.9.63.1.3.2.1.25";
        }

        leaf cvVoIPCallActiveRemMediaIPAddrT {
          type inet-address:InetAddressType;
          description
           "This object specifies the type of address contained in
            the associated instance of
            cvVoIPCallActiveRemMediaIPAddr.";
          smiv2:max-access "read-only";
          smiv2:oid "1.3.6.1.4.1.9.9.63.1.3.2.1.26";
        }

        leaf cvVoIPCallActiveRemMediaIPAddr {
          type inet-address:InetAddress;
          description
           "Remote media end point IP address for the VoIP call.";
          smiv2:max-access "read-only";
          smiv2:oid "1.3.6.1.4.1.9.9.63.1.3.2.1.27";
        }

        leaf cvVoIPCallActiveRemMediaPort {
          type int32 {
            range "0..65535";
          }
          description
           "Remote media end point listener port to which to transmit
            voice packets.";
          smiv2:max-access "read-only";
          smiv2:oid "1.3.6.1.4.1.9.9.63.1.3.2.1.28";
        }

        leaf cvVoIPCallActiveSRTPEnable {
          type boolean;
          description
           "The object indicates whether or not the SRTP (Secured RTP)
            was enabled for the voice call.";
          smiv2:max-access "read-only";
          smiv2:oid "1.3.6.1.4.1.9.9.63.1.3.2.1.29";
        }

        leaf cvVoIPCallActiveOctetAligned {
          type boolean;
          description
           "If the object has a value true(1) octet align operation
            is used, and if the value is false(2), bandwidth efficient
            operation is used. This object is not instantiated when
            the object cvVoIPCallActiveCoderTypeRate is not equal to
            gsmAmrNb enum.";
          smiv2:max-access "read-only";
          smiv2:oid "1.3.6.1.4.1.9.9.63.1.3.2.1.30";
        }

        leaf cvVoIPCallActiveBitRates {
          type CISCO-VOICE-DIAL-CONTROL-MIB:CvAmrNbBitRateMode;
          description
           "This object indicates modes of Bit rates.
            This object is not instantiated when the object
            cvVoIPCallActiveCoderTypeRate is not equal to
            gsmAmrNb enum.";
          smiv2:max-access "read-only";
          smiv2:oid "1.3.6.1.4.1.9.9.63.1.3.2.1.31";
        }

        leaf cvVoIPCallActiveModeChgPeriod {
          type int32 {
            range "1..100";
          }
          units "frame-blocks";
          description
           "The object indicates the interval (N frame-blocks) at which
            codec mode changes are allowed. This object is not
            instantiated when the object cvVoIPCallActiveCoderTypeRate
            is not equal to gsmAmrNb enum.";
          smiv2:max-access "read-only";
          smiv2:oid "1.3.6.1.4.1.9.9.63.1.3.2.1.32";
        }

        leaf cvVoIPCallActiveModeChgNeighbor {
          type boolean;
          description
           "If the object has a value of true(1), mode changes will be
            made to only neighboring modes set to
            cvVoIPCallActiveBitRates object. If the value is false(2),
            mode changes will be allowed to any modes set to
            cvVoIPCallActiveBitRates object. This object is not
            instantiated when the object cvVoIPCallActiveCoderTypeRate
            is not equal to gsmAmrNb enum.";
          smiv2:max-access "read-only";
          smiv2:oid "1.3.6.1.4.1.9.9.63.1.3.2.1.33";
        }

        leaf cvVoIPCallActiveMaxPtime {
          type int32 {
            range "20..100";
          }
          units "milliseconds";
          description
           "The object indicates the maximum amount of media that
            can be encapsulated in a payload. Supported value is
            20 msec. This object is not instantiated when the
            object cvVoIPCallActiveCoderTypeRate is not equal to
            gsmAmrNb enum.";
          smiv2:max-access "read-only";
          smiv2:oid "1.3.6.1.4.1.9.9.63.1.3.2.1.34";
        }

        leaf cvVoIPCallActiveCRC {
          type boolean;
          description
           "If the object has a value of true(1), frame CRC will be
            included in the payload and if the value is false(2),
            frame CRC will not be included in the payload.
            This object is applicable only when RTP frame type
            is octet aligned. This object is not instantiated when
            the object cvVoIPCallActiveCoderTypeRate is not equal to
            gsmAmrNb enum.";
          smiv2:max-access "read-only";
          smiv2:oid "1.3.6.1.4.1.9.9.63.1.3.2.1.35";
        }

        leaf cvVoIPCallActiveRobustSorting {
          type boolean;
          description
           "If the object has a value of true(1), payload employs
            robust sorting and if the value is false(2), payload
            does not employ robust sorting. This object is applicable
            only when RTP frame type is octet aligned. This object
            is not instantiated when the object
            cvVoIPCallActiveCoderTypeRate is not equal to gsmAmrNb
            enum.";
          smiv2:max-access "read-only";
          smiv2:oid "1.3.6.1.4.1.9.9.63.1.3.2.1.36";
        }

        leaf cvVoIPCallActiveEncap {
          type CISCO-VOICE-DIAL-CONTROL-MIB:CvAmrNbRtpEncap;
          description
           "The object indicates the RTP encapsulation type.
            Supported RTP encapsulation type is RFC3267.
            This object is not instantiated when the object
            cvVoIPCallActiveCoderTypeRate is not equal to
            gsmAmrNb enum.";
          smiv2:max-access "read-only";
          smiv2:oid "1.3.6.1.4.1.9.9.63.1.3.2.1.37";
        }

        leaf cvVoIPCallActiveInterleaving {
          type int32 {
            range "1..50";
          }
          units "frame-blocks";
          description
           "The object indicates the maximum number of frame-blocks
            allowed in an interleaving group. It indicates that
            frame-block level interleaving will be used for that
            session. If this object is not set, interleaving
            is not used. This object is applicable only when
            RTP frame type is octet aligned. This object is not
            instantiated when the object cvVoIPCallActiveCoderTypeRate
            is not equal to gsmAmrNb enum.";
          smiv2:max-access "read-only";
          smiv2:oid "1.3.6.1.4.1.9.9.63.1.3.2.1.38";
        }

        leaf cvVoIPCallActivePtime {
          type int32 {
            range "20..100";
          }
          units "milliseconds";
          description
           "The object indicates the length of the time in milliseconds
            represented by the media of the packet. Supported value is
            20 milliseconds. This object is not instantiated when the
            object cvVoIPCallActiveCoderTypeRate is not equal to
            gsmAmrNb enum.";
          smiv2:max-access "read-only";
          smiv2:oid "1.3.6.1.4.1.9.9.63.1.3.2.1.39";
        }

        leaf cvVoIPCallActiveChannels {
          type int32 {
            range "1..6";
          }
          units "channels";
          description
           "The object indicates the number of audio channels.
            Supported value is 1. This object is not instantiated
            when the object cvVoIPCallActiveCoderTypeRate is not equal
            to gsmAmrNb enum.";
          smiv2:max-access "read-only";
          smiv2:oid "1.3.6.1.4.1.9.9.63.1.3.2.1.40";
        }

        leaf cvVoIPCallActiveCoderMode {
          type CISCO-VOICE-DIAL-CONTROL-MIB:CvIlbcFrameMode;
          units "milliseconds";
          description
           "The object indicates the iLBC codec mode.
            The value of this object is valid only if 
            cvVoIPCallActiveCoderTypeRate is equal to 
            'iLBC'.";
          reference
           "RFC 3952: Section 5, for codec negotiation for iLBC mode.";
          smiv2:max-access "read-only";
          smiv2:oid "1.3.6.1.4.1.9.9.63.1.3.2.1.41";
        }

        leaf cvVoIPCallActiveCallId {
          type uint32 {
            range "1..4294967295";
          }
          description
           "This object represents the call identifier
            for the active VoIP leg of the call.";
          smiv2:max-access "read-only";
          smiv2:oid "1.3.6.1.4.1.9.9.63.1.3.2.1.42";
        }

        leaf cvVoIPCallActiveCallReferenceId {
          type cisco-voice:CvcCallReferenceIdOrZero;
          description
           "The call reference ID associates the video call entry and voice
            call entry of the same endpoint.  An audio-only call may or may
            not have a valid call reference ID (i.e. value greater than
            zero), but in both cases, there will not be a video call entry
            associated with it.  
            
            For a video call, the video-specific information  is stored in a
            call entry in cVideoSessionActive of CISCO-VIDEO-SESSION-MIB, in
            which the call reference ID is also identified.";
          smiv2:max-access "read-only";
          smiv2:oid "1.3.6.1.4.1.9.9.63.1.3.2.1.43";
        }

        leaf ccVoIPCallActivePolicyName {
          type snmpv2-tc:DisplayString;
          description
           "This object holds the policy name. It could be media
            policy, DSCP policy etc.";
          smiv2:max-access "read-only";
          smiv2:oid "1.3.6.1.4.1.9.9.63.1.3.2.1.44";
        }

        leaf cvVoIPCallActiveReversedDirectionPeerAddress {
          type snmpv2-tc:DisplayString;
          description
           "This object store the reversed direction peer address  If the
            address is not available, then it will have a length of zero.
            
            If the call is ingress then it contains called number and if the
            call is egress then it contains calling number.";
          smiv2:max-access "read-only";
          smiv2:oid "1.3.6.1.4.1.9.9.63.1.3.2.1.45";
        }

        leaf cvVoIPCallActiveSessionId {
          type uint32;
          description
           "This object indicates the active session ID assigned by the
            call manager to identify call legs that belong to the same call
            session.";
          smiv2:max-access "read-only";
          smiv2:oid "1.3.6.1.4.1.9.9.63.1.3.2.1.46";
        }
      }
    }

    container cvCallVolConnTable {
      description
       "This table represents the number of active
        call connections for each call connection type
        in the voice gateway.";
      smiv2:oid "1.3.6.1.4.1.9.9.63.1.3.8.1";

      list cvCallVolConnEntry {
        key "cvCallVolConnIndex";
        description
         "An entry in the cvCallVolConnTable indicates
          number of active calls for a call connection type
          in the voice gateway.";
        smiv2:oid "1.3.6.1.4.1.9.9.63.1.3.8.1.1";

        leaf cvCallVolConnIndex {
          type CISCO-VOICE-DIAL-CONTROL-MIB:CvCallConnectionType;
          description
           "This object represents index to the
            cvCallVolConnTable.";
          smiv2:max-access "not-accessible";
          smiv2:oid "1.3.6.1.4.1.9.9.63.1.3.8.1.1.1";
        }

        leaf cvCallVolConnActiveConnection {
          type yang:gauge32 {
            range "0..65535";
          }
          description
           "This object represents the total number of
            active calls for a connection type 
            in the voice gateway.";
          smiv2:max-access "read-only";
          smiv2:oid "1.3.6.1.4.1.9.9.63.1.3.8.1.1.2";
        }
      }
    }

    container cvCallVolIfTable {
      description
       "This table represents the information about
        the usage of an IP interface in a voice
        gateway for voice media calls. This table
        has a sparse-dependent relationship with  
        ifTable. There exists an entry in this table, 
        for each of the  entries in ifTable where ifType 
        is one of 'ethernetCsmacd' and 'softwareLoopback'.";
      smiv2:oid "1.3.6.1.4.1.9.9.63.1.3.8.5";

      list cvCallVolIfEntry {
        key "ifIndex";
        description
         "Each entry represents a row in cvCallVolIfTable
          and corresponds to the information about an IP 
          interface in the voice gateway.";
        smiv2:oid "1.3.6.1.4.1.9.9.63.1.3.8.5.1";

        leaf ifIndex {
          type leafref {
            path "/if-mib:IF-MIB/if-mib:ifTable/if-mib:ifEntry/if-mib:ifIndex";
          }
        }

        leaf cvCallVolMediaIncomingCalls {
          type yang:gauge32 {
            range "0..65535";
          }
          description
           "This object represents the total number of
            inbound active media calls through this IP 
            interface.";
          smiv2:max-access "read-only";
          smiv2:oid "1.3.6.1.4.1.9.9.63.1.3.8.5.1.1";
        }

        leaf cvCallVolMediaOutgoingCalls {
          type yang:gauge32 {
            range "0..65535";
          }
          description
           "This object represents the total number of
            outbound active media calls through the IP 
            interface.";
          smiv2:max-access "read-only";
          smiv2:oid "1.3.6.1.4.1.9.9.63.1.3.8.5.1.2";
        }
      }
    }

    container cvCallHistoryTable {
      description
       "This table is the voice extension to the call history table
        of IETF Dial Control MIB. It contains voice encapsulation
        call leg information such as voice packet statistics,
        coder usage and end to end bandwidth of the call leg.";
      smiv2:oid "1.3.6.1.4.1.9.9.63.1.4.1";

      list cvCallHistoryEntry {
        key "cCallHistoryIndex";
        description
         "The information regarding a single voice encapsulation
          call leg.
          The call leg entry is identified by using the same index
          objects that are used by Call Active table of IETF Dial
          Control MIB to identify the call.
          An entry of this table is created when its associated call
          history entry in the IETF Dial Control MIB is created and
          the call history entry contains the call establishment to
          a voice encapsulation peer.
          The entry is deleted when its associated call active entry
          in the IETF Dial Control MIB is deleted.";
        smiv2:oid "1.3.6.1.4.1.9.9.63.1.4.1.1";

        leaf cCallHistoryIndex {
          type leafref {
            path "/cisco-dial:CISCO-DIAL-CONTROL-MIB/cisco-dial:cCallHistoryTable/cisco-dial:cCallHistoryEntry/cisco-dial:cCallHistoryIndex";
          }
        }

        leaf cvCallHistoryConnectionId {
          type cisco-voice:CvcGUid;
          description
           "The global connection identifier for the
            telephony leg, which was assigned to the call.";
          smiv2:max-access "read-only";
          smiv2:oid "1.3.6.1.4.1.9.9.63.1.4.1.1.1";
        }

        leaf cvCallHistoryTxDuration {
          type dial-control:AbsoluteCounter32;
          units "milliseconds";
          description
           "Duration of Transmit path open from this peer to the
            voice gateway for the call leg. This counter object will
            lock at the maximum value which is approximately two
            days.";
          smiv2:max-access "read-only";
          smiv2:oid "1.3.6.1.4.1.9.9.63.1.4.1.1.2";
        }

        leaf cvCallHistoryVoiceTxDuration {
          type dial-control:AbsoluteCounter32;
          units "milliseconds";
          description
           "Duration for this call leg. The Voice Utilization Rate
            can be obtained by dividing this by
            cvCallHistoryTXDuration object. This counter object will
            lock at the maximum value which is approximately two
            days.";
          smiv2:max-access "read-only";
          smiv2:oid "1.3.6.1.4.1.9.9.63.1.4.1.1.3";
        }

        leaf cvCallHistoryFaxTxDuration {
          type dial-control:AbsoluteCounter32;
          units "milliseconds";
          description
           "Duration of fax transmitted from this peer to voice
            gateway for this call leg. The FAX Utilization Rate can be
            obtained by dividing this by cvCallHistoryTXDuration
            object. This counter object will lock at the maximum
            value which is approximately two days.";
          smiv2:max-access "read-only";
          smiv2:oid "1.3.6.1.4.1.9.9.63.1.4.1.1.4";
        }

        leaf cvCallHistoryCoderTypeRate {
          type cisco-voice:CvcCoderTypeRate;
          description
           "The negotiated coder rate. It specifies the transmit rate
            of voice/fax compression to its associated call leg for
            the call.";
          smiv2:max-access "read-only";
          smiv2:oid "1.3.6.1.4.1.9.9.63.1.4.1.1.5";
        }

        leaf cvCallHistoryNoiseLevel {
          type int32 {
            range "-128..8";
          }
          units "dBm";
          description
           "The object contains the average noise level for the call
            leg.";
          smiv2:max-access "read-only";
          smiv2:oid "1.3.6.1.4.1.9.9.63.1.4.1.1.6";
        }

        leaf cvCallHistoryACOMLevel {
          type int32 {
            range "-1..127";
          }
          units "dB";
          description
           "The object contains the average ACOM level for the call
            leg. The value -1 indicates the level can not be
            determined or level detection is disabled.";
          smiv2:max-access "read-only";
          smiv2:oid "1.3.6.1.4.1.9.9.63.1.4.1.1.7";
        }

        leaf cvCallHistorySessionTarget {
          type snmpv2-tc:DisplayString {
            length "0..64";
          }
          description
           "The object specifies the session target of the peer that
            is used for the call leg via telephony interface.";
          smiv2:max-access "read-only";
          smiv2:oid "1.3.6.1.4.1.9.9.63.1.4.1.1.8";
        }

        leaf cvCallHistoryImgPageCount {
          type dial-control:AbsoluteCounter32;
          units "pages";
          description
           "The number of FAX related image pages are received or
            transmitted via the peer for the call leg.";
          smiv2:max-access "read-only";
          smiv2:oid "1.3.6.1.4.1.9.9.63.1.4.1.1.9";
        }

        leaf cvCallHistoryCallingName {
          type snmp-framework:SnmpAdminString;
          description
           "The calling party name of the call. If the name is
            not available, then it will have a length of zero.";
          smiv2:max-access "read-only";
          smiv2:oid "1.3.6.1.4.1.9.9.63.1.4.1.1.10";
        }

        leaf cvCallHistoryCallerIDBlock {
          type boolean;
          description
           "The object indicates whether or not the caller ID feature
            is blocked for this call.";
          smiv2:max-access "read-only";
          smiv2:oid "1.3.6.1.4.1.9.9.63.1.4.1.1.11";
        }

        leaf cvCallHistoryAccountCode {
          type snmp-framework:SnmpAdminString {
            length "0..50";
          }
          description
           "The object indicates the account code input to the call.
            It could be used by down stream billing server.
            The value of empty string indicates no account code input.";
          smiv2:defval "";
          smiv2:max-access "read-only";
          smiv2:oid "1.3.6.1.4.1.9.9.63.1.4.1.1.12";
        }

        leaf cvCallHistoryCallId {
          type uint32 {
            range "1..4294967295";
          }
          description
           "This object represents the call identifier for the
            telephony leg, which was assigned to the call.";
          smiv2:max-access "read-only";
          smiv2:oid "1.3.6.1.4.1.9.9.63.1.4.1.1.13";
        }
      }
    }

    container cvVoIPCallHistoryTable {
      description
       "This table is the VoIP extension to the call history table
        of IETF Dial Control MIB. It contains VoIP call leg
        information about specific VoIP call destination and the
        selected QoS for the call leg.";
      smiv2:oid "1.3.6.1.4.1.9.9.63.1.4.2";

      list cvVoIPCallHistoryEntry {
        key "cCallHistoryIndex";
        description
         "The information regarding a single VoIP call leg.
          The call leg entry is identified by using the same index
          objects that are used by Call Active table of IETF Dial
          Control MIB to identify the call.
          An entry of this table is created when its associated call
          history entry in the IETF Dial Control MIB is created and
          the call history entry contains information for the call
          establishment to the peer on the IP backbone via a voice
          over IP peer.
          The entry is deleted when its associated call history
          entry in the IETF Dial Control MIB is deleted.";
        smiv2:oid "1.3.6.1.4.1.9.9.63.1.4.2.1";

        leaf cCallHistoryIndex {
          type leafref {
            path "/cisco-dial:CISCO-DIAL-CONTROL-MIB/cisco-dial:cCallHistoryTable/cisco-dial:cCallHistoryEntry/cisco-dial:cCallHistoryIndex";
          }
        }

        leaf cvVoIPCallHistoryConnectionId {
          type cisco-voice:CvcGUid;
          description
           "The global connection identifier for the
            VoIP leg, which was assigned to the call.";
          smiv2:max-access "read-only";
          smiv2:oid "1.3.6.1.4.1.9.9.63.1.4.2.1.1";
        }

        leaf cvVoIPCallHistoryRemoteIPAddress {
          type inet:ipv4-address;
          status deprecated;
          description
           "Remote system IP address for the call.";
          smiv2:max-access "read-only";
          smiv2:oid "1.3.6.1.4.1.9.9.63.1.4.2.1.2";
        }

        leaf cvVoIPCallHistoryRemoteUDPPort {
          type int32 {
            range "0..65535";
          }
          status deprecated;
          description
           "Remote system UDP listener port to which to transmit voice
            packets for the call.";
          smiv2:max-access "read-only";
          smiv2:oid "1.3.6.1.4.1.9.9.63.1.4.2.1.3";
        }

        leaf cvVoIPCallHistoryRoundTripDelay {
          type yang:gauge32;
          units "milliseconds";
          description
           "The voice packet round trip delay between local and
            the remote system on the IP backbone during the call.";
          smiv2:max-access "read-only";
          smiv2:oid "1.3.6.1.4.1.9.9.63.1.4.2.1.4";
        }

        leaf cvVoIPCallHistorySelectedQoS {
          type int-serv:QosService;
          description
           "The selected RSVP QoS for the call.";
          smiv2:max-access "read-only";
          smiv2:oid "1.3.6.1.4.1.9.9.63.1.4.2.1.5";
        }

        leaf cvVoIPCallHistorySessionProtocol {
          type CISCO-VOICE-DIAL-CONTROL-MIB:CvSessionProtocol;
          description
           "The object specifies the session protocol to be used
            for Internet call between local and remote router via
            IP backbone.";
          smiv2:max-access "read-only";
          smiv2:oid "1.3.6.1.4.1.9.9.63.1.4.2.1.6";
        }

        leaf cvVoIPCallHistorySessionTarget {
          type snmpv2-tc:DisplayString;
          description
           "The object specifies the session target of the peer that
            is used for the Voice over IP call.";
          smiv2:max-access "read-only";
          smiv2:oid "1.3.6.1.4.1.9.9.63.1.4.2.1.7";
        }

        leaf cvVoIPCallHistoryOnTimeRvPlayout {
          type dial-control:AbsoluteCounter32;
          units "milliseconds";
          description
           "Duration of voice playout from data received on time for
            this call. This plus the durations for the GapFills in the
            following entries gives the Total Voice Playout Duration
            for Active Voice.
            This does not include duration for which no data was sent by the
            Transmit end as voice signal, e.g., silence suppression
            and fax signal. The On Time Playout Rate can be computed
            by dividing this entry by the Total Voice Playout Duration.
            This counter object will lock at the maximum value which
            is approximately two days.";
          smiv2:max-access "read-only";
          smiv2:oid "1.3.6.1.4.1.9.9.63.1.4.2.1.8";
        }

        leaf cvVoIPCallHistoryGapFillWithSilence {
          type dial-control:AbsoluteCounter32;
          units "milliseconds";
          description
           "Duration of voice signal replaced with signal played out
            during silence due to voice data not received on time
            (or lost) from voice gateway this call. This counter
            object will lock at the maximum value which is
            approximately two days.";
          smiv2:max-access "read-only";
          smiv2:oid "1.3.6.1.4.1.9.9.63.1.4.2.1.9";
        }

        leaf cvVoIPCallHistoryGapFillWithPrediction {
          type dial-control:AbsoluteCounter32;
          units "milliseconds";
          description
           "Duration of voice signal played out with signal synthesized
            from parameters or samples of data preceding in time due to
            voice data not received on time (or lost) from voice gateway
            for this call. An example of such playout is frame-erasure
            or  frame-concealment strategies in G.729 and G.723.1
            compression algorithms. This counter object will lock at
            the maximum value which is approximately two days.";
          smiv2:max-access "read-only";
          smiv2:oid "1.3.6.1.4.1.9.9.63.1.4.2.1.10";
        }

        leaf cvVoIPCallHistoryGapFillWithInterpolation {
          type dial-control:AbsoluteCounter32;
          units "milliseconds";
          description
           "Duration of voice signal played out with signal synthesized
            from parameters or samples of data preceding and following
            in time due to voice data not received on time (or lost)
            from voice gateway for this call. This counter object
            will lock at the maximum value which is approximately two
            days.";
          smiv2:max-access "read-only";
          smiv2:oid "1.3.6.1.4.1.9.9.63.1.4.2.1.11";
        }

        leaf cvVoIPCallHistoryGapFillWithRedundancy {
          type dial-control:AbsoluteCounter32;
          units "milliseconds";
          description
           "Duration of voice signal played out with signal synthesized
            from redundancy parameters available due to voice data not
            received on time (or lost) from voice gateway for this call.
            This counter object will lock at the maximum value which
            is approximately two days.";
          smiv2:max-access "read-only";
          smiv2:oid "1.3.6.1.4.1.9.9.63.1.4.2.1.12";
        }

        leaf cvVoIPCallHistoryHiWaterPlayoutDelay {
          type dial-control:AbsoluteCounter32;
          units "milliseconds";
          description
           "The high water mark Voice Playout FIFO Delay during
            the voice call. This counter object will lock at the
            maximum value which is approximately two days.";
          smiv2:max-access "read-only";
          smiv2:oid "1.3.6.1.4.1.9.9.63.1.4.2.1.13";
        }

        leaf cvVoIPCallHistoryLoWaterPlayoutDelay {
          type yang:gauge32;
          units "milliseconds";
          description
           "The low water mark Voice Playout FIFO Delay during
            the voice call.";
          smiv2:max-access "read-only";
          smiv2:oid "1.3.6.1.4.1.9.9.63.1.4.2.1.14";
        }

        leaf cvVoIPCallHistoryReceiveDelay {
          type yang:gauge32;
          description
           "The average Playout FIFO Delay plus the decoder delay
            during the voice call.";
          smiv2:max-access "read-only";
          smiv2:oid "1.3.6.1.4.1.9.9.63.1.4.2.1.15";
        }

        leaf cvVoIPCallHistoryVADEnable {
          type boolean;
          status deprecated;
          description
           "The object indicates whether or not the VAD (Voice Activity
            Detection) was enabled for the voice call.";
          smiv2:max-access "read-only";
          smiv2:oid "1.3.6.1.4.1.9.9.63.1.4.2.1.16";
        }

        leaf cvVoIPCallHistoryCoderTypeRate {
          type cisco-voice:CvcCoderTypeRate;
          status deprecated;
          description
           "The negotiated coder rate. It specifies the transmit rate of
            voice/fax compression to its associated call leg for the
            call. This rate is different from the configuration rate
            because of rate negotiation during the call.";
          smiv2:max-access "read-only";
          smiv2:oid "1.3.6.1.4.1.9.9.63.1.4.2.1.17";
        }

        leaf cvVoIPCallHistoryIcpif {
          type int32 {
            range "-1..55";
          }
          units "equipment impairment factor (eif)";
          description
           "The Calculated Planning Impairment Factor (Icpif) of the
            call  that is associated to this call leg.
            The value in this object is computed by the following
            equation.
            Icpif of the call =
            Itotal (total impairment value) of the call - A
            (Expectation Factor) in the cvVoIPPeerCfgExpectFactor of
            the call leg associated peer.
            A value of -1 implies that Icpif was not calculated and is
            meaningless for this call.";
          reference
           "[1] ITU G.113: Section 7.2 Impairment factors and the total
            impairment value.
                [2] ITU G.113: Sections 9 Considerations associated with
            the Calculated Planning Impairment Factor (Icpif).";
          smiv2:max-access "read-only";
          smiv2:oid "1.3.6.1.4.1.9.9.63.1.4.2.1.18";
        }

        leaf cvVoIPCallHistoryLostPackets {
          type dial-control:AbsoluteCounter32;
          units "packets";
          description
           "The number of lost voice packets during the call.";
          smiv2:max-access "read-only";
          smiv2:oid "1.3.6.1.4.1.9.9.63.1.4.2.1.19";
        }

        leaf cvVoIPCallHistoryEarlyPackets {
          type dial-control:AbsoluteCounter32;
          units "packets";
          description
           "The number of received voice packets that are
            arrived too early to store in jitter buffer
            during the call.";
          smiv2:max-access "read-only";
          smiv2:oid "1.3.6.1.4.1.9.9.63.1.4.2.1.20";
        }

        leaf cvVoIPCallHistoryLatePackets {
          type dial-control:AbsoluteCounter32;
          units "packets";
          description
           "The number of received voice packets that are
            arrived too late to playout with CODEC (Coder/Decoder)
            during the call.";
          smiv2:max-access "read-only";
          smiv2:oid "1.3.6.1.4.1.9.9.63.1.4.2.1.21";
        }

        leaf cvVoIPCallHistoryUsername {
          type snmp-framework:SnmpAdminString {
            length "0..16";
          }
          description
           "The textual identifier of the calling party (user) of the
            call. If the username is not available, then the value of
            this object will have a length of zero.";
          smiv2:max-access "read-only";
          smiv2:oid "1.3.6.1.4.1.9.9.63.1.4.2.1.22";
        }

        leaf cvVoIPCallHistoryProtocolCallId {
          type binary {
            length "0..255";
          }
          description
           "The protocol-specific call identifier for the VoIP call.";
          smiv2:max-access "read-only";
          smiv2:oid "1.3.6.1.4.1.9.9.63.1.4.2.1.23";
        }

        leaf cvVoIPCallHistoryRemSigIPAddrT {
          type inet-address:InetAddressType;
          description
           "This object specifies the type of address contained in
            the associated instance of cvVoIPCallHistoryRemSigIPAddr.";
          smiv2:max-access "read-only";
          smiv2:oid "1.3.6.1.4.1.9.9.63.1.4.2.1.24";
        }

        leaf cvVoIPCallHistoryRemSigIPAddr {
          type inet-address:InetAddress;
          description
           "Remote signalling IP address for the VoIP call.";
          smiv2:max-access "read-only";
          smiv2:oid "1.3.6.1.4.1.9.9.63.1.4.2.1.25";
        }

        leaf cvVoIPCallHistoryRemSigPort {
          type int32 {
            range "0..65535";
          }
          description
           "Remote signalling listener port to which to transmit
            voice packets.";
          smiv2:max-access "read-only";
          smiv2:oid "1.3.6.1.4.1.9.9.63.1.4.2.1.26";
        }

        leaf cvVoIPCallHistoryRemMediaIPAddrT {
          type inet-address:InetAddressType;
          description
           "This object specifies the type of address contained in
            the associated instance of
            cvVoIPCallHistoryRemMediaIPAddr.";
          smiv2:max-access "read-only";
          smiv2:oid "1.3.6.1.4.1.9.9.63.1.4.2.1.27";
        }

        leaf cvVoIPCallHistoryRemMediaIPAddr {
          type inet-address:InetAddress;
          description
           "Remote media end point IP address for the VoIP call.";
          smiv2:max-access "read-only";
          smiv2:oid "1.3.6.1.4.1.9.9.63.1.4.2.1.28";
        }

        leaf cvVoIPCallHistoryRemMediaPort {
          type int32 {
            range "0..65535";
          }
          description
           "Remote media end point listener port to which to transmit
            voice packets.";
          smiv2:max-access "read-only";
          smiv2:oid "1.3.6.1.4.1.9.9.63.1.4.2.1.29";
        }

        leaf cvVoIPCallHistorySRTPEnable {
          type boolean;
          description
           "The object indicates whether or not the SRTP (Secured RTP)
            was enabled for the voice call.";
          smiv2:max-access "read-only";
          smiv2:oid "1.3.6.1.4.1.9.9.63.1.4.2.1.30";
        }

        leaf cvVoIPCallHistoryFallbackIcpif {
          type int32;
          description
           "The Calculated Planning Impairment Factor (Icpif) of the
            call  that is associated to this call leg.
            The value in this object is computed by the following
            equation.
            Icpif of the fallback probe =
            Itotal (total impairment value)  - configured fallback
            (Expectation Factor).
            A value of 0 implies that Icpif was not calculated and is
            meaningless for this attempt.";
          smiv2:max-access "read-only";
          smiv2:oid "1.3.6.1.4.1.9.9.63.1.4.2.1.31";
        }

        leaf cvVoIPCallHistoryFallbackLoss {
          type dial-control:AbsoluteCounter32;
          description
           "FallbackLoss is the percentage of loss packets based on
            the total packets sent.";
          smiv2:max-access "read-only";
          smiv2:oid "1.3.6.1.4.1.9.9.63.1.4.2.1.32";
        }

        leaf cvVoIPCallHistoryFallbackDelay {
          type yang:gauge32;
          description
           "The FallbackDelay is calculated as follows -
            Take the sum of the round trips for all the probes, 
            divide by the number of probes, 
            and divide by two to get the one-way delay.  
            Then add in jitter_in or jiter_out,
            which ever is higher.";
          smiv2:max-access "read-only";
          smiv2:oid "1.3.6.1.4.1.9.9.63.1.4.2.1.33";
        }

        leaf cvVoIPCallHistoryOctetAligned {
          type boolean;
          description
           "If the object has a value true(1) octet align operation
            is used, and if the value is false(2), bandwidth efficient
            operation is used. This object is not instantiated when
            the object cvVoIPCallHistoryCoderTypeRate is not equal to
            gsmAmrNb enum.";
          smiv2:max-access "read-only";
          smiv2:oid "1.3.6.1.4.1.9.9.63.1.4.2.1.34";
        }

        leaf cvVoIPCallHistoryBitRates {
          type CISCO-VOICE-DIAL-CONTROL-MIB:CvAmrNbBitRateMode;
          description
           "This object indicates modes of Bit rates.
            This object is not instantiated when the object
            cvVoIPCallHistoryCoderTypeRate is not equal to
            gsmAmrNb enum.";
          smiv2:max-access "read-only";
          smiv2:oid "1.3.6.1.4.1.9.9.63.1.4.2.1.35";
        }

        leaf cvVoIPCallHistoryModeChgPeriod {
          type int32 {
            range "1..100";
          }
          units "frame-blocks";
          description
           "The object indicates the interval (N frame-blocks) at which
            codec mode changes are allowed. This object is not
            instantiated when the object cvVoIPCallHistoryCoderTypeRate
            is not equal to gsmAmrNb enum.";
          smiv2:max-access "read-only";
          smiv2:oid "1.3.6.1.4.1.9.9.63.1.4.2.1.36";
        }

        leaf cvVoIPCallHistoryModeChgNeighbor {
          type boolean;
          description
           "If the object has a value of true(1), mode changes will be
            made to only neighboring modes set to
            cvVoIPCallHistoryBitRates object. If the value is false(2),
            mode changes will be allowed to any modes set to
            cvVoIPCallHistoryBitRates object. This object is not
            instantiated when the object cvVoIPCallHistoryCoderTypeRate
            is not equal to gsmAmrNb enum.";
          smiv2:max-access "read-only";
          smiv2:oid "1.3.6.1.4.1.9.9.63.1.4.2.1.37";
        }

        leaf cvVoIPCallHistoryMaxPtime {
          type int32 {
            range "20..100";
          }
          units "milliseconds";
          description
           "The object indicates the maximum amount of media that
            can be encapsulated in a payload. Supported value is
            20 msec. This object is not instantiated when the
            object cvVoIPCallHistoryCoderTypeRate is not equal to
            gsmAmrNb enum.";
          smiv2:max-access "read-only";
          smiv2:oid "1.3.6.1.4.1.9.9.63.1.4.2.1.38";
        }

        leaf cvVoIPCallHistoryCRC {
          type boolean;
          description
           "If the object has a value of true(1), frame CRC will be
            included in the payload and if the value is false(2),
            frame CRC will not be included in the payload.
            This object is applicable only when RTP frame type
            is octet aligned. This object is not instantiated when
            the object cvVoIPCallHistoryCoderTypeRate is not equal to
            gsmAmrNb enum.";
          smiv2:max-access "read-only";
          smiv2:oid "1.3.6.1.4.1.9.9.63.1.4.2.1.39";
        }

        leaf cvVoIPCallHistoryRobustSorting {
          type boolean;
          description
           "If the object has a value of true(1), payload employs
            robust sorting and if the value is false(2), payload
            does not employ robust sorting. This object is applicable
            only when RTP frame type is octet aligned. This object
            is not instantiated when the object
            cvVoIPCallHistoryCoderTypeRate is not equal to gsmAmrNb
            enum.";
          smiv2:max-access "read-only";
          smiv2:oid "1.3.6.1.4.1.9.9.63.1.4.2.1.40";
        }

        leaf cvVoIPCallHistoryEncap {
          type CISCO-VOICE-DIAL-CONTROL-MIB:CvAmrNbRtpEncap;
          description
           "The object indicates the RTP encapsulation type.
            Supported RTP encapsulation type is RFC3267.
            This object is not instantiated when the object
            cvVoIPCallHistoryCoderTypeRate is not equal to
            gsmAmrNb enum.";
          smiv2:max-access "read-only";
          smiv2:oid "1.3.6.1.4.1.9.9.63.1.4.2.1.41";
        }

        leaf cvVoIPCallHistoryInterleaving {
          type int32 {
            range "1..50";
          }
          units "frame-blocks";
          description
           "The object indicates the maximum number of frame-blocks
            allowed in an interleaving group. It indicates that
            frame-block level interleaving will be used for that
            session. If this object is not set, interleaving
            is not used. This object is applicable only when
            RTP frame type is octet aligned. This object is not
            instantiated when the object cvVoIPCallHistoryCoderTypeRate
            is not equal to gsmAmrNb enum.";
          smiv2:max-access "read-only";
          smiv2:oid "1.3.6.1.4.1.9.9.63.1.4.2.1.42";
        }

        leaf cvVoIPCallHistoryPtime {
          type int32 {
            range "20..100";
          }
          units "milliseconds";
          description
           "The object indicates the length of the time in milliseconds
            represented by the media of the packet. Supported value is
            20 milliseconds. This object is not instantiated when the
            object cvVoIPCallHistoryCoderTypeRate is not equal to
            gsmAmrNb enum.";
          smiv2:max-access "read-only";
          smiv2:oid "1.3.6.1.4.1.9.9.63.1.4.2.1.43";
        }

        leaf cvVoIPCallHistoryChannels {
          type int32 {
            range "1..6";
          }
          units "channels";
          description
           "The object indicates the number of audio channels.
            Supported value is 1. This object is not instantiated
            when the object cvVoIPCallHistoryCoderTypeRate is not equal
            to gsmAmrNb enum.";
          smiv2:max-access "read-only";
          smiv2:oid "1.3.6.1.4.1.9.9.63.1.4.2.1.44";
        }

        leaf cvVoIPCallHistoryCoderMode {
          type CISCO-VOICE-DIAL-CONTROL-MIB:CvIlbcFrameMode;
          units "milliseconds";
          description
           "The object indicates the iLBC mode.
            The value of this object is valid only if 
            cvVoIPCallHistoryCoderTypeRate is equal to 
            'iLBC'.";
          reference
           "RFC 3952: Section 5, for codec negotiation for iLBC mode.";
          smiv2:max-access "read-only";
          smiv2:oid "1.3.6.1.4.1.9.9.63.1.4.2.1.45";
        }

        leaf cvVoIPCallHistoryCallId {
          type uint32 {
            range "1..4294967295";
          }
          description
           "This object represents the call identifier for the
            VoIP leg, which was assigned to the call.";
          smiv2:max-access "read-only";
          smiv2:oid "1.3.6.1.4.1.9.9.63.1.4.2.1.46";
        }

        leaf cvVoIPCallHistoryCallReferenceId {
          type cisco-voice:CvcCallReferenceIdOrZero;
          description
           "The call reference ID associates the video call entry and voice
            call entry of the same endpoint.  An audio-only call may or may
            not have a valid call reference ID (i.e. value greater than
            zero), but in both cases, there will not be a video call entry
            associated with it. 
            
            For a video call, the video-specific information  is stored in a
            call entry in cVideoSessionActive of CISCO-VIDEO-SESSION-MIB, in
            which the call reference ID is also identified.";
          smiv2:max-access "read-only";
          smiv2:oid "1.3.6.1.4.1.9.9.63.1.4.2.1.47";
        }

        leaf cvVoIPCallHistorySessionId {
          type uint32;
          description
           "This object indicates the session ID assigned by the call
            manager to identify call legs that belong to the same call
            session.  This session ID (history) represents a completed call
            session, whereas the active session ID
            (cvVoIPCallActiveSessionId) represents an ongoing session.";
          smiv2:max-access "read-only";
          smiv2:oid "1.3.6.1.4.1.9.9.63.1.4.2.1.48";
        }
      }
    }

    container cvCallRateStatsTable {
      description
       "This table represents voice call rate measurement in various
        interval lengths defined by the 
        CvCallVolumeStatsIntvlType object.
        
        Each interval may contain one or more entries to allow for
        detailed measurement to be collected.";
      smiv2:oid "1.3.6.1.4.1.9.9.63.1.4.3.1";

      list cvCallRateStatsEntry {
        key "cvCallRateStatsIntvlDurUnits cvCallRateStatsIntvlDur";
        description
         "This is a conceptual-row in cvCallRateStatsTable
          This entry is created at the system initialization and is
          updated at every epoch based on CvCallVolumeStatsIntvlType";
        smiv2:oid "1.3.6.1.4.1.9.9.63.1.4.3.1.1";

        leaf cvCallRateStatsIntvlDurUnits {
          type CISCO-VOICE-DIAL-CONTROL-MIB:CvCallVolumeStatsIntvlType;
          description
           "The Object indexes in Call Rate Table to select one among three
            interval-tables.
            
            The different types in this table are represented by 
            CvCallVolumeStatsIntvlType";
          smiv2:max-access "not-accessible";
          smiv2:oid "1.3.6.1.4.1.9.9.63.1.4.3.1.1.1";
        }

        leaf cvCallRateStatsIntvlDur {
          type uint32 {
            range "1..72";
          }
          description
           "This is an index that references to the different past periods
            in given in interval of call rate table.
            This range is 1-60 for Seconds and Minutes table 
            wherein 1-72 for hours table.";
          smiv2:max-access "not-accessible";
          smiv2:oid "1.3.6.1.4.1.9.9.63.1.4.3.1.1.2";
        }

        leaf cvCallRateStatsMaxVal {
          type uint32;
          units "calls-per-second";
          description
           "This object indicates the maximum calls per second
            that occured for the given period for the given interval.";
          smiv2:max-access "read-only";
          smiv2:oid "1.3.6.1.4.1.9.9.63.1.4.3.1.1.3";
        }

        leaf cvCallRateStatsAvgVal {
          type uint32;
          units "calls-per-second";
          description
           "This object indicates the average calls per second
            that occured for the given period for the given interval.";
          smiv2:max-access "read-only";
          smiv2:oid "1.3.6.1.4.1.9.9.63.1.4.3.1.1.4";
        }
      }
    }

    container cvCallLegRateStatsTable {
      description
       "cvCallLegRateStatsTable table represents voice call leg rate
        measurement in various interval lengths defined by 
        the CvCallVolumeStatsIntvlType object.
        Each interval may contain one or more entries to allow for
        detailed measurement to be collected.";
      smiv2:oid "1.3.6.1.4.1.9.9.63.1.4.3.2";

      list cvCallLegRateStatsEntry {
        key "cvCallLegRateStatsIntvlDurUnits cvCallLegRateStatsIntvlDur";
        description
         "This is a conceptual-row in cvCallLegRateStatsTable
          This entry is created at the system initialization and is
          updated at every epoch based on CvCallVolumeStatsIntvlType";
        smiv2:oid "1.3.6.1.4.1.9.9.63.1.4.3.2.1";

        leaf cvCallLegRateStatsIntvlDurUnits {
          type CISCO-VOICE-DIAL-CONTROL-MIB:CvCallVolumeStatsIntvlType;
          description
           "The Object indexes in Call Leg Rate Table to select one among
            three
            interval-tables.
            
            The different types in this table are represented by 
            CvCallVolumeStatsIntvlType";
          smiv2:max-access "not-accessible";
          smiv2:oid "1.3.6.1.4.1.9.9.63.1.4.3.2.1.1";
        }

        leaf cvCallLegRateStatsIntvlDur {
          type uint32 {
            range "1..72";
          }
          description
           "This is an index that references to the different past periods
            in given in interval of call rate table.
            This range is 1-60 for Seconds and Minutes table 
            wherein 1-72 for hours table.";
          smiv2:max-access "not-accessible";
          smiv2:oid "1.3.6.1.4.1.9.9.63.1.4.3.2.1.2";
        }

        leaf cvCallLegRateStatsMaxVal {
          type uint32;
          units "call-legs per second";
          description
           "This object indicates the maximum call-legs per second
            that occured for the given period for the given interval.";
          smiv2:max-access "read-only";
          smiv2:oid "1.3.6.1.4.1.9.9.63.1.4.3.2.1.3";
        }

        leaf cvCallLegRateStatsAvgVal {
          type uint32;
          units "call-legs per second";
          description
           "This object indicates the average call-legs per second
            that occured for the given period for the given interval.";
          smiv2:max-access "read-only";
          smiv2:oid "1.3.6.1.4.1.9.9.63.1.4.3.2.1.4";
        }
      }
    }

    container cvActiveCallStatsTable {
      description
       "This table represents the active voice calls in various
        interval lengths defined by the 
        CvCallVolumeStatsIntvlType object.
        
        Each interval may contain one or more entries to allow for
        detailed measurement to be collected.";
      smiv2:oid "1.3.6.1.4.1.9.9.63.1.4.3.3";

      list cvActiveCallStatsEntry {
        key "cvActiveCallStatsIntvlDurUnits cvActiveCallStatsIntvlDur";
        description
         "This is a conceptual-row in cvActiveCallStatsTable
          This entry is created at the system initialization and is
          updated at every epoch based on CvCallVolumeStatsIntvlType";
        smiv2:oid "1.3.6.1.4.1.9.9.63.1.4.3.3.1";

        leaf cvActiveCallStatsIntvlDurUnits {
          type CISCO-VOICE-DIAL-CONTROL-MIB:CvCallVolumeStatsIntvlType;
          description
           "The Object indexes in Active Call Rate Table (con-current calls
            table) to select one among three interval-tables.
            
            The different types in this table are represented by 
            CvCallVolumeStatsIntvlType";
          smiv2:max-access "not-accessible";
          smiv2:oid "1.3.6.1.4.1.9.9.63.1.4.3.3.1.1";
        }

        leaf cvActiveCallStatsIntvlDur {
          type uint32 {
            range "1..72";
          }
          description
           "This is an index that references to the different past periods
            in given in interval of active call table.
            This range is 1-60 for Seconds and Minutes table 
            wherein 1-72 for hours table.";
          smiv2:max-access "not-accessible";
          smiv2:oid "1.3.6.1.4.1.9.9.63.1.4.3.3.1.2";
        }

        leaf cvActiveCallStatsMaxVal {
          type uint32;
          units "calls";
          description
           "This object indicates the maximum number of active call
            that occured for the given period for the given interval.";
          smiv2:max-access "read-only";
          smiv2:oid "1.3.6.1.4.1.9.9.63.1.4.3.3.1.3";
        }

        leaf cvActiveCallStatsAvgVal {
          type uint32;
          units "calls";
          description
           "This object indicates the average number of active calls
            that occured for the given period for the given interval.";
          smiv2:max-access "read-only";
          smiv2:oid "1.3.6.1.4.1.9.9.63.1.4.3.3.1.4";
        }
      }
    }

    container cvCallDurationStatsTable {
      description
       "This table represents the number of calls below a specific
        duration in various interval length defined by 
        the CvCallVolumeStatsIntvlType object.  
        
        The specific duration is configurable value of 
         cvCallDurationStatsThreshold object.
        
        Each interval may contain one or more entries to allow for 
        detailed measurement to be collected.";
      smiv2:oid "1.3.6.1.4.1.9.9.63.1.4.3.4";

      list cvCallDurationStatsEntry {
        key "cvCallDurationStatsIntvlDurUnits cvCallDurationStatsIntvlDur";
        description
         "This is a conceptual-row in cvCallDurationStatsTable
          This entry is created at the system initialization and is
          updated at every epoch based on CvCallVolumeStatsIntvlType";
        smiv2:oid "1.3.6.1.4.1.9.9.63.1.4.3.4.1";

        leaf cvCallDurationStatsIntvlDurUnits {
          type CISCO-VOICE-DIAL-CONTROL-MIB:CvCallVolumeStatsIntvlType;
          description
           "The Object indexes in Call Duration Table to select one among
            three interval-tables.
            
            The different types in this table are represented by 
            CvCallVolumeStatsIntvlType";
          smiv2:max-access "not-accessible";
          smiv2:oid "1.3.6.1.4.1.9.9.63.1.4.3.4.1.1";
        }

        leaf cvCallDurationStatsIntvlDur {
          type uint32 {
            range "1..72";
          }
          description
           "This is an index that references to the different past periods
            in given in interval of call Duration table.
            This range is 1-60 for Seconds and Minutes table 
            wherein 1-72 for hours table.";
          smiv2:max-access "not-accessible";
          smiv2:oid "1.3.6.1.4.1.9.9.63.1.4.3.4.1.2";
        }

        leaf cvCallDurationStatsMaxVal {
          type uint32;
          units "calls";
          description
           "This object indicates the maximum number of calls having a
            duration which is below the threshold for the given interval.";
          smiv2:max-access "read-only";
          smiv2:oid "1.3.6.1.4.1.9.9.63.1.4.3.4.1.3";
        }

        leaf cvCallDurationStatsAvgVal {
          type uint32;
          units "calls";
          description
           "This object indicates the average number of calls having a
            duration which is below the threshold for the given interval.";
          smiv2:max-access "read-only";
          smiv2:oid "1.3.6.1.4.1.9.9.63.1.4.3.4.1.4";
        }
      }
    }

    container cvSipMsgRateStatsTable {
      description
       "This table represents the SIP message rate measurement in
        various interval length defined by the 
        CvCallVolumeStatsIntvlType object.
        
        Each interval may contain one or more entries to allow for
        detailed measurement to be collected";
      smiv2:oid "1.3.6.1.4.1.9.9.63.1.4.3.5";

      list cvSipMsgRateStatsEntry {
        key "cvSipMsgRateStatsIntvlDurUnits cvSipMsgRateStatsIntvlDur";
        description
         "This is a conceptual-row in cvSipMsgRateStatsTable
          This entry is created at the system initialization and is
          updated at every epoch based on CvCallVolumeStatsIntvlType";
        smiv2:oid "1.3.6.1.4.1.9.9.63.1.4.3.5.1";

        leaf cvSipMsgRateStatsIntvlDurUnits {
          type CISCO-VOICE-DIAL-CONTROL-MIB:CvCallVolumeStatsIntvlType;
          description
           "The Object indexes in SIP Message Rate Table to select one
            among three interval-tables.
            
            The different types in this table are represented by 
            CvCallVolumeStatsIntvlType";
          smiv2:max-access "not-accessible";
          smiv2:oid "1.3.6.1.4.1.9.9.63.1.4.3.5.1.1";
        }

        leaf cvSipMsgRateStatsIntvlDur {
          type uint32 {
            range "1..72";
          }
          description
           "This is an index that references to the different past
            periods in given in interval of SIP message rate table.
            This range is 1-60 for Seconds and Minutes table 
            wherein 1-72 for hours table.";
          smiv2:max-access "not-accessible";
          smiv2:oid "1.3.6.1.4.1.9.9.63.1.4.3.5.1.2";
        }

        leaf cvSipMsgRateStatsMaxVal {
          type uint32;
          units "SIP messages per second";
          description
           "This object indicates the maximum SIP messages  per second that
            is received for the given interval.";
          smiv2:max-access "read-only";
          smiv2:oid "1.3.6.1.4.1.9.9.63.1.4.3.5.1.3";
        }

        leaf cvSipMsgRateStatsAvgVal {
          type uint32;
          units "SIP messages per second";
          description
           "This object indicates the average SIP messages per second that
            is received for the given interval.";
          smiv2:max-access "read-only";
          smiv2:oid "1.3.6.1.4.1.9.9.63.1.4.3.5.1.4";
        }
      }
    }

    container cvCallRateWMTable {
      description
       "This table represents high watermarks achieved
        by call rate in various interval length defined 
        by CvCallVolumeWMIntvlType. 
        
        Each interval may contain one or more entries to allow for 
        detailed measurement to be collected";
      smiv2:oid "1.3.6.1.4.1.9.9.63.1.4.3.6";

      list cvCallRateWMEntry {
        key "cvCallRateWMIntvlDurUnits cvCallRateWMIndex";
        description
         "This is a conceptual-row in cvCallRateWMTable
          This entry is created at the system initialization and is
          updated whenever 
          a) This entry is obsolete OR
          b) A new/higher entry is available.
          These entries are reinitialised/added/deleted  if
          cvCallVolumeWMTableSize is changed";
        smiv2:oid "1.3.6.1.4.1.9.9.63.1.4.3.6.1";

        leaf cvCallRateWMIntvlDurUnits {
          type CISCO-VOICE-DIAL-CONTROL-MIB:CvCallVolumeWMIntvlType;
          description
           "The Object indexes in call rate Water mark Table to select one
            among four interval-tables.
            
            The different types in this table are represented by 
            CvCallVolumeWMIntvlType";
          smiv2:max-access "not-accessible";
          smiv2:oid "1.3.6.1.4.1.9.9.63.1.4.3.6.1.1";
        }

        leaf cvCallRateWMIndex {
          type uint32 {
            range "1..10";
          }
          description
           "This is an index that references to different peaks in
            past period in call rate watermark table.
            
            The number of watermarks entries stored for each table are 
            based on cvCallVolumeWMTableSize";
          smiv2:max-access "not-accessible";
          smiv2:oid "1.3.6.1.4.1.9.9.63.1.4.3.6.1.2";
        }

        leaf cvCallRateWMValue {
          type uint32;
          units "calls per second";
          description
           "This object indicates high watermark value achieved by the
            calls per second for the given interval";
          smiv2:max-access "read-only";
          smiv2:oid "1.3.6.1.4.1.9.9.63.1.4.3.6.1.3";
        }

        leaf cvCallRateWMts {
          type snmpv2-tc:DateAndTime;
          description
           "This object indicates date and Time when the high watermark
            is achieved for calls per second for the given interval";
          smiv2:max-access "read-only";
          smiv2:oid "1.3.6.1.4.1.9.9.63.1.4.3.6.1.4";
        }
      }
    }

    container cvCallLegRateWMTable {
      description
       "cvCallLegRateWMTable table represents high watermarks achieved
        by call-leg rate in various interval length defined 
        by CvCallVolumeWMIntvlType. 
        
        Each interval may contain one or more entries to allow for 
        detailed measurement to be collected";
      smiv2:oid "1.3.6.1.4.1.9.9.63.1.4.3.7";

      list cvCallLegRateWMEntry {
        key "cvCallLegRateWMIntvlDurUnits cvCallLegRateWMIndex";
        description
         "This is a conceptual-row in cvCallLegRateWMTable
          This entry is created at the system initialization and is
          updated whenever 
          a) This entry is obsolete OR
          b) A new/higher entry is available.
          These entries are reinitialised/added/deleted  if
          cvCallVolumeWMTableSize is changed";
        smiv2:oid "1.3.6.1.4.1.9.9.63.1.4.3.7.1";

        leaf cvCallLegRateWMIntvlDurUnits {
          type CISCO-VOICE-DIAL-CONTROL-MIB:CvCallVolumeWMIntvlType;
          description
           "The Object indexes in call leg rate Water mark Table to select
            one
            among four interval-tables.
            
            The different types in this table are represented by 
            CvCallVolumeWMIntvlType";
          smiv2:max-access "not-accessible";
          smiv2:oid "1.3.6.1.4.1.9.9.63.1.4.3.7.1.1";
        }

        leaf cvCallLegRateWMIndex {
          type uint32 {
            range "1..10";
          }
          description
           "This is an index that references to different peaks in
            past period in call leg rate watermark table.
            
            The number of watermarks entries stored for each table are 
            based on cvCallVolumeWMTableSize";
          smiv2:max-access "not-accessible";
          smiv2:oid "1.3.6.1.4.1.9.9.63.1.4.3.7.1.2";
        }

        leaf cvCallLegRateWMValue {
          type uint32;
          units "call legs per second";
          description
           "This object indicates high watermark value achieved by the
            call legs per second for the given interval";
          smiv2:max-access "read-only";
          smiv2:oid "1.3.6.1.4.1.9.9.63.1.4.3.7.1.3";
        }

        leaf cvCallLegRateWMts {
          type snmpv2-tc:DateAndTime;
          description
           "This object indicates date and time when the high watermark
            is achieved for call-legs per second for the given interval";
          smiv2:max-access "read-only";
          smiv2:oid "1.3.6.1.4.1.9.9.63.1.4.3.7.1.4";
        }
      }
    }

    container cvActiveCallWMTable {
      description
       "This table represents high watermarks achieved
        by active calls in various interval length defined 
        by CvCallVolumeWMIntvlType. 
        
        Each interval may contain one or more entries to allow 
        for detailed measurement to be collected.";
      smiv2:oid "1.3.6.1.4.1.9.9.63.1.4.3.8";

      list cvActiveCallWMEntry {
        key "cvActiveCallWMIntvlDurUnits cvActiveCallWMIndex";
        description
         "This is a conceptual-row in cvActiveCallWMTable
          This entry is created at the system initialization and is
          updated whenever 
          a) This entry is obsolete OR
          b) A new/higher entry is available.
          These entries are reinitialised/added/deleted  if
          cvCallVolumeWMTableSize is changed";
        smiv2:oid "1.3.6.1.4.1.9.9.63.1.4.3.8.1";

        leaf cvActiveCallWMIntvlDurUnits {
          type CISCO-VOICE-DIAL-CONTROL-MIB:CvCallVolumeWMIntvlType;
          description
           "The Object indexes in active call Water mark Table to select
            one among four interval-tables.
            
            The different types in this table are represented by 
            CvCallVolumeWMIntvlType";
          smiv2:max-access "not-accessible";
          smiv2:oid "1.3.6.1.4.1.9.9.63.1.4.3.8.1.1";
        }

        leaf cvActiveCallWMIndex {
          type uint32 {
            range "1..10";
          }
          description
           "This is an index that references to different peaks in
            past period in acive call watermark table.
            
            The number of watermarks entries stored for each table are 
            based on cvCallVolumeWMTableSize";
          smiv2:max-access "not-accessible";
          smiv2:oid "1.3.6.1.4.1.9.9.63.1.4.3.8.1.2";
        }

        leaf cvActiveCallWMValue {
          type uint32;
          units "calls";
          description
           "This object indicates high watermark value achieved by the
            active calls for the given interval";
          smiv2:max-access "read-only";
          smiv2:oid "1.3.6.1.4.1.9.9.63.1.4.3.8.1.3";
        }

        leaf cvActiveCallWMts {
          type snmpv2-tc:DateAndTime;
          description
           "This object indicates date and time when the high watermark
            is achieved for active calls for the given interval";
          smiv2:max-access "read-only";
          smiv2:oid "1.3.6.1.4.1.9.9.63.1.4.3.8.1.4";
        }
      }
    }

    container cvSipMsgRateWMTable {
      description
       "This table represents of high watermarks achieved
        by SIP message rate in various interval length defined 
        by CvCallVolumeWMIntvlType. 
        
        Each interval may contain one or more entries to allow for
        detailed measurement to be collected";
      smiv2:oid "1.3.6.1.4.1.9.9.63.1.4.3.9";

      list cvSipMsgRateWMEntry {
        key "cvSipMsgRateWMIntvlDurUnits cvSipMsgRateWMIndex";
        description
         "This is a conceptual-row in cvSipMsgRateWMTable.
          This entry is created at the system initialization and is
          updated whenever 
          a) This entry is obsolete OR
          b) A new/higher entry is available.
          These entries are reinitialised/added/deleted if
          cvCallVolumeWMTableSize is changed";
        smiv2:oid "1.3.6.1.4.1.9.9.63.1.4.3.9.1";

        leaf cvSipMsgRateWMIntvlDurUnits {
          type CISCO-VOICE-DIAL-CONTROL-MIB:CvCallVolumeWMIntvlType;
          description
           "The Object indexes in SIP Message rate Water mark Table to
            select one among four interval-tables.
            
            The different types in this table are represented by 
            CvCallVolumeWMIntvlType";
          smiv2:max-access "not-accessible";
          smiv2:oid "1.3.6.1.4.1.9.9.63.1.4.3.9.1.1";
        }

        leaf cvSipMsgRateWMIndex {
          type uint32 {
            range "1..10";
          }
          description
           "This is an index that references to different peaks in
            past period in sip message rate watermark table.
            
            The number of watermarks entries stored for each table are 
            based on cvCallVolumeWMTableSize";
          smiv2:max-access "not-accessible";
          smiv2:oid "1.3.6.1.4.1.9.9.63.1.4.3.9.1.2";
        }

        leaf cvSipMsgRateWMValue {
          type uint32;
          units "SIP messages per second";
          description
           "This object indicates high watermark value achieved by the
            SIP messages per second for the given interval";
          smiv2:max-access "read-only";
          smiv2:oid "1.3.6.1.4.1.9.9.63.1.4.3.9.1.3";
        }

        leaf cvSipMsgRateWMts {
          type snmpv2-tc:DateAndTime;
          description
           "This object indicates date and time when the high watermark
            is achieved for SIP messages per second for the given interval";
          smiv2:max-access "read-only";
          smiv2:oid "1.3.6.1.4.1.9.9.63.1.4.3.9.1.4";
        }
      }
    }
  }

  smiv2:alias "cvCallVolPeerTable" {
    description
     "This table represents the information about
      the usage of dialpeers configured in a 
      voice gateway.";
    smiv2:oid "1.3.6.1.4.1.9.9.63.1.3.8.4";
  }

  smiv2:alias "cvCallVolPeerEntry" {
    description
     "Each entry represents a row in cvCallVolPeerTable
      and corresponds to the information about a 
      dialpeer configured on the voice gateway.";
    smiv2:oid "1.3.6.1.4.1.9.9.63.1.3.8.4.1";
  }

  augment "/CISCO-VOICE-DIAL-CONTROL-MIB:CISCO-VOICE-DIAL-CONTROL-MIB/CISCO-VOICE-DIAL-CONTROL-MIB:cvPeerCfgTable/CISCO-VOICE-DIAL-CONTROL-MIB:cvPeerCfgEntry" {
    description
     "Each entry represents a row in cvCallVolPeerTable
      and corresponds to the information about a 
      dialpeer configured on the voice gateway.";
    smiv2:oid "1.3.6.1.4.1.9.9.63.1.3.8.4.1";

    leaf cvCallVolPeerIncomingCalls {
      type yang:gauge32 {
        range "0..65535";
      }
      description
       "This object represents the total number of
        active calls that has selected the dialpeer
        as an incoming dialpeer.";
      smiv2:max-access "read-only";
      smiv2:oid "1.3.6.1.4.1.9.9.63.1.3.8.4.1.1";
    }

    leaf cvCallVolPeerOutgoingCalls {
      type yang:gauge32 {
        range "0..65535";
      }
      description
       "This object represents the total number of
        active calls that has selected the dialpeer
        as an outgoing dialpeer.";
      smiv2:max-access "read-only";
      smiv2:oid "1.3.6.1.4.1.9.9.63.1.3.8.4.1.2";
    }
  }

  notification cvdcPoorQoVNotification {
    status deprecated;
    description
     "Poor quality of voice notification. A
      cvdcPoorQoVNotification is sent at the call disconnection
      time if the value of cvVoIPCallHistoryIcpif exceeds the
      value of cvVoIPPeerCfgIcpif in the call associated peer.";
    smiv2:oid "1.3.6.1.4.1.9.9.63.2.0.1";

    container object-1 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryConnectionId {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryConnectionId";
        }
      }
    }

    container object-2 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryIcpif {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryIcpif";
        }
      }
    }

    container object-3 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemoteIPAddress {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemoteIPAddress";
        }
        status deprecated;
      }
    }

    container object-4 {

      leaf cCallHistoryIndex {
        type leafref {
          path "/cisco-dial:CISCO-DIAL-CONTROL-MIB/cisco-dial:cCallHistoryTable/cisco-dial:cCallHistoryEntry/cisco-dial:cCallHistoryIndex";
        }
      }

      leaf cCallHistoryCallOrigin {
        type leafref {
          path "/cisco-dial:CISCO-DIAL-CONTROL-MIB/cisco-dial:cCallHistoryTable/cisco-dial:cCallHistoryEntry/cisco-dial:cCallHistoryCallOrigin";
        }
      }
    }

    container object-5 {

      leaf cCallHistoryIndex {
        type leafref {
          path "/cisco-dial:CISCO-DIAL-CONTROL-MIB/cisco-dial:cCallHistoryTable/cisco-dial:cCallHistoryEntry/cisco-dial:cCallHistoryIndex";
        }
      }

      leaf cvCommonDcCallHistoryCoderTypeRate {
        type leafref {
          path "/cisco-voice:CISCO-VOICE-COMMON-DIAL-CONTROL-MIB/cisco-voice:cvCommonDcCallHistoryTable/cisco-voice:cvCommonDcCallHistoryEntry/cisco-voice:cvCommonDcCallHistoryCoderTypeRate";
        }
      }
    }
  }

  notification cvdcPoorQoVNotificationRev1 {
    description
     "Poor quality of voice notification. A
      cvdcPoorQoVNotificationRev1 is sent at the call
      disconnection time if the value of cvVoIPCallHistoryIcpif
      exceeds the value of cvVoIPPeerCfgIcpif in the call
      associated peer.";
    smiv2:oid "1.3.6.1.4.1.9.9.63.2.0.2";

    container object-1 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryConnectionId {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryConnectionId";
        }
      }
    }

    container object-2 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryIcpif {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryIcpif";
        }
      }
    }

    container object-3 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemMediaIPAddrT {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemMediaIPAddrT";
        }
      }
    }

    container object-4 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemMediaIPAddr {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemMediaIPAddr";
        }
      }
    }

    container object-5 {

      leaf cCallHistoryIndex {
        type leafref {
          path "/cisco-dial:CISCO-DIAL-CONTROL-MIB/cisco-dial:cCallHistoryTable/cisco-dial:cCallHistoryEntry/cisco-dial:cCallHistoryIndex";
        }
      }

      leaf cCallHistoryCallOrigin {
        type leafref {
          path "/cisco-dial:CISCO-DIAL-CONTROL-MIB/cisco-dial:cCallHistoryTable/cisco-dial:cCallHistoryEntry/cisco-dial:cCallHistoryCallOrigin";
        }
      }
    }

    container object-6 {

      leaf cCallHistoryIndex {
        type leafref {
          path "/cisco-dial:CISCO-DIAL-CONTROL-MIB/cisco-dial:cCallHistoryTable/cisco-dial:cCallHistoryEntry/cisco-dial:cCallHistoryIndex";
        }
      }

      leaf cvCommonDcCallHistoryCoderTypeRate {
        type leafref {
          path "/cisco-voice:CISCO-VOICE-COMMON-DIAL-CONTROL-MIB/cisco-voice:cvCommonDcCallHistoryTable/cisco-voice:cvCommonDcCallHistoryEntry/cisco-voice:cvCommonDcCallHistoryCoderTypeRate";
        }
      }
    }
  }

  notification cvdcActiveDS0sHighNotification {
    description
     "The cvdcActiveDS0sHighNotification is sent when the
      percentage of active DS0s exceeds 
      cvCallActiveDS0sHighThreshold value.";
    smiv2:oid "1.3.6.1.4.1.9.9.63.2.0.3";

    container object-1 {

      leaf cvCallActiveDS0s {
        type leafref {
          path "/CISCO-VOICE-DIAL-CONTROL-MIB:CISCO-VOICE-DIAL-CONTROL-MIB/CISCO-VOICE-DIAL-CONTROL-MIB:cvGatewayCallActive/CISCO-VOICE-DIAL-CONTROL-MIB:cvCallActiveDS0s";
        }
      }
    }

    container object-2 {

      leaf cvCallActiveDS0sHighThreshold {
        type leafref {
          path "/CISCO-VOICE-DIAL-CONTROL-MIB:CISCO-VOICE-DIAL-CONTROL-MIB/CISCO-VOICE-DIAL-CONTROL-MIB:cvGatewayCallActive/CISCO-VOICE-DIAL-CONTROL-MIB:cvCallActiveDS0sHighThreshold";
        }
      }
    }
  }

  notification cvdcActiveDS0sLowNotification {
    description
     "The cvdcActiveDS0sLowNotification is sent when the
      percentage of active DS0s is less than 
      cvCallActiveDS0sLowThreshold value.";
    smiv2:oid "1.3.6.1.4.1.9.9.63.2.0.4";

    container object-1 {

      leaf cvCallActiveDS0s {
        type leafref {
          path "/CISCO-VOICE-DIAL-CONTROL-MIB:CISCO-VOICE-DIAL-CONTROL-MIB/CISCO-VOICE-DIAL-CONTROL-MIB:cvGatewayCallActive/CISCO-VOICE-DIAL-CONTROL-MIB:cvCallActiveDS0s";
        }
      }
    }

    container object-2 {

      leaf cvCallActiveDS0sLowThreshold {
        type leafref {
          path "/CISCO-VOICE-DIAL-CONTROL-MIB:CISCO-VOICE-DIAL-CONTROL-MIB/CISCO-VOICE-DIAL-CONTROL-MIB:cvGatewayCallActive/CISCO-VOICE-DIAL-CONTROL-MIB:cvCallActiveDS0sLowThreshold";
        }
      }
    }
  }

  notification cvdcFallbackNotification {
    description
     "This cvdcFallbackNotificaion is sent out,
      when the destination
          IP address of call fallback probe fails. This probe
          generated for beginning of each call, 
          with exception of existing cached entry.";
    smiv2:oid "1.3.6.1.4.1.9.9.63.2.0.5";

    container object-1 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryConnectionId {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryConnectionId";
        }
      }
    }

    container object-2 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryFallbackIcpif {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryFallbackIcpif";
        }
      }
    }

    container object-3 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryFallbackLoss {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryFallbackLoss";
        }
      }
    }

    container object-4 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryFallbackDelay {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryFallbackDelay";
        }
      }
    }

    container object-5 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemSigIPAddrT {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemSigIPAddrT";
        }
      }
    }

    container object-6 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemSigIPAddr {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemSigIPAddr";
        }
      }
    }

    container object-7 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemMediaIPAddrT {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemMediaIPAddrT";
        }
      }
    }

    container object-8 {

      leaf cCallHistoryIndex {
        type leafref {
          path "/cisco-dial:CISCO-DIAL-CONTROL-MIB/cisco-dial:cCallHistoryTable/cisco-dial:cCallHistoryEntry/cisco-dial:cCallHistoryIndex";
        }
      }

      leaf cvVoIPCallHistoryRemMediaIPAddr {
        type leafref {
          path "/CISCO-VOICE-DIAL-CONTROL-MIB:CISCO-VOICE-DIAL-CONTROL-MIB/CISCO-VOICE-DIAL-CONTROL-MIB:cvVoIPCallHistoryTable/CISCO-VOICE-DIAL-CONTROL-MIB:cvVoIPCallHistoryEntry/CISCO-VOICE-DIAL-CONTROL-MIB:cvVoIPCallHistoryRemMediaIPAddr";
        }
      }
    }

    container object-9 {

      leaf cCallHistoryIndex {
        type leafref {
          path "/cisco-dial:CISCO-DIAL-CONTROL-MIB/cisco-dial:cCallHistoryTable/cisco-dial:cCallHistoryEntry/cisco-dial:cCallHistoryIndex";
        }
      }

      leaf cCallHistoryCallOrigin {
        type leafref {
          path "/cisco-dial:CISCO-DIAL-CONTROL-MIB/cisco-dial:cCallHistoryTable/cisco-dial:cCallHistoryEntry/cisco-dial:cCallHistoryCallOrigin";
        }
      }
    }

    container object-10 {

      leaf cCallHistoryIndex {
        type leafref {
          path "/cisco-dial:CISCO-DIAL-CONTROL-MIB/cisco-dial:cCallHistoryTable/cisco-dial:cCallHistoryEntry/cisco-dial:cCallHistoryIndex";
        }
      }

      leaf cvCommonDcCallHistoryCoderTypeRate {
        type leafref {
          path "/cisco-voice:CISCO-VOICE-COMMON-DIAL-CONTROL-MIB/cisco-voice:cvCommonDcCallHistoryTable/cisco-voice:cvCommonDcCallHistoryEntry/cisco-voice:cvCommonDcCallHistoryCoderTypeRate";
        }
      }
    }
  }

  notification cvdcPolicyViolationNotification {
    description
     "Policy violation voice notification. A
      cvdcPolicyViolationNotification is sent when the call is active
      and has policy violation. It can be media policy violation or
      DSCP policy violation.";
    smiv2:oid "1.3.6.1.4.1.9.9.63.2.0.6";

    container object-1 {

      leaf callActiveSetupTime {
        type leafref {
          path "/dial-control:DIAL-CONTROL-MIB/dial-control:callActiveTable/dial-control:callActiveEntry/dial-control:callActiveSetupTime";
        }
      }

      leaf callActiveIndex {
        type leafref {
          path "/dial-control:DIAL-CONTROL-MIB/dial-control:callActiveTable/dial-control:callActiveEntry/dial-control:callActiveIndex";
        }
      }

      leaf ccVoIPCallActivePolicyName {
        type leafref {
          path "/CISCO-VOICE-DIAL-CONTROL-MIB:CISCO-VOICE-DIAL-CONTROL-MIB/CISCO-VOICE-DIAL-CONTROL-MIB:cvVoIPCallActiveTable/CISCO-VOICE-DIAL-CONTROL-MIB:cvVoIPCallActiveEntry/CISCO-VOICE-DIAL-CONTROL-MIB:ccVoIPCallActivePolicyName";
        }
      }
    }

    container object-2 {

      leaf callActiveSetupTime {
        type leafref {
          path "/dial-control:DIAL-CONTROL-MIB/dial-control:callActiveTable/dial-control:callActiveEntry/dial-control:callActiveSetupTime";
        }
      }

      leaf callActiveIndex {
        type leafref {
          path "/dial-control:DIAL-CONTROL-MIB/dial-control:callActiveTable/dial-control:callActiveEntry/dial-control:callActiveIndex";
        }
      }

      leaf cvVoIPCallActiveReversedDirectionPeerAddress {
        type leafref {
          path "/CISCO-VOICE-DIAL-CONTROL-MIB:CISCO-VOICE-DIAL-CONTROL-MIB/CISCO-VOICE-DIAL-CONTROL-MIB:cvVoIPCallActiveTable/CISCO-VOICE-DIAL-CONTROL-MIB:cvVoIPCallActiveEntry/CISCO-VOICE-DIAL-CONTROL-MIB:cvVoIPCallActiveReversedDirectionPeerAddress";
        }
      }
    }

    container object-3 {

      leaf callActiveSetupTime {
        type leafref {
          path "/dial-control:DIAL-CONTROL-MIB/dial-control:callActiveTable/dial-control:callActiveEntry/dial-control:callActiveSetupTime";
        }
      }

      leaf callActiveIndex {
        type leafref {
          path "/dial-control:DIAL-CONTROL-MIB/dial-control:callActiveTable/dial-control:callActiveEntry/dial-control:callActiveIndex";
        }
      }

      leaf callActivePeerId {
        type leafref {
          path "/dial-control:DIAL-CONTROL-MIB/dial-control:callActiveTable/dial-control:callActiveEntry/dial-control:callActivePeerId";
        }
      }
    }

    container object-4 {

      leaf callActiveSetupTime {
        type leafref {
          path "/dial-control:DIAL-CONTROL-MIB/dial-control:callActiveTable/dial-control:callActiveEntry/dial-control:callActiveSetupTime";
        }
      }

      leaf callActiveIndex {
        type leafref {
          path "/dial-control:DIAL-CONTROL-MIB/dial-control:callActiveTable/dial-control:callActiveEntry/dial-control:callActiveIndex";
        }
      }

      leaf callActivePeerAddress {
        type leafref {
          path "/dial-control:DIAL-CONTROL-MIB/dial-control:callActiveTable/dial-control:callActiveEntry/dial-control:callActivePeerAddress";
        }
      }
    }
  }

  smiv2:alias "ciscoVoiceDialControlMIB" {
    smiv2:oid "1.3.6.1.4.1.9.9.63";
  }

  smiv2:alias "cvdcMIBObjects" {
    smiv2:oid "1.3.6.1.4.1.9.9.63.1";
  }

  smiv2:alias "cvGeneralConfiguration" {
    smiv2:oid "1.3.6.1.4.1.9.9.63.1.1";
  }

  smiv2:alias "cvPeer" {
    smiv2:oid "1.3.6.1.4.1.9.9.63.1.2";
  }

  smiv2:alias "cvGatewayCallActive" {
    smiv2:oid "1.3.6.1.4.1.9.9.63.1.3";
  }

  smiv2:alias "cvCallVolume" {
    smiv2:oid "1.3.6.1.4.1.9.9.63.1.3.8";
  }

  smiv2:alias "cvCallRateMonitor" {
    smiv2:oid "1.3.6.1.4.1.9.9.63.1.3.11";
  }

  smiv2:alias "cvGatewayCallHistory" {
    smiv2:oid "1.3.6.1.4.1.9.9.63.1.4";
  }

  smiv2:alias "cvCallVolumeStatsHistory" {
    smiv2:oid "1.3.6.1.4.1.9.9.63.1.4.3";
  }

  smiv2:alias "cvdcMIBNotificationPrefix" {
    smiv2:oid "1.3.6.1.4.1.9.9.63.2";
  }

  smiv2:alias "cvdcMIBNotifications" {
    smiv2:oid "1.3.6.1.4.1.9.9.63.2.0";
  }

  smiv2:alias "cvdcMIBConformance" {
    smiv2:oid "1.3.6.1.4.1.9.9.63.3";
  }

  smiv2:alias "cvdcMIBCompliances" {
    smiv2:oid "1.3.6.1.4.1.9.9.63.3.1";
  }

  smiv2:alias "cvdcMIBGroups" {
    smiv2:oid "1.3.6.1.4.1.9.9.63.3.2";
  }

}
