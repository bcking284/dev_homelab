/*
 * Generated by confdc --mib2yang-std
 * Source: mgmt/dmi/model/mib/src/RFC-1212.mib
 */
/*
 * This YANG module has been generated by smidump 0.5.0:
 *
 *      smidump -f yang RFC-1212
 *
 * Do not edit. Edit the source file instead!
 */

module RFC-1212 {

  namespace "urn:ietf:params:xml:ns:yang:smiv2:RFC-1212";
  prefix RFC-1212;

  import ietf-yang-smiv2 {
    prefix "smiv2";
  }

}
