/*
 * Generated by confdc --mib2yang-std
 * Source: mgmt/dmi/model/mib/src/DOCS-L2VPN-MIB.mib
 */
/*
 * This YANG module has been generated by smidump 0.5.0:
 *
 *      smidump -f yang DOCS-L2VPN-MIB
 *
 * Do not edit. Edit the source file instead!
 */

module DOCS-L2VPN-MIB {

  namespace "urn:ietf:params:xml:ns:yang:smiv2:DOCS-L2VPN-MIB";
  prefix DOCS-L2VPN-MIB;

  import BRIDGE-MIB {
    prefix "bridge-mib";
  }

  import DOCS-IF-MIB {
    prefix "docs-if";
  }

  import DOCS-QOS-MIB {
    prefix "docs-qos";
  }

  import IF-MIB {
    prefix "if-mib";
  }

  import Q-BRIDGE-MIB {
    prefix "q-bridge";
  }

  import ietf-yang-smiv2 {
    prefix "smiv2";
  }

  import ietf-yang-types {
    prefix "yang";
  }

  organization
   "CableLabs";

  contact
   "Postal: Cable Television Laboratories, Inc.  
    858 Coal Creek Circle  
    Louisville, Colorado 80027-9750  
    U.S.A.  
    Phone:  +1 303-661-9100  
    Fax:   +1 303-661-9199  
    E-mail: mibs@cablelabs.com";

  description
   "This is the management MIB for devices complying to the  
    DOCSIS L2VPN Feature.";

  revision 2006-03-28 {
    description
     "Initial version.";
  }

  typedef DocsL2vpnIdentifier {
    type string;
    description
     "An externally administered octet string identifying an  
      L2VPN. An implementation MUST support a length of at least 
      16 octets. The octet string is used as an index. As such,  
      the CMTS enforces that objects of type DocsL2vpnIdentifier 
      are unique per CMTS. An MSO is encouraged to define  
      DocsL2vpnIdentifier values as globally unique.";
    smiv2:display-hint "255a";
  }

  typedef DocsL2vpnIndex {
    type uint32 {
      range "0..4294967295";
    }
    description
     "An integer value locally generated by the agent for each  
      known DocsL2vpnIdentifier administrative identifier. It is 
      intended to be used as a short index for tables in this MIB 
      module in lieu of an object of the type  
      DocsL2vpnIdentifier.";
  }

  typedef DocsNsiEncapSubtype {
    type enumeration {
      enum "other" {
        value "1";
      }
      enum "ieee8021q" {
        value "2";
      }
      enum "ieee8021ad" {
        value "3";
      }
      enum "mpls" {
        value "4";
      }
      enum "l2tpv3" {
        value "5";
      }
    }
    description
     "An enumerated integer that defines the default  
      encapsulation on NSI ports of an L2VPN-forwarded packet. 
      A CMTS implementation MUST support ieee802.1q(2). 
      A CMTS MAY omit support for all NSI  encapsulations  
      other than ieee802.1q(2).";
  }

  typedef DocsNsiEncapValue {
    type binary;
    description
     "The encapsulation value for L2VPN forwarded packets on NSI 
      ports. The value of an object of this type depends on the  
      value of an associated object of type DocsEncapSubtype: 
      
      other(1): vendor specific, 
      ieee8021q(2): 802.1Q tag with VLAN ID in lower 12 bits, 
      ieee8021ad(3): pair of 16-bit values with service provider 
      in lower 12 bits of the first 16-bit value and customer  
      VLAN ID in the lower 12 bits of the second 16-bit value, 
      mpls(4): must be zero length string, 
      l2tpv3(5): must be zero length string.";
  }

  typedef DocsL2vpnIfList {
    type bits {
      bit eCm {
        position "0";
      }
      bit cmci {
        position "1";
      }
      bit docsCableMacLayer {
        position "2";
      }
      bit docsCableDownstream {
        position "3";
      }
      bit docsCableUpstream {
        position "4";
      }
      bit eMta {
        position "16";
      }
      bit eStbIp {
        position "17";
      }
      bit eStbDsg {
        position "18";
      }
    }
    description
     "A object of this type indicates a set of CM  
      MAC bridge interfaces, encoded as a BITS syntax with a ?1? 
      Bit for each interface included in the set. 
      
      Bit position eCM(0) represents a conceptual interface to  
      the internal 'self' host MAC of the eCM itself. All other  
      bit positions K correspond to CM MAC bridge port interface 
      index with ifIndex value K.  
      
      A BITS object is encoded as an OCTET STRING, which may have 
      length zero. Bit position 0 is encoded in the most 
      significant bit of the first octet, proceeding to  
      bit position 7 in the least significant bit. Bit position 8 
      is encoded in the most significant bit of the second octet, 
      and so on. 
      
      In a CM, ifIndex value 1 corresponds to the primary CPE  
      interface. In CableHome devices, this interface is assigned 
      to the embedded Portal Services (ePS) host interface, which 
      provides a portal to the primary physical CPE interface.  
      In many contexts of a DocsL2VpnIfList, a '1' in bit  
      position 1 corresponds to 'any' or 'all' CPE interfaces  
      when the CM contains more than one CPE interface.  
      
      ifIndex value 2 corresponds to the docsCableMacLayer  
      RF MAC interface.  
      
      ifIndex values 3 and 4 correspond to the  
      docsCableDownstream and docsCableUpstream interfaces,  
      respectively, which are not separate MAC bridge port  
      interfaces. Bit positions 3 and 4 are unused in this type; 
      they must be saved and reported as configured, but  
      otherwise ignored.  
      
      ifIndex values 5 through 15 are reserved for individual 
      CPE interfaces for devices that implement more than one 
      CPE interface. In such devices, DocsL2vpnIfList bit  
      position 1 corresponds to the set of all CPE interfaces. 
      A CM with more than one CPE interface MAY assign a 
      DocsL2vpnIfList bit position within the range of 5..15 to 
      refer to the single primary CPE interface.  
      
      ifIndex value 16 is assigned to any embedded Multimedia  
      Terminal Adapter (eMTA) as defined by PacketCable. 
      
      ifIndex value 17 is assigned to the IP management host  
      interface of an embedded Set Top Box (eSTB). ifIndex value  
      18 is reserved for the DOCSIS Set-top Gateway (DSG) traffic 
      delivered to an eSTB.  
      
      ifIndex values 19 through 31 are 
      reserved for future defined embedded Service Application.";
  }


  container DOCS-L2VPN-MIB {
    config false;

    container docsL2vpnIdToIndexTable {
      description
       "Table indexed by the octet string DocsL2vpnIdentifier that 
        provides the local agent's internally assigned docsL2vpnIdx 
        value for that DocsL2vpnIdentifier value. The mapping of  
        DocsL2vpnIdentifier to docsL2vpnIdx is 1-1. The agent  
        must instantiate a row in both docsL2vpnIndexToIdTable and 
        docsL2vpnIdToIndexTable for each known L2VPN Identifier.";
      smiv2:oid "1.3.6.1.4.1.4491.2.1.8.1.1";

      list docsL2vpnIdToIndexEntry {
        key "docsL2vpnId";
        description
         "Maps a DocsL2vpnIdentifier octet string into the local  
          agent's locally assigned docsL2vpnIdx value.";
        smiv2:oid "1.3.6.1.4.1.4491.2.1.8.1.1.1";

        leaf docsL2vpnId {
          type DOCS-L2VPN-MIB:DocsL2vpnIdentifier;
          description
           "An externally configured octet string that identifies an 
            L2VPN.";
          smiv2:max-access "not-accessible";
          smiv2:oid "1.3.6.1.4.1.4491.2.1.8.1.1.1.1";
        }

        leaf docsL2vpnIdToIndexIdx {
          type DOCS-L2VPN-MIB:DocsL2vpnIndex;
          description
           "An internally assigned index value for a known L2VPN.";
          smiv2:max-access "read-only";
          smiv2:oid "1.3.6.1.4.1.4491.2.1.8.1.1.1.2";
        }
      }
    }

    container docsL2vpnIndexToIdTable {
      description
       "Table indexed by agent's local docsL2vpnIdx that provides 
        the global L2VPN Identifier. The mapping of docsL2vpnIdx to 
        DocsL2vpnIdentifier is 1-1. The agent must instantiate a  
        row in both docsL2vpnIndexToIdTable and  
        docsL2vpnIdToIndexTable for each known L2VPN.";
      smiv2:oid "1.3.6.1.4.1.4491.2.1.8.1.2";

      list docsL2vpnIndexToIdEntry {
        key "docsL2vpnIdx";
        description
         "Provides the L2VPN Identifier for each locally-assigned  
          L2vpn Index.";
        smiv2:oid "1.3.6.1.4.1.4491.2.1.8.1.2.1";

        leaf docsL2vpnIdx {
          type DOCS-L2VPN-MIB:DocsL2vpnIndex;
          description
           "An internally assigned index value for a known L2VPN.";
          smiv2:max-access "not-accessible";
          smiv2:oid "1.3.6.1.4.1.4491.2.1.8.1.2.1.1";
        }

        leaf docsL2vpnIndexToIdId {
          type DOCS-L2VPN-MIB:DocsL2vpnIdentifier;
          description
           "An administered octet string that externally identifies an 
            L2VPN.";
          smiv2:max-access "read-only";
          smiv2:oid "1.3.6.1.4.1.4491.2.1.8.1.2.1.2";
        }
      }
    }

    container docsL2vpnCmTable {
      description
       "This table describes L2VPN per-CM information that 
        is in common with all L2VPNs for the CM, regardless 
        of forwarding mode.";
      smiv2:oid "1.3.6.1.4.1.4491.2.1.8.1.3";

      list docsL2vpnCmEntry {
        key "docsIfCmtsCmStatusIndex";
        description
         "An entry is indexed by Cable Modem Index that 
          describes L2VPN information for a single CM that is in 
          common with all L2VPNs implemented by the CM, 
          regardless of the L2VPN forwarding mode. 
          
          An entry in this table is created for every CM that  
          registers with a forwarding L2VPN encoding.";
        smiv2:oid "1.3.6.1.4.1.4491.2.1.8.1.3.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf docsL2vpnCmCompliantCapability {
          type boolean;
          description
           "This object reports whether an L2VPN forwarding CM is 
            compliant with the DOCSIS L2VPN specification, as reported 
            in the L2VPN Capability encoding in the CM's registration 
            request message. 
            
            If the capability encoding was omitted, this object must 
            report the value false(2).";
          smiv2:max-access "read-only";
          smiv2:oid "1.3.6.1.4.1.4491.2.1.8.1.3.1.1";
        }

        leaf docsL2vpnCmDutFilteringCapability {
          type boolean;
          description
           "This object reports whether an L2VPN forwarding CM is 
            capable of Downstream Unencrypted Traffic (DUT) Filtering, 
            as reported in the CM's registration request message. 
            
            If the capability encoding was omitted, this object must 
            report the value false(2).";
          smiv2:max-access "read-only";
          smiv2:oid "1.3.6.1.4.1.4491.2.1.8.1.3.1.2";
        }

        leaf docsL2vpnCmDutCMIM {
          type binary;
          description
           "This object reports the value configured in a per-CM  
            L2VPN Encoding for Downstream Unencrypted Traffic (DUT) 
            Cable Modem Interface Mask (CMIM).  
            
            The DUT CMIM is a bit string with a '1' for each bit  
            position K for an internal or external CM interface with  
            ifIndex K to which the CM permits DUT to be forwarded. A CM 
            capable of DUT filtering MUST discard DUT to interfaces 
            with a '0' in the DUT CMIM.  
            
            If a CM's top-level registration request L2VPN Encoding 
            contained no DUT CMIM subtype, this object is reported 
            with its default value of a '1' in bit position 0  
            (corresponding to the eCM's own 'self' host) and a '1' in  
            each bit position K for which an eSAFE interface exists at 
            ifIndex K. In other words, the default DUT CMIM includes  
            the eCM and all eSAFE interfaces. 
            
            This value is reported independently of whether the CM is 
            actually capable of performing DUT filtering.";
          smiv2:max-access "read-only";
          smiv2:oid "1.3.6.1.4.1.4491.2.1.8.1.3.1.3";
        }

        leaf docsL2vpnCmDhcpSnooping {
          type DOCS-L2VPN-MIB:DocsL2vpnIfList;
          description
           "This object reports the value of the Enable DHCP Snooping 
            subtype of a top-level L2VPN Encoding.  
            
            It has the syntax of a CM Interface List bitmask and 
            represents a set of CM MAC bridge interfaces  
            corresponding to eSAFE hosts for which the CMTS is enabled  
            to snoop DHCP traffic in order to learn the eSAFE host MAC 
            address on that interface.   
            
            Only bits corresponding to eSAFE host MAC addresses may be 
            validly set in this object, including cpe(1) for ePS 
            and the eSAFE interfaces in bits positions 16 through 31.";
          smiv2:max-access "read-only";
          smiv2:oid "1.3.6.1.4.1.4491.2.1.8.1.3.1.4";
        }
      }
    }

    container docsL2vpnVpnCmTable {
      description
       "This table describes the operation of L2VPN forwarding 
        on each CM.";
      smiv2:oid "1.3.6.1.4.1.4491.2.1.8.1.4";

      list docsL2vpnVpnCmEntry {
        key "docsL2vpnIdx docsIfCmtsCmStatusIndex";
        description
         "An entry is indexed by VPN ID and Cable Modem Index that 
          describes the operation of L2VPN forwarding for a single 
          L2VPN on a single CM.";
        smiv2:oid "1.3.6.1.4.1.4491.2.1.8.1.4.1";

        leaf docsL2vpnIdx {
          type leafref {
            path "/DOCS-L2VPN-MIB:DOCS-L2VPN-MIB/DOCS-L2VPN-MIB:docsL2vpnIndexToIdTable/DOCS-L2VPN-MIB:docsL2vpnIndexToIdEntry/DOCS-L2VPN-MIB:docsL2vpnIdx";
          }
        }

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf docsL2vpnVpnCmCMIM {
          type DOCS-L2VPN-MIB:DocsL2vpnIfList;
          description
           "A Cable Modem Interface Mask represents a set of  
            MAC bridge interfaces within the CM. This object 
            represents the CMIM within a forwarding per-SF L2VPN  
            encoding, which specifies a set of CM MAC bridge  
            interfaces to which L2VPN forwarding is restricted. 
            
            If the CMIM Subtype is omitted from a forwarding 
            per-SF encoding, its default value includes only 
            cpePrimary(1) and cableMac(2), which can be encoded 
            with a single octet with the value 0x60.";
          smiv2:max-access "read-only";
          smiv2:oid "1.3.6.1.4.1.4491.2.1.8.1.4.1.1";
        }

        leaf docsL2vpnVpnCmIndividualSAId {
          type int32 {
            range "0..16383";
          }
          description
           "The BPI+ Security Association ID in which traffic intended 
            for point-to-point forwarding through an individual CM is  
            forwarded.  
            
            If the CMTS does not allocate an individual SAID for 
            multipoint forwarding (as is recommended),it MUST  
            report this object as zero.";
          smiv2:max-access "read-only";
          smiv2:oid "1.3.6.1.4.1.4491.2.1.8.1.4.1.2";
        }

        leaf docsL2vpnVpnCmVendorSpecific {
          type binary;
          description
           "This object encodes the concatenation of all Vendor  
            Specific Subtype encodings that appeared in any  
            registration per-CM L2VPN Encoding associated with this  
            entry.";
          smiv2:max-access "read-only";
          smiv2:oid "1.3.6.1.4.1.4491.2.1.8.1.4.1.3";
        }
      }
    }

    container docsL2vpnVpnCmStatsTable {
      description
       "This table contains statistics for forwarding of  
        packets to and from a CM on each VPN.";
      smiv2:oid "1.3.6.1.4.1.4491.2.1.8.1.5";

      list docsL2vpnVpnCmStatsEntry {
        key "docsL2vpnIdx docsIfCmtsCmStatusIndex";
        description
         "An entry is indexed by VPN ID and Cable Modem Index.";
        smiv2:oid "1.3.6.1.4.1.4491.2.1.8.1.5.1";

        leaf docsL2vpnIdx {
          type leafref {
            path "/DOCS-L2VPN-MIB:DOCS-L2VPN-MIB/DOCS-L2VPN-MIB:docsL2vpnIndexToIdTable/DOCS-L2VPN-MIB:docsL2vpnIndexToIdEntry/DOCS-L2VPN-MIB:docsL2vpnIdx";
          }
        }

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf docsL2vpnVpnCmStatsUpstreamPkts {
          type yang:counter32;
          description
           "The number of L2vpn-forwarded packets received 
            from this instance's Cable Modem on 
            this instance's L2VPN.";
          smiv2:max-access "read-only";
          smiv2:oid "1.3.6.1.4.1.4491.2.1.8.1.5.1.1";
        }

        leaf docsL2vpnVpnCmStatsUpstreamBytes {
          type yang:counter32;
          description
           "The number of L2vpn-forwarded bytes received 
            from this instance's Cable Modem on 
            this instance's L2VPN.";
          smiv2:max-access "read-only";
          smiv2:oid "1.3.6.1.4.1.4491.2.1.8.1.5.1.2";
        }

        leaf docsL2vpnVpnCmStatsUpstreamDiscards {
          type yang:counter32;
          description
           "The number of L2-forwarded packets  
            discarded from this instance's  
            Cable Modem on this instance's VPN.";
          smiv2:max-access "read-only";
          smiv2:oid "1.3.6.1.4.1.4491.2.1.8.1.5.1.3";
        }

        leaf docsL2vpnVpnCmStatsDownstreamPkts {
          type yang:counter32;
          description
           "The number of L2-forwarded packets 
            transmitted to this instance's 
            Cable Modem on this instance's VPN.";
          smiv2:max-access "read-only";
          smiv2:oid "1.3.6.1.4.1.4491.2.1.8.1.5.1.4";
        }

        leaf docsL2vpnVpnCmStatsDownstreamBytes {
          type yang:counter32;
          description
           "The number of L2-forwarded bytes 
            transmitted to this instance's 
            Cable Modem on this instance's VPN.";
          smiv2:max-access "read-only";
          smiv2:oid "1.3.6.1.4.1.4491.2.1.8.1.5.1.5";
        }

        leaf docsL2vpnVpnCmStatsDownstreamDiscards {
          type yang:counter32;
          description
           "The number of L2-forwarded packets that were discarded  
            before they could be transmitted to this instance's  
            Cable Modem on this instance's VPN.";
          smiv2:max-access "read-only";
          smiv2:oid "1.3.6.1.4.1.4491.2.1.8.1.5.1.6";
        }
      }
    }

    container docsL2vpnPortStatusTable {
      description
       "This table displays summary information for the 
        run-time state of each VPN that is currently operating  
        on each bridge port.";
      smiv2:oid "1.3.6.1.4.1.4491.2.1.8.1.6";

      list docsL2vpnPortStatusEntry {
        key "dot1dBasePort docsL2vpnIdx";
        description
         "Information specific to the operation of L2VPN forwarding 
          on a particular CMTS 'bridge port'. A CMTS 'bridge port'  
          may be defined by the CMTS vendor, but is advantageously a 
          single DOCSIS MAC Domain.";
        smiv2:oid "1.3.6.1.4.1.4491.2.1.8.1.6.1";

        leaf dot1dBasePort {
          type leafref {
            path "/bridge-mib:BRIDGE-MIB/bridge-mib:dot1dBasePortTable/bridge-mib:dot1dBasePortEntry/bridge-mib:dot1dBasePort";
          }
        }

        leaf docsL2vpnIdx {
          type leafref {
            path "/DOCS-L2VPN-MIB:DOCS-L2VPN-MIB/DOCS-L2VPN-MIB:docsL2vpnIndexToIdTable/DOCS-L2VPN-MIB:docsL2vpnIndexToIdEntry/DOCS-L2VPN-MIB:docsL2vpnIdx";
          }
        }

        leaf docsL2vpnPortStatusGroupSAId {
          type int32 {
            range "0..16383";
          }
          description
           "The Group SAID associated with this VPN on a  
            particular CMTS MAC domain. This SAID is used to encrypt 
            all downstream flooded bridge traffic sent to CMs on  
            this VPN and CMTS MAC domain bridge port.  
            
            A value of '0' means there is no associated Group SAID for 
            this VPN and bridge port, e.g., if the L2VPN uses 
            point-to-point individual SAIDs only for forwarding. 
            
            A bridge port that is not a CMTS MAC 
            domain will report a value of '0'.";
          smiv2:max-access "read-only";
          smiv2:oid "1.3.6.1.4.1.4491.2.1.8.1.6.1.1";
        }
      }
    }

    container docsL2vpnSfStatusTable {
      description
       "This table displays SF-specific L2VPN forwarding status  
        for each upstream service flow configured with a per-SF  
         L2VPN Encoding. 
        
         Objects which were signaled in a per-SF L2VPN Encoding but 
         apply for the entire CM are shown in the  
         docsL2vpnVpnCmTable.";
      smiv2:oid "1.3.6.1.4.1.4491.2.1.8.1.7";

      list docsL2vpnSfStatusEntry {
        key "ifIndex docsQosServiceFlowId";
        description
         "SF-specific L2VPN forwarding status information for each 
          upstream service flow configured with a per-SF L2VPN  
          Encoding. The ifIndex is of type docsCableMacLayer(127).";
        smiv2:oid "1.3.6.1.4.1.4491.2.1.8.1.7.1";

        leaf ifIndex {
          type leafref {
            path "/if-mib:IF-MIB/if-mib:ifTable/if-mib:ifEntry/if-mib:ifIndex";
          }
        }

        leaf docsQosServiceFlowId {
          type leafref {
            path "/docs-qos:DOCS-QOS-MIB/docs-qos:docsQosServiceFlowTable/docs-qos:docsQosServiceFlowEntry/docs-qos:docsQosServiceFlowId";
          }
        }

        leaf docsL2vpnSfStatusL2vpnId {
          type binary;
          description
           "This object represents the value of the L2VPN Identifier 
            subtype of a per-SF L2VPN Encoding.";
          smiv2:max-access "read-only";
          smiv2:oid "1.3.6.1.4.1.4491.2.1.8.1.7.1.1";
        }

        leaf docsL2vpnSfStatusIngressUserPriority {
          type uint32 {
            range "0..7";
          }
          description
           "This object provides the configured Ingress User Priority 
            subtype of a per-SF L2VPN Encoding for this CM. If the  
            subtype was omitted, this object's value is zero.";
          smiv2:max-access "read-only";
          smiv2:oid "1.3.6.1.4.1.4491.2.1.8.1.7.1.2";
        }

        leaf docsL2vpnSfStatusVendorSpecific {
          type binary;
          description
           "This object provides the set of configured Vendor Specific 
            subtypes within a per-SF L2VPN Encoding for a CM. If no  
            Vendor Specific subtype was specified, this object is a  
            zero length octet string. If one or more Vendor Specific  
            subtype parameters was specified, this object represents  
            the concatenation of all such subtypes.";
          smiv2:max-access "read-only";
          smiv2:oid "1.3.6.1.4.1.4491.2.1.8.1.7.1.3";
        }
      }
    }

    container docsL2vpnPktClassTable {
      description
       "This table provides the L2VPN-specific objects for 
        packet classifiers that apply to only L2VPN traffic.  
        The indices of this table are a subset of the 
        indices of classifiers in docsQosPktClassTable.";
      smiv2:oid "1.3.6.1.4.1.4491.2.1.8.1.8";

      list docsL2vpnPktClassEntry {
        key "ifIndex docsQosServiceFlowId docsQosPktClassId";
        description
         "An entry in this table extends a single row 
          of docsQosPktClassTable for a rule that applies only to 
          downstream L2VPN forwarded packets. 
          The index ifIndex is an ifType of docsCableMaclayer(127).";
        smiv2:oid "1.3.6.1.4.1.4491.2.1.8.1.8.1";

        leaf ifIndex {
          type leafref {
            path "/if-mib:IF-MIB/if-mib:ifTable/if-mib:ifEntry/if-mib:ifIndex";
          }
        }

        leaf docsQosServiceFlowId {
          type leafref {
            path "/docs-qos:DOCS-QOS-MIB/docs-qos:docsQosServiceFlowTable/docs-qos:docsQosServiceFlowEntry/docs-qos:docsQosServiceFlowId";
          }
        }

        leaf docsQosPktClassId {
          type leafref {
            path "/docs-qos:DOCS-QOS-MIB/docs-qos:docsQosPktClassTable/docs-qos:docsQosPktClassEntry/docs-qos:docsQosPktClassId";
          }
        }

        leaf docsL2vpnPktClassL2vpnId {
          type DOCS-L2VPN-MIB:DocsL2vpnIdentifier;
          description
           "The locally assigned L2VPN index corresponding to the VPN 
            Identifier subtype of a Downstream Classifier L2VPN  
            Encoding.";
          smiv2:max-access "read-only";
          smiv2:oid "1.3.6.1.4.1.4491.2.1.8.1.8.1.1";
        }

        leaf docsL2vpnPktClassUserPriRangeLow {
          type uint32 {
            range "0..7";
          }
          description
           "The lower priority of the user Priority Range subtype 
            of a Downstream Classifier L2VPN Encoding. If the subtype 
            was omitted, this object has value 0.";
          smiv2:max-access "read-only";
          smiv2:oid "1.3.6.1.4.1.4491.2.1.8.1.8.1.2";
        }

        leaf docsL2vpnPktClassUserPriRangeHigh {
          type uint32 {
            range "0..7";
          }
          description
           "The higher priority of the user Priority Range subtype 
            of a Downstream Classifier L2VPN Encoding. If the subtype 
            was omitted, this object has value 7.";
          smiv2:max-access "read-only";
          smiv2:oid "1.3.6.1.4.1.4491.2.1.8.1.8.1.3";
        }

        leaf docsL2vpnPktClassCMIM {
          type DOCS-L2VPN-MIB:DocsL2vpnIfList;
          description
           "The Cable Modem Interface Mask (CMIM) signaled in a  
            Packet Classifier Encoding.  In a Downstream Packet  
            Classifier Encoding, a specified CMIM value restricts the  
            classifier to match packets with a Destination MAC address 
            corresponding to the interfaces indicated in the CMIM mask. 
            The eCM self and any eSAFE interface bits correspond to 
            the individual eCM and eSAFE host MAC addresses. 
            
            In an Upstream Packet Classifier encoding, a specified CMIM 
            value restricts the classifier to match packets with an  
            ingress bridge port interface matching the bits in the  
            CMIM value. 
            
            If the CMIM subtype was omitted, this object should be  
            reported as a zero length octet string.";
          smiv2:max-access "read-only";
          smiv2:oid "1.3.6.1.4.1.4491.2.1.8.1.8.1.4";
        }

        leaf docsL2vpnPktClassVendorSpecific {
          type binary;
          description
           "This object provides the set of configured  
            Vendor Specific subtypes within a Packet Classifier  
            Encoding for a CM. If no Vendor Specific subtype was  
            specified, this object is a zero length octet string.  
            If one or more Vendor Specific subtype parameters was  
            specified, this object represents the concatenation of all 
            such subtypes.";
          smiv2:max-access "read-only";
          smiv2:oid "1.3.6.1.4.1.4491.2.1.8.1.8.1.5";
        }
      }
    }

    container docsL2vpnCmNsiTable {
      description
       "This table describes the NSI configuration for a single 
        CM when operating in point-to-point forwarding mode for an 
        L2VPN.";
      smiv2:oid "1.3.6.1.4.1.4491.2.1.8.1.9";

      list docsL2vpnCmNsiEntry {
        key "docsL2vpnIdx docsIfCmtsCmStatusIndex";
        description
         "An entry indexed by VPN ID and Cable Modem Index that 
          describes the point-to-point forwarding between a single 
          NSI encapsulation and a single CM. This table is  
          implemented only for a CM forwarding an L2VPN on a  
          point-to-point basis. It is associated with a single  
          per-CM L2VPN encoding.";
        smiv2:oid "1.3.6.1.4.1.4491.2.1.8.1.9.1";

        leaf docsL2vpnIdx {
          type leafref {
            path "/DOCS-L2VPN-MIB:DOCS-L2VPN-MIB/DOCS-L2VPN-MIB:docsL2vpnIndexToIdTable/DOCS-L2VPN-MIB:docsL2vpnIndexToIdEntry/DOCS-L2VPN-MIB:docsL2vpnIdx";
          }
        }

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf docsL2vpnCmNsiEncapSubtype {
          type DOCS-L2VPN-MIB:DocsNsiEncapSubtype;
          description
           "The General Encapsulation Information (GEI) subtype of the 
            Network System Interface (NSI) encapsulation configured 
            for the CM.";
          smiv2:max-access "read-only";
          smiv2:oid "1.3.6.1.4.1.4491.2.1.8.1.9.1.1";
        }

        leaf docsL2vpnCmNsiEncapValue {
          type DOCS-L2VPN-MIB:DocsNsiEncapValue;
          description
           "The encapsulation value for L2VPN forwarded packets on NSI 
            ports.";
          smiv2:max-access "read-only";
          smiv2:oid "1.3.6.1.4.1.4491.2.1.8.1.9.1.2";
        }

        leaf docsL2vpnCmNsiAGI {
          type binary;
          description
           "This object is the configuration of any Attachment Group  
            Identifier subtype in the per-SF L2VPN Encoding  
            represented by this row. If the subtype was omitted, this  
            object's value is a zero length string.";
          smiv2:max-access "read-only";
          smiv2:oid "1.3.6.1.4.1.4491.2.1.8.1.9.1.3";
        }

        leaf docsL2vpnCmNsiSAII {
          type binary;
          description
           "This object is the configuration of any Source  
            Attachment Individual ID subtype in the L2VPN Encoding  
            represented by this row. If the subtype was omitted, this 
            object's value is a zero length string.";
          smiv2:max-access "read-only";
          smiv2:oid "1.3.6.1.4.1.4491.2.1.8.1.9.1.4";
        }

        leaf docsL2vpnCmNsiTAII {
          type binary;
          description
           "This object is the configuration of any Target 
            Attachment Individual ID subtype in the L2VPN Encoding 
            represented by this row. If the subtype was omitted, this 
            object's value is a zero length string.";
          smiv2:max-access "read-only";
          smiv2:oid "1.3.6.1.4.1.4491.2.1.8.1.9.1.5";
        }
      }
    }

    container docsL2vpnCmVpnCpeTable {
      description
       "This table is a list of CPEs, indexed by the VPNs on a  
        Cable Modem.";
      smiv2:oid "1.3.6.1.4.1.4491.2.1.8.1.10";

      list docsL2vpnCmVpnCpeEntry {
        key "docsIfCmtsCmStatusIndex docsL2vpnIdx docsL2vpnCmVpnCpeMacAddress";
        description
         "This table is a list of CPEs, indexed by the VPNs on a  
          Cable Modem.";
        smiv2:oid "1.3.6.1.4.1.4491.2.1.8.1.10.1";

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf docsL2vpnIdx {
          type leafref {
            path "/DOCS-L2VPN-MIB:DOCS-L2VPN-MIB/DOCS-L2VPN-MIB:docsL2vpnIndexToIdTable/DOCS-L2VPN-MIB:docsL2vpnIndexToIdEntry/DOCS-L2VPN-MIB:docsL2vpnIdx";
          }
        }

        leaf docsL2vpnCmVpnCpeMacAddress {
          type yang:mac-address;
          description
           "The Customer Premise Equipment (CPE) Mac Address 
            that is attached to this instances Cable Modem 
            and bridging on this instance's VPN Id.";
          smiv2:max-access "read-only";
          smiv2:oid "1.3.6.1.4.1.4491.2.1.8.1.10.1.1";
        }
      }
    }

    container docsL2vpnVpnCmCpeTable {
      description
       "This table contains a list of bridging CPEs, indexed by 
        L2VPN Index and the corresponding CMs on that VPN.";
      smiv2:oid "1.3.6.1.4.1.4491.2.1.8.1.11";

      list docsL2vpnVpnCmCpeEntry {
        key "docsL2vpnIdx docsIfCmtsCmStatusIndex docsL2vpnVpnCmCpeMacAddress";
        description
         "This table contains a list of bridging CPEs, indexed by 
          VPN and the corresponding CMs on that VPN.";
        smiv2:oid "1.3.6.1.4.1.4491.2.1.8.1.11.1";

        leaf docsL2vpnIdx {
          type leafref {
            path "/DOCS-L2VPN-MIB:DOCS-L2VPN-MIB/DOCS-L2VPN-MIB:docsL2vpnIndexToIdTable/DOCS-L2VPN-MIB:docsL2vpnIndexToIdEntry/DOCS-L2VPN-MIB:docsL2vpnIdx";
          }
        }

        leaf docsIfCmtsCmStatusIndex {
          type leafref {
            path "/docs-if:DOCS-IF-MIB/docs-if:docsIfCmtsCmStatusTable/docs-if:docsIfCmtsCmStatusEntry/docs-if:docsIfCmtsCmStatusIndex";
          }
        }

        leaf docsL2vpnVpnCmCpeMacAddress {
          type yang:mac-address;
          description
           "The Customer Premise Equipment (CPE) Mac Address 
            that is attached to this instances Cable Modem 
            and bridging on this instance's L2vpn Index.";
          smiv2:max-access "read-only";
          smiv2:oid "1.3.6.1.4.1.4491.2.1.8.1.11.1.1";
        }
      }
    }

    container docsL2vpnDot1qTpFdbExtTable {
      description
       "This table contains packet counters for  
        Unicast MAC Addresses within a VPN.";
      smiv2:oid "1.3.6.1.4.1.4491.2.1.8.1.12";

      list docsL2vpnDot1qTpFdbExtEntry {
        key "dot1qFdbId dot1qTpFdbAddress";
        description
         "This table extends the dot1qTpFdbTable only for RF network 
          bridge port entries.  It is implemented by an agent only 
          if the agent implements dot1qTpFdbTable for RF network 
          bridge ports.";
        smiv2:oid "1.3.6.1.4.1.4491.2.1.8.1.12.1";

        leaf dot1qFdbId {
          type leafref {
            path "/q-bridge:Q-BRIDGE-MIB/q-bridge:dot1qFdbTable/q-bridge:dot1qFdbEntry/q-bridge:dot1qFdbId";
          }
        }

        leaf dot1qTpFdbAddress {
          type leafref {
            path "/q-bridge:Q-BRIDGE-MIB/q-bridge:dot1qTpFdbTable/q-bridge:dot1qTpFdbEntry/q-bridge:dot1qTpFdbAddress";
          }
        }

        leaf docsL2vpnDot1qTpFdbExtTransmitPkts {
          type yang:counter32;
          description
           "The number of packets where the Destination  
            MAC Address matched this instance  
            dot1qTpFdbAddress and packet was bridged on 
            a VPN, where the VPN ID matched this  
            instance's dot1qFdbId.";
          smiv2:max-access "read-only";
          smiv2:oid "1.3.6.1.4.1.4491.2.1.8.1.12.1.1";
        }

        leaf docsL2vpnDot1qTpFdbExtReceivePkts {
          type yang:counter32;
          description
           "The number of packets where the Source MAC  
            Address matched this instance dot1qTpFdbAddress 
            and the packet was bridged on a VPN, 
            where the docsL2vpnIdx matched this instance's  
            dot1qFdbId.";
          smiv2:max-access "read-only";
          smiv2:oid "1.3.6.1.4.1.4491.2.1.8.1.12.1.2";
        }
      }
    }

    container docsL2vpnDot1qTpGroupExtTable {
      description
       "This table contains packet counters for  
        Multicast MAC Addresses within a VPN.";
      smiv2:oid "1.3.6.1.4.1.4491.2.1.8.1.13";

      list docsL2vpnDot1qTpGroupExtEntry {
        key "dot1qVlanIndex dot1qTpGroupAddress";
        description
         "This table extends the dot1qTpGroupTable only for RF  
          Network bridge port entries.  It is implemented by an agent 
          Only if the agent implements dot1qTpGroupTable for RF  
          network bridge ports.";
        smiv2:oid "1.3.6.1.4.1.4491.2.1.8.1.13.1";

        leaf dot1qVlanIndex {
          type leafref {
            path "/q-bridge:Q-BRIDGE-MIB/q-bridge:dot1qVlanCurrentTable/q-bridge:dot1qVlanCurrentEntry/q-bridge:dot1qVlanIndex";
          }
        }

        leaf dot1qTpGroupAddress {
          type leafref {
            path "/q-bridge:Q-BRIDGE-MIB/q-bridge:dot1qTpGroupTable/q-bridge:dot1qTpGroupEntry/q-bridge:dot1qTpGroupAddress";
          }
        }

        leaf docsL2vpnDot1qTpGroupExtTransmitPkts {
          type yang:counter32;
          description
           "The number of packets where the Destination  
            MAC Address matched this instance  
            dot1qTpGroupAddress and packet was bridged on 
            a VPN, where the docsL2vpnIdx matched this  
            instance's dot1qVlanIndex.";
          smiv2:max-access "read-only";
          smiv2:oid "1.3.6.1.4.1.4491.2.1.8.1.13.1.1";
        }

        leaf docsL2vpnDot1qTpGroupExtReceivePkts {
          type yang:counter32;
          description
           "The number of packets where the Source MAC  
            Address matched this instance dot1qTpGroupAddress 
            and the packet was bridged on a VPN, 
            where the docsL2vpnIdx matched this instance's  
            dot1qVlanIndex.";
          smiv2:max-access "read-only";
          smiv2:oid "1.3.6.1.4.1.4491.2.1.8.1.13.1.2";
        }
      }
    }
  }

  smiv2:alias "docsL2vpnMIB" {
    smiv2:oid "1.3.6.1.4.1.4491.2.1.8";
  }

  smiv2:alias "docsL2vpnMIBNotifications" {
    smiv2:oid "1.3.6.1.4.1.4491.2.1.8.0";
  }

  smiv2:alias "docsL2vpnMIBObjects" {
    smiv2:oid "1.3.6.1.4.1.4491.2.1.8.1";
  }

  smiv2:alias "docsL2vpnConformance" {
    smiv2:oid "1.3.6.1.4.1.4491.2.1.8.2";
  }

  smiv2:alias "docsL2vpnCompliances" {
    smiv2:oid "1.3.6.1.4.1.4491.2.1.8.2.1";
  }

  smiv2:alias "docsL2vpnGroups" {
    smiv2:oid "1.3.6.1.4.1.4491.2.1.8.2.2";
  }

}
