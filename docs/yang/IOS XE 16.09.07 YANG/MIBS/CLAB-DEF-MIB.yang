/*
 * Generated by confdc --mib2yang-std
 * Source: mgmt/dmi/model/mib/src/CLAB-DEF-MIB.mib
 */
/*
 * This YANG module has been generated by smidump 0.5.0:
 *
 *      smidump -f yang CLAB-DEF-MIB
 *
 * Do not edit. Edit the source file instead!
 */

module CLAB-DEF-MIB {

  namespace "urn:ietf:params:xml:ns:yang:smiv2:CLAB-DEF-MIB";
  prefix CLAB-DEF-MIB;

  import DOCS-IETF-BPI2-MIB {
    prefix "docs-ietf";
  }

  import ietf-yang-smiv2 {
    prefix "smiv2";
  }

  organization
   "Cable Television Laboratories, Inc.";

  contact
   "Postal: Cable Television Laboratories
    858 Coal Creek Circle
    Louisville, Colorado 80027-9750
    U.S.A.
    Phone:  +1 303-661-9100
    Fax:    +1 303-661-9199
    E-mail: mibs@cablelabs.com";

  description
   "This MIB module defines the namespace organization for the
    CableLabs enterprise OID registry.
    
    Copyright 1999-2012 Cable Television Laboratories, Inc.
    All rights reserved.";

  revision 2012-08-09 {
    description
     "Revised Version includes ECN MIB-CLABDEF-N-12.0113-1
      and published as CL-SP-MIB-CLABDEF-I10-120809";
  }

  revision 2011-02-10 {
    description
     "Revised Version includes ECN MIB-CLABDEF-N-10.0092-1
      and published as CL-SP-MIB-CLABDEF-I09-110210";
  }

  revision 2009-08-11 {
    description
     "Revised Version includes ECN MIB-CLABDEF-N-08.0039-2
      and published as CL-SP-MIB-CLABDEF-I08-090811";
  }

  revision 2008-03-06 {
    description
     "Revised Version includes ECN MIB-CLABDEF-N-07.0032-4 and
      published as CL-SP-MIB-CLABDEF-I07.";
  }

  revision 2007-01-19 {
    description
     "This revision published as CL-SP-MIB-CLABDEF-I06.";
  }

  revision 2005-04-08 {
    description
     "This revision published as CL-SP-MIB-CLABDEF-I05.";
  }

  typedef DocsL2vpnIfList {
    type bits {
      bit eCm {
        position "0";
      }
      bit cmci {
        position "1";
      }
      bit docsCableMacLayer {
        position "2";
      }
      bit docsCableDownstream {
        position "3";
      }
      bit docsCableUpstream {
        position "4";
      }
      bit eMta {
        position "16";
      }
      bit eStbIp {
        position "17";
      }
      bit eStbDsg {
        position "18";
      }
    }
    description
     "An object of this type indicates a set of CM 
      MAC bridge interfaces, encoded as a BITS syntax with a ?1?
      Bit for each interface included in the set.
      
      Bit position eCM(0) represents a conceptual interface to 
      the internal 'self' host MAC of the eCM itself. All other 
      bit positions K correspond to CM MAC bridge port interface
      index with ifIndex value K. 
      
      A BITS object is encoded as an OCTET STRING, which may have
      length zero. Bit position 0 is encoded in the most
      significant bit of the first octet, proceeding to 
      bit position 7 in the least significant bit. Bit position 8
      is encoded in the most significant bit of the second octet,
      and so on.
      
      In a CM, ifIndex value 1 corresponds to the primary CPE 
      interface. In CableHome devices, this interface is assigned
      to the embedded Portal Services (ePS) host interface, which
      provides a portal to the primary physical CPE interface. 
      In many contexts of a DocsL2VpnIfList, a '1' in bit 
      position 1 corresponds to 'any' or 'all' CPE interfaces 
      when the CM contains more than one CPE interface. 
      
      ifIndex value 2 corresponds to the docsCableMacLayer 
      RF MAC interface. 
      
      ifIndex values 3 and 4 correspond to the 
      docsCableDownstream and docsCableUpstream interfaces, 
      respectively, which are not separate MAC bridge port 
      interfaces. Bit positions 3 and 4 are unused in this type;
      they must be saved and reported as configured, but 
      otherwise ignored. 
      
      ifIndex values 5 through 15 are reserved for individual
      CPE interfaces for devices that implement more than one
      CPE interface. In such devices, DocsL2vpnIfList bit 
      position 1 corresponds to the set of all CPE interfaces.
      A CM with more than one CPE interface MAY assign a 
      DocsL2vpnIfList bit position within the range of 5..15 to
      refer to the single primary CPE interface.
      
      ifIndex value 16 is assigned to any embedded Multimedia 
      Terminal Adapter (eMTA) as defined by PacketCable.
      
      ifIndex value 17 is assigned to the IP management host 
      interface of an embedded Set Top Box (eSTB). ifIndex value 
      18 is reserved for the DOCSIS Set-top Gateway (DSG) traffic
      delivered to an eSTB. 
      
      ifIndex values 19 through 31 are
      reserved for future defined embedded Service Application.";
  }


  container CLAB-DEF-MIB {
    config false;

    container clabSecCertObject {
      smiv2:oid "1.3.6.1.4.1.4491.3.1";

      leaf clabSrvcPrvdrRootCACert {
        type docs-ietf:DocsX509ASN1DEREncodedCertificate;
        description
         "The X509 DER-encoded CableLabs Service Provider Root CA
          Certificate.";
        reference
         "CableLabs CableHome Specification;
          CableLabs PacketCable Security Specification.";
        smiv2:max-access "read-only";
        smiv2:oid "1.3.6.1.4.1.4491.3.1.1";
      }

      leaf clabCVCRootCACert {
        type docs-ietf:DocsX509ASN1DEREncodedCertificate;
        description
         "The X509 DER-encoded CableLabs CVC Root CA Certificate.";
        reference
         "CableLabs CableHome Specification;
          CableLabs PacketCable Security Specification.";
        smiv2:max-access "read-only";
        smiv2:oid "1.3.6.1.4.1.4491.3.1.2";
      }

      leaf clabCVCCACert {
        type docs-ietf:DocsX509ASN1DEREncodedCertificate;
        description
         "The X509 DER-encoded CableLabs CVC CA Certificate.";
        reference
         "CableLabs CableHome Specification;
          CableLabs PacketCable Security Specification.";
        smiv2:max-access "read-only";
        smiv2:oid "1.3.6.1.4.1.4491.3.1.3";
      }

      leaf clabMfgCVCCert {
        type docs-ietf:DocsX509ASN1DEREncodedCertificate;
        description
         "The X509 DER-encoded Manufacturer CVC Certificate.";
        reference
         "CableLabs CableHome Specification;
          CableLabs PacketCable Security Specification.";
        smiv2:max-access "read-only";
        smiv2:oid "1.3.6.1.4.1.4491.3.1.4";
      }

      leaf clabMfgCACert {
        type docs-ietf:DocsX509ASN1DEREncodedCertificate;
        description
         "The X509 DER-encoded Manufacturer CA Certificate.";
        reference
         "CableLabs CableHome Specification;
          CableLabs PacketCable Security Specification.";
        smiv2:max-access "read-only";
        smiv2:oid "1.3.6.1.4.1.4491.3.1.5";
      }
    }
  }

  smiv2:alias "cableLabs" {
    smiv2:oid "1.3.6.1.4.1.4491";
  }

  smiv2:alias "clabFunction" {
    smiv2:oid "1.3.6.1.4.1.4491.1";
  }

  smiv2:alias "clabFuncMib2" {
    smiv2:oid "1.3.6.1.4.1.4491.1.1";
  }

  smiv2:alias "clabFuncProprietary" {
    smiv2:oid "1.3.6.1.4.1.4491.1.2";
  }

  smiv2:alias "clabProject" {
    smiv2:oid "1.3.6.1.4.1.4491.2";
  }

  smiv2:alias "clabProjDocsis" {
    smiv2:oid "1.3.6.1.4.1.4491.2.1";
  }

  smiv2:alias "clabProjPacketCable" {
    smiv2:oid "1.3.6.1.4.1.4491.2.2";
  }

  smiv2:alias "pktcSecurity" {
    smiv2:oid "1.3.6.1.4.1.4491.2.2.4";
  }

  smiv2:alias "pktcLawfulIntercept" {
    smiv2:oid "1.3.6.1.4.1.4491.2.2.5";
  }

  smiv2:alias "pktcEnhancements" {
    smiv2:oid "1.3.6.1.4.1.4491.2.2.6";
  }

  smiv2:alias "pktcPACMMibs" {
    smiv2:oid "1.3.6.1.4.1.4491.2.2.7";
  }

  smiv2:alias "pktcPACMTC" {
    smiv2:oid "1.3.6.1.4.1.4491.2.2.7.1";
  }

  smiv2:alias "pktcPACMUEMib" {
    smiv2:oid "1.3.6.1.4.1.4491.2.2.7.2";
  }

  smiv2:alias "pktcPACMUserMib" {
    smiv2:oid "1.3.6.1.4.1.4491.2.2.7.3";
  }

  smiv2:alias "pktcApplicationMibs" {
    smiv2:oid "1.3.6.1.4.1.4491.2.2.8";
  }

  smiv2:alias "pktcSupportMibs" {
    smiv2:oid "1.3.6.1.4.1.4491.2.2.9";
  }

  smiv2:alias "pktcESSupportMibs" {
    smiv2:oid "1.3.6.1.4.1.4491.2.2.9.1";
  }

  smiv2:alias "pktcEUEMibs" {
    smiv2:oid "1.3.6.1.4.1.4491.2.2.10";
  }

  smiv2:alias "pktcEUEDeviceMibs" {
    smiv2:oid "1.3.6.1.4.1.4491.2.2.10.1";
  }

  smiv2:alias "pktcSMAMibs" {
    smiv2:oid "1.3.6.1.4.1.4491.2.2.11";
  }

  smiv2:alias "clabProjOpenCable" {
    smiv2:oid "1.3.6.1.4.1.4491.2.3";
  }

  smiv2:alias "clabProjCableHome" {
    smiv2:oid "1.3.6.1.4.1.4491.2.4";
  }

  smiv2:alias "clabProjWireless" {
    smiv2:oid "1.3.6.1.4.1.4491.2.5";
  }

  smiv2:alias "clabSecurity" {
    smiv2:oid "1.3.6.1.4.1.4491.3";
  }

  smiv2:alias "clabSecCertObject" {
    smiv2:oid "1.3.6.1.4.1.4491.3.1";
  }

  smiv2:alias "clabSecOlcaObject" {
    smiv2:oid "1.3.6.1.4.1.4491.3.2";
  }

  smiv2:alias "clabCommonMibs" {
    smiv2:oid "1.3.6.1.4.1.4491.4";
  }

  smiv2:alias "clabUpsMib" {
    smiv2:oid "1.3.6.1.4.1.4491.4.1";
  }

  smiv2:alias "clabTopoMib" {
    smiv2:oid "1.3.6.1.4.1.4491.4.2";
  }

}
