/*
 * Generated by confdc --mib2yang-std
 * Source: mgmt/dmi/model/mib/src/CISCO-SONET-MIB.mib
 */
/*
 * This YANG module has been generated by smidump 0.5.0:
 *
 *      smidump -f yang CISCO-SONET-MIB
 *
 * Do not edit. Edit the source file instead!
 */

module CISCO-SONET-MIB {

  namespace "urn:ietf:params:xml:ns:yang:smiv2:CISCO-SONET-MIB";
  prefix CISCO-SONET-MIB;

  import IF-MIB {
    prefix "if-mib";
  }

  import SONET-MIB {
    prefix "sonet-mib";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-wanatm@cisco.com";

  description
   "The MIB module to describe SONET/SDH interfaces
    objects. This is an extension to the standard SONET 
    MIB(RFC 2558).";

  revision 2003-03-07 {
    description
     "(1) Added enumerations e3(8) and vtStructured(9) 
      in object cspSonetPathPayload.
      (2) Added table csAu4Tug3Config to configure the  
      VC(Virtual Container) related properties of a 
      TUG-3 within a AU-4 paths.";
  }

  revision 2002-06-14 {
    description
     "(1)Added following objects to cspConfigTable:
      cspTributaryMappingType
      cspSignallingTransportMode
      cspTributaryGroupingType
      (2)Added an optional ciscoSonetPathConfMIBGroup1 
      for the above objects.";
  }

  revision 2002-05-22 {
    description
     "(1) Added cspConfigTable which augments 
      sonetPathCurrentTable.
      (2) Added the Notifications - 
            ciscoSonetSectionStatusChange,
            ciscoSonetLineStatusChange,
            ciscoSonetPathStatusChange,
            ciscoSonetVTStatusChange
      and the object - 
            csNotificationsEnabled.
      (3) Changed the Module-Compliance and made 
      ciscoSonetStatsMIBGroup and
      ciscoSonetApsMIBGroup1 groups as optional";
  }

  revision 2001-10-17 {
    description
     "(1) Added CsApsLineFailureCode,
      CsApsLineFailureStatus, and
      CsApsLineSwitchReason TEXTUAL-CONVENTION.
      (2) Added csApsSwitchReason, csApsFailureStatus,
      and csApsPrimarySection columnar objects to
      CsApsConfigEntry.
      (3) Added csApsModeMismatch enumeration to
      CsApsLineFailureCode.
      (4) Added csApsNoSwitch enumeration to
      CsApsLineSwitchReason.
      (5) Changed descriptions for csApsWorkingIndex,
      and csApsProtectionIndex specifically related
      to ITU G.783 AnnexB protocol support.
      (6) Add objects csConfigRDIVType and csConfigRDIPType in table
      csConfigTable.
      (7) Add enum sonetSts3(9) for obj csConfigType.
      (8) Add table csVTConfigTable augmenting the table csConfigTable.
      The table csVTVonfigTable contains the following objects:
                csTributaryType
                csTributaryMappingType
                csTributaryFramingType
                csSignallingTransportMode
                csTributaryGroupingType";
  }

  revision 2000-07-12 {
    description
     "Made following changes
      
      (1) Added enumeration csApsNone(3) to 
          csApsActiveLine object and updated the 
          description.
      (2) Added enumerations sonetSts192c(7) and 
          sonetStm64(8) to csConfigType object and 
          updated the descripton.
      (3) Fixed description of csConfigType object.";
  }

  revision 1999-03-08 {
    description
     "Initial version of the MIB.";
  }

  typedef CsApsLineFailureCode {
    type enumeration {
      enum "csApsChannelMismatch" {
        value "1";
      }
      enum "csApsProtectionByteFail" {
        value "2";
      }
      enum "csApsFEProtectionFailure" {
        value "3";
      }
      enum "csApsModeMismatch" {
        value "4";
      }
    }
    description
     "The Sonet APS line failure code - this is the failure
      encountered by the APS line.
      
          csApsChannelMismatch:     Transmitted K1 byte and
                                    received K2 byte do not match.
          csApsProtectionByteFail:  It could mean either K1 byte
                                    with invalid type of switch
                                    request bits was received, or,
                                    priority of received K1 byte
                                    is lower than the transmitted
                                    K1 byte.
          csApsFEProtectionFailure: Remote end error detected.
          csApsModeMismatch:        APS architecture mode mismatch.";
  }

  typedef CsApsLineFailureStatus {
    type bits {
      bit noApsLineFailure {
        position "0";
      }
      bit csApsChannelMismatchBit {
        position "1";
      }
      bit csApsProtectionByteFailBit {
        position "2";
      }
      bit csApsFEProtectionFailureBit {
        position "3";
      }
      bit csApsModeMismatchBit {
        position "4";
      }
    }
    description
     "The indication of the APS line failure status with a bit
      map representing multiple failures. 
      
         noApsLineFailure bit indicates current failure status.
           This bit should be set ONLY if no other bit is set.
      
         csApsChannelMismatchBit is set when the APS line is in
           csApsChannelMismatch.
      
         csApsProtectionByteFailBit is set when the APS line is
           in csApsProtectionByteFail failure code.
      
         csApsFEProtectionFailureBit is set when the APS line is
           in csApsFEProtectionFailure.
      
         csApsModeMismatchBit is set when the APS line is in 
           csApsModeMismatch.";
  }

  typedef CsApsLineSwitchReason {
    type enumeration {
      enum "csApsOther" {
        value "1";
      }
      enum "csApsRevertive" {
        value "2";
      }
      enum "csApsManual" {
        value "3";
      }
      enum "csApsSignalDefectLow" {
        value "4";
      }
      enum "csApsSignalDefectHigh" {
        value "5";
      }
      enum "csApsSignalFailureLow" {
        value "6";
      }
      enum "csApsSignalFailureHigh" {
        value "7";
      }
      enum "csApsForceSwitch" {
        value "8";
      }
      enum "csApsLockOut" {
        value "9";
      }
      enum "csApsNoSwitch" {
        value "10";
      }
    }
    description
     "The reason why APS switch happened. When the working
      line on one end fails, its other end is told to do
      an APS switch. The following options in the increasing
      order of priority indicate what type of switch request
      it is.
      
        csApsRevertive : Switch back to working line after the
          Wait-to-Restore interval is over, and failures are
          cleared. It is the lowest priority.
        csApsManual : Manual switch causes APS switch unless a
          request of equal or higher priority is in effect.
        csApsSignalDefectLow : Switch happened because threshold
          for 'csApsSigFaultBER' was exceeded.
        csApsSignalDefectHigh : Same as above, but higher priority.
        csApsSignalFailureLow : Switch happened because threshold
          for 'csApsSigDegradeBER' was exceeded.
        csApsSignalFailureHigh : Same as above, but higher
          priority.
        csApsForceSwitch : Forced switch forces hardware to switch
          the active line even if the other line (could be
          working line or protection line) is in alarm.
        csApsLockOut : This is the highest priority switch. This
          will override all other requests.
        csApsNoSwitch : This is a state when no switch happens.";
  }


  container CISCO-SONET-MIB {
    config false;

    container csApsConfig {
      smiv2:oid "1.3.6.1.4.1.9.9.126.1.2";

      leaf csApsLineFailureCode {
        type CISCO-SONET-MIB:CsApsLineFailureCode;
        description
         "The object indicates the APS line failure code. This is the
          failure encountered by the APS line.
          Refer to CsApsLineFailureCode TC for failure code definitions.
          The object is used for notifications.";
        reference
         "GR-253-CORE, G.783";
        smiv2:max-access "read-only";
        smiv2:oid "1.3.6.1.4.1.9.9.126.1.2.2";
      }

      leaf csApsLineSwitchReason {
        type CISCO-SONET-MIB:CsApsLineSwitchReason;
        description
         "This object indicates the APS line switch reason.
          When the working line on one end fails, its other end
          is told to do an APS switch. 
          Refer to CsApsLineSwitchReason TC for more information.
          The object is used for notifications.";
        smiv2:max-access "read-only";
        smiv2:oid "1.3.6.1.4.1.9.9.126.1.2.3";
      }
    }

    container csNotifications {
      smiv2:oid "1.3.6.1.4.1.9.9.126.1.8";

      leaf csNotificationsEnabled {
        type boolean;
        description
         "This object controls if the generation of 
          ciscoSonetSectionStatusChange, ciscoSonetLineStatusChange, 
          ciscoSonetPathStatusChange and ciscoSonetVTStatusChange
          notifications is enabled. If the value of this object
          is 'true(1)', then all notifications in this MIB are
          enabled; otherwise they are disabled.";
        smiv2:defval "false";
        smiv2:max-access "read-write";
        smiv2:oid "1.3.6.1.4.1.9.9.126.1.8.1";
      }
    }

    container csConfigTable {
      description
       "The SONET/SDH configuration table. This table has objects 
        for configuring sonet lines.";
      smiv2:oid "1.3.6.1.4.1.9.9.126.1.1.1";

      list csConfigEntry {
        key "ifIndex";
        description
         "An entry in the table. There is an entry for each SONET line 
          in the table. Entries are automatically created for an 
          ifType value of sonet(39). 'ifAdminStatus' from the ifTable 
          must be used to enable or disable a line. A line is in 
          disabled(down) state unless provisioned 'up' using 
          'ifAdminStatus'.";
        smiv2:oid "1.3.6.1.4.1.9.9.126.1.1.1.1";

        leaf ifIndex {
          type leafref {
            path "/if-mib:IF-MIB/if-mib:ifTable/if-mib:ifEntry/if-mib:ifIndex";
          }
        }

        leaf csConfigLoopbackType {
          type enumeration {
            enum "noLoopback" {
              value "1";
            }
            enum "lineLocal" {
              value "2";
            }
            enum "lineRemote" {
              value "3";
            }
          }
          description
           "This object specifies the desired loopback mode
            configuration of the SONET line.
            The possible values of this objects are follows:
            
            noLoopback :  
                    Not in the loopback state.  
            lineLocal : 
                    The signal transmitted from this interface
                    is connected to the associated incoming
                    receiver. This ensures that the SONET frame
                    transmitted from the interface is received back
                    at the interface.
            lineRemote :
                    The signal received at the interface is looped
                    back out to the associated transmitter.
                    This ensures that the remote equipment that
                    originated the signal receives it back. The 
                    signal may undergo degradation as a result of
                    the characteristics of the transmission 
                    medium.";
          smiv2:defval "noLoopback";
          smiv2:max-access "read-write";
          smiv2:oid "1.3.6.1.4.1.9.9.126.1.1.1.1.1";
        }

        leaf csConfigXmtClockSource {
          type enumeration {
            enum "loopTiming" {
              value "1";
            }
            enum "localTiming" {
              value "2";
            }
          }
          description
           "Specifies the source of the transmit clock.
            
            loopTiming: indicates that the recovered receive 
                        clock is used as the transmit clock.
            
            localTiming: indicates that a local clock source is
                         used or that an external clock is 
                         attached to the box containing the 
                         interface. ";
          smiv2:defval "localTiming";
          smiv2:max-access "read-write";
          smiv2:oid "1.3.6.1.4.1.9.9.126.1.1.1.1.2";
        }

        leaf csConfigFrameScramble {
          type enumeration {
            enum "disabled" {
              value "1";
            }
            enum "enabled" {
              value "2";
            }
          }
          description
           "This object is used to disable or enable the Scrambling
            option in SONET line.";
          reference
           "GR-253-CORE Issue 3, September 2000: Section 5.1.3.";
          smiv2:defval "enabled";
          smiv2:max-access "read-write";
          smiv2:oid "1.3.6.1.4.1.9.9.126.1.1.1.1.3";
        }

        leaf csConfigType {
          type enumeration {
            enum "sonetSts3c" {
              value "1";
            }
            enum "sonetStm1" {
              value "2";
            }
            enum "sonetSts12c" {
              value "3";
            }
            enum "sonetStm4" {
              value "4";
            }
            enum "sonetSts48c" {
              value "5";
            }
            enum "sonetStm16" {
              value "6";
            }
            enum "sonetSts192c" {
              value "7";
            }
            enum "sonetStm64" {
              value "8";
            }
            enum "sonetSts3" {
              value "9";
            }
          }
          description
           "This object represents the configured line type.
            Sts is SONET format. Stm is SDH format. 
                sonetSts3c   : OC3 concatenated
                sonetStm1    : European standard OC3
                sonetSts12c  : OC12 concatenated
                sonetStm4    : European standard OC12
                sonetSts48c  : OC48 concatenated
                sonetStm16   : European standard OC48 
                sonetSts192c : OC-192 concatenated
                sonetStm64   : European standard OC-192
                sonetSts3    : OC3 (unconcatenated)
                ";
          smiv2:max-access "read-only";
          smiv2:oid "1.3.6.1.4.1.9.9.126.1.1.1.1.4";
        }

        leaf csConfigRDIVType {
          type enumeration {
            enum "onebit" {
              value "1";
            }
            enum "threebit" {
              value "3";
            }
          }
          description
           "This object specifies the type of RDI-V (Remote Defect
            Indication - Virtual Tributary/Container) sent by this 
            Network Element (NE) to the remote Network Element.
            
                  onebit     : use 1 bit RDI-V
                  threebit   : use 3 bit enhanced RDI-V.
            
            Default is onebit.";
          smiv2:defval "onebit";
          smiv2:max-access "read-write";
          smiv2:oid "1.3.6.1.4.1.9.9.126.1.1.1.1.5";
        }

        leaf csConfigRDIPType {
          type enumeration {
            enum "onebit" {
              value "1";
            }
            enum "threebit" {
              value "3";
            }
          }
          description
           "This object represents the type of RDI-P (Remote Defect
            Indication - Path) sent by this Network Element (NE)
            to remote Network Element.
            
                  onebit     : use 1 bit RDI-P
                  threebit   : use 3 bit enhanced RDI-P.
            
            Default is onebit.";
          smiv2:defval "onebit";
          smiv2:max-access "read-write";
          smiv2:oid "1.3.6.1.4.1.9.9.126.1.1.1.1.6";
        }
      }
    }

    container csApsConfigTable {
      description
       "This table contains objects to configure APS 
        (Automatic Protection Switching) feature in a SONET 
        Line. APS is the ability to configure a pair of SONET 
        lines for redundancy so that the hardware will 
        automatically switch the active line from working line
        to the protection line or vice versa, within 60ms, 
        when the active line fails.";
      smiv2:oid "1.3.6.1.4.1.9.9.126.1.2.1";

      list csApsConfigEntry {
        key "csApsWorkingIndex";
        description
         "An entry is created when an APS pair is configured.
          To create an entry, the following objects must be 
          specified:
          csApsWorkingIndex, csApsProtectionIndex, csApsEnable,  
          csApsArchMode. The protection line must not be active,
          i.e, ifAdminStatus must be 'down',  while configuring 
          APS. An entry is created by setting the value of 
          'csApsEnable' to csApsEnabled (2) and deleted by 
          setting it to csApsDisabled (1). Once a line is 
          configured as working line or protection line, it 
          remains in that role until APS is disabled on that 
          sonet line pair. It remains in the  working/protection 
          role even after the card is reset.";
        smiv2:oid "1.3.6.1.4.1.9.9.126.1.2.1.1";

        leaf csApsWorkingIndex {
          type if-mib:InterfaceIndex;
          description
           "When a pair of APS lines is configured, one line has
            to be the working line, which is the primary line,
            and the other has to be the protection line, which
            is the backup line. This object refers to the working line
            in the APS pair. For G.783 AnnexB, this index refers to
            Working Section 1.";
          reference
           "GR-253-CORE, G.783 AnnexB";
          smiv2:max-access "not-accessible";
          smiv2:oid "1.3.6.1.4.1.9.9.126.1.2.1.1.1";
        }

        leaf csApsProtectionIndex {
          type if-mib:InterfaceIndex;
          description
           "The protection line indicates that it will become
            the active line when an APS switch occurs (APS switch
            could occur because of a failure on the working line).
            For G.783 AnnexB, This index refers to Working Section
            2.";
          reference
           "GR-253-CORE, G.783 AnnexB";
          smiv2:max-access "read-write";
          smiv2:oid "1.3.6.1.4.1.9.9.126.1.2.1.1.2";
        }

        leaf csApsEnable {
          type enumeration {
            enum "csApsDisabled" {
              value "1";
            }
            enum "csApsEnabled" {
              value "2";
            }
          }
          description
           "This object is used to enable or disable the APS feature
            on the working/protection line pairs. When enabled,
            the hardware will automatically switch the active line 
            from the working line to the protection line within 60ms,
            or vice versa.";
          smiv2:max-access "read-write";
          smiv2:oid "1.3.6.1.4.1.9.9.126.1.2.1.1.3";
        }

        leaf csApsArchMode {
          type enumeration {
            enum "onePlusOne" {
              value "1";
            }
            enum "oneToOne" {
              value "2";
            }
            enum "anexBOnePlusOne" {
              value "3";
            }
            enum "ycableOnePlusOneNok1k2" {
              value "4";
            }
            enum "straightOnePlusOneNok1k2" {
              value "5";
            }
          }
          description
           "This object is used to configure APS architecture mode
            on the working/protection line pairs.
            
             All of the following are supported on single slot.
             oneToOne(2) is not  supported across 2 slots,i.e. the 
             working and protection slot numbers must be the same in 
             oneToOne(2).
            
             onePlusOne : This can be supported on the same card
             and across 2 cards.
             This mode means that the transmit and receive signals
             go only over the active line(which could be working or 
             protection line). (straight cable implied)
            
             oneToOne : This is supported only on the same card
             This mode means that the transmit and receive signals
             go over the working and protection lines.
             (straight cable implied)
            
             anexBOnePlusOne : This can be supported on the same card
             and across 2 cards.
             This mode is like the onePlusOne mode, except that the
             'csApsDirection' can only be bi-directional.
             (straight cable implied)
            
             ycableOnePlusOneNok1k2: With Y-cable ignore K1K2 bytes.
             This mode is the Y-cable redundancy mode.
            
             straightOnePlusOneNok1k2 : With straight cable, ignore 
                                        K1K2 bytes. This mode is like
                                        onePlusOne, but with K1, K2 
                                        bytes ignored.";
          smiv2:max-access "read-write";
          smiv2:oid "1.3.6.1.4.1.9.9.126.1.2.1.1.4";
        }

        leaf csApsActiveLine {
          type enumeration {
            enum "csApsWorkingLine" {
              value "1";
            }
            enum "csApsProtectionLine" {
              value "2";
            }
            enum "csApsNone" {
              value "3";
            }
          }
          description
           "This object indicates which line is currently active. 
            It could be the working line(Section 1 for Annex B),
            the protection line(Section 2 for Annex B) or none
            if neither working nor protection line is active. 
            This object reflects the status of receive direction.";
          reference
           "GR-253-CORE, G.783 AnnexB";
          smiv2:max-access "read-only";
          smiv2:oid "1.3.6.1.4.1.9.9.126.1.2.1.1.5";
        }

        leaf csApsSigFaultBER {
          type uint32 {
            range "3..5";
          }
          description
           "This object contains the Bit Error Rate threshold for
            Signal Fault detection on the working line. Once this
            threshold is exceeded, an APS switch will occur.
            This value is 10 to the -n, where n is between 3 and 5.";
          smiv2:defval "3";
          smiv2:max-access "read-write";
          smiv2:oid "1.3.6.1.4.1.9.9.126.1.2.1.1.6";
        }

        leaf csApsSigDegradeBER {
          type uint32 {
            range "5..9";
          }
          description
           "This object contains the Bit Error Rate threshold for
            Signal Degrade detection on the working line. Once this
            threshold is exceeded, an APS switch will occur.
            This value is 10 to -n where n is between 5 and 9.";
          smiv2:defval "5";
          smiv2:max-access "read-write";
          smiv2:oid "1.3.6.1.4.1.9.9.126.1.2.1.1.7";
        }

        leaf csApsWaitToRestore {
          type uint32 {
            range "1..12";
          }
          units "minutes";
          description
           "This object contains interval in minutes to wait 
            before attempting to switch back to working line. 
            Not applicable if the line is configured in 
            non-revertive mode, i.e. protection line will 
            continue to be active, even if failures on the 
            working line are cleared. The framer clears the 
            signal-fault and signal-degrade when APS switch 
            occurs. Please refer to 'csApsRevertive' for 
            description of non-revertive.";
          smiv2:max-access "read-write";
          smiv2:oid "1.3.6.1.4.1.9.9.126.1.2.1.1.8";
        }

        leaf csApsDirection {
          type enumeration {
            enum "uniDirectional" {
              value "1";
            }
            enum "biDirectional" {
              value "2";
            }
          }
          description
           "This object is used to configure the switching 
            direction which this APS line supports. 
            
            Unidirectional : APS switch only in one direction.
            Bidirectional  : APS switch in both ends of the line.";
          smiv2:max-access "read-write";
          smiv2:oid "1.3.6.1.4.1.9.9.126.1.2.1.1.9";
        }

        leaf csApsRevertive {
          type enumeration {
            enum "nonrevertive" {
              value "1";
            }
            enum "revertive" {
              value "2";
            }
          }
          description
           "This object is used to configure the APS revertive or
            nonrevertive option. 
            
            revertive : 
              Will switch the working line back to active state after
              the Wait-To-restore interval has expired and the 
              working line Signal-Fault/Signal-Degrade has been 
              cleared. Please refer to 'csApsWaitToRestore' for 
              description of Wait-To-Restore interval.
            nonrevertive : 
              The  protection line continues to be the active line,
              The active line does not switch to the working line.";
          smiv2:max-access "read-write";
          smiv2:oid "1.3.6.1.4.1.9.9.126.1.2.1.1.10";
        }

        leaf csApsDirectionOperational {
          type enumeration {
            enum "uniDirectional" {
              value "1";
            }
            enum "biDirectional" {
              value "2";
            }
          }
          description
           "This object shows the actual APS direction that is 
            implemented on the Near End terminal. APS direction 
            configured through csApsDirection is negotiated with
            the Far End and APS direction setting acceptable to 
            both ends is operational at the Near End.";
          smiv2:max-access "read-only";
          smiv2:oid "1.3.6.1.4.1.9.9.126.1.2.1.1.11";
        }

        leaf csApsArchModeOperational {
          type enumeration {
            enum "onePlusOne" {
              value "1";
            }
            enum "oneToOne" {
              value "2";
            }
            enum "anexBOnePlusOne" {
              value "3";
            }
            enum "ycableOnePlusOneNok1k2" {
              value "4";
            }
            enum "straightOnePlusOneNok1k2" {
              value "5";
            }
          }
          description
           "This object shows the actual APS architecture mode that
            is implemented on the Near End terminal. APS architecture
            mode configured through csApsArchMode object is 
            negotiated with the Far End through APS channel. 
            Architecture mode acceptable to both the Near End and 
            the Far End terminals is then operational at the Near 
            End. This value can be different than the APS 
            Architecture mode configured.";
          smiv2:max-access "read-only";
          smiv2:oid "1.3.6.1.4.1.9.9.126.1.2.1.1.12";
        }

        leaf csApsChannelProtocol {
          type enumeration {
            enum "bellcore" {
              value "1";
            }
            enum "itu" {
              value "2";
            }
          }
          description
           "This object allows to configure APS channel protocol to 
            be implemented at Near End terminal.
            
            K1 and K2 overhead bytes in a SONET signal are used as
            an APS channel.
            This channel is used to carry APS protocol.
            
            Possible values:
            bellcore(1) : Implements APS channel protocol as defined
                          in bellcore document GR-253-CORE.
            itu(2) : Implements APS channel protocol as defined in 
                     ITU document G.783.";
          reference
           "GR-253-CORE, G.783";
          smiv2:max-access "read-write";
          smiv2:oid "1.3.6.1.4.1.9.9.126.1.2.1.1.13";
        }

        leaf csApsFailureStatus {
          type CISCO-SONET-MIB:CsApsLineFailureStatus;
          description
           "This object indicates APS line failure status.";
          reference
           "GR-253-CORE, G.783";
          smiv2:max-access "read-only";
          smiv2:oid "1.3.6.1.4.1.9.9.126.1.2.1.1.14";
        }

        leaf csApsSwitchReason {
          type CISCO-SONET-MIB:CsApsLineSwitchReason;
          description
           "This object indicates APS line switch reason.";
          reference
           "GR-253-CORE, G.783";
          smiv2:max-access "read-only";
          smiv2:oid "1.3.6.1.4.1.9.9.126.1.2.1.1.15";
        }

        leaf csApsPrimarySection {
          type enumeration {
            enum "workingSection1" {
              value "1";
            }
            enum "workingSection2" {
              value "2";
            }
            enum "none" {
              value "3";
            }
          }
          description
           "This object indicates which working section is the APS
            primary section. In G.783 AnnexB, the K1/K2 Bytes are
            received on the secondary Section. All the Switch
            Requests are for a switch from the primary section to
            the secondary section. The object csApsActiveline will
            indicate which section is currently carrying the
            traffic.  Once the switch request clears normally,
            traffic is maintained on the section to which it was
            switched by making that section the primary section. 
            
            Possible values: 
            workingSection1(1): Working Section 1 is Primary Section
            workingSection2(2): Working Section 2 is Primary Section
            none(3)           : none.";
          reference
           "G.783 AnnexB";
          smiv2:max-access "read-only";
          smiv2:oid "1.3.6.1.4.1.9.9.126.1.2.1.1.16";
        }
      }
    }

    container cssTotalTable {
      description
       "The SONET/SDH Section Total table. It contains the 
        cumulative sum of the various statistics for the 24 hour
        period preceding the current interval. The object 
        'sonetMediumValidIntervals' from RFC2558 contains the
        number of 15 minute intervals that have elapsed since
        the line is enabled. ";
      smiv2:oid "1.3.6.1.4.1.9.9.126.1.3.1";

      list cssTotalEntry {
        key "ifIndex";
        description
         "An entry in the SONET/SDH Section Total table. Entries
          are created automatically for sonet lines.";
        smiv2:oid "1.3.6.1.4.1.9.9.126.1.3.1.1";

        leaf ifIndex {
          type leafref {
            path "/if-mib:IF-MIB/if-mib:ifTable/if-mib:ifEntry/if-mib:ifIndex";
          }
        }

        leaf cssTotalESs {
          type yang:gauge32;
          units "errored seconds";
          description
           "The number of Errored Seconds encountered by a SONET/SDH
            Section in the last 24 hours.";
          reference
           " RFC2558 ";
          smiv2:max-access "read-only";
          smiv2:oid "1.3.6.1.4.1.9.9.126.1.3.1.1.1";
        }

        leaf cssTotalSESs {
          type yang:gauge32;
          units "severely errored seconds";
          description
           "The number of Severely Errored Seconds encountered by a 
            SONET/SDH Section in the last 24 hours.";
          reference
           " RFC2558 ";
          smiv2:max-access "read-only";
          smiv2:oid "1.3.6.1.4.1.9.9.126.1.3.1.1.2";
        }

        leaf cssTotalSEFSs {
          type yang:gauge32;
          units "severely errored framing seconds";
          description
           "The number of Severely Errored Framing Seconds 
            encountered by a SONET/SDH Section in the last 24 hours.";
          reference
           " RFC2558 ";
          smiv2:max-access "read-only";
          smiv2:oid "1.3.6.1.4.1.9.9.126.1.3.1.1.3";
        }

        leaf cssTotalCVs {
          type yang:gauge32;
          units "coding violations";
          description
           "The number of Coding Violations encountered by a 
            SONET/SDH Section in the last 24 hours.";
          reference
           " RFC2558 ";
          smiv2:max-access "read-only";
          smiv2:oid "1.3.6.1.4.1.9.9.126.1.3.1.1.4";
        }
      }
    }

    container cssTraceTable {
      description
       "The SONET/SDH Section Trace table. This table contains 
        objects for tracing the sonet section.";
      smiv2:oid "1.3.6.1.4.1.9.9.126.1.3.2";

      list cssTraceEntry {
        key "ifIndex";
        description
         "An entry in the trace table. Entries exist for active sonet
          lines. The objects in this table are used to verify 
          continued connection between the two ends of the line.";
        smiv2:oid "1.3.6.1.4.1.9.9.126.1.3.2.1";

        leaf ifIndex {
          type leafref {
            path "/if-mib:IF-MIB/if-mib:ifTable/if-mib:ifEntry/if-mib:ifIndex";
          }
        }

        leaf cssTraceToTransmit {
          type binary {
            length "0|16|64";
          }
          description
           "Sonet Section Trace To Transmit. This is string that
            is transmitted to perform Sonet section trace 
            diagnostics. The trace string is  repetitively 
            transmited so that a trace receiving terminal can 
            verify its continued connection to the intended 
            transmitter. The default value is a zero-length string.
            Unless this object is set to a non-zero length string, 
            tracing will not be performed.";
          reference
           "GR-253-CORE";
          smiv2:max-access "read-write";
          smiv2:oid "1.3.6.1.4.1.9.9.126.1.3.2.1.1";
        }

        leaf cssTraceToExpect {
          type binary {
            length "0|16|64";
          }
          description
           "Sonet Section Trace To Expect. The receiving terminal 
            verifies if the incoming string matches this string. 
            The value of 'cssTraceFailure' indicates whether a 
            trace mismatch occurred. The default value is a 
            zero-length string.";
          reference
           "GR-253-CORE";
          smiv2:max-access "read-write";
          smiv2:oid "1.3.6.1.4.1.9.9.126.1.3.2.1.2";
        }

        leaf cssTraceFailure {
          type boolean;
          description
           "The value of this object is set to 'true' when Sonet 
            Section received trace does not match the 
            'cssTraceToExpect'.";
          reference
           "GR-253-CORE";
          smiv2:max-access "read-only";
          smiv2:oid "1.3.6.1.4.1.9.9.126.1.3.2.1.3";
        }

        leaf cssTraceReceived {
          type binary {
            length "0|16|64";
          }
          description
           "This object is used to view the Sonet Section Trace that 
            is received by the receiving terminal.";
          reference
           "GR-253-CORE";
          smiv2:max-access "read-only";
          smiv2:oid "1.3.6.1.4.1.9.9.126.1.3.2.1.4";
        }
      }
    }

    container cslTotalTable {
      description
       "The SONET/SDH Line Total table. It contains the 
        cumulative sum of the various statistics for the 24 
        hour period preceding the current interval. The object 
        'sonetMediumValidIntervals' from RFC2558 contains the 
        number of 15 minute intervals that have elapsed since
        the line is enabled.";
      smiv2:oid "1.3.6.1.4.1.9.9.126.1.4.1";

      list cslTotalEntry {
        key "ifIndex";
        description
         "An entry in the SONET/SDH Line Total table. Entries
          are created automatically for sonet lines.";
        smiv2:oid "1.3.6.1.4.1.9.9.126.1.4.1.1";

        leaf ifIndex {
          type leafref {
            path "/if-mib:IF-MIB/if-mib:ifTable/if-mib:ifEntry/if-mib:ifIndex";
          }
        }

        leaf cslTotalESs {
          type yang:gauge32;
          units "errored seconds";
          description
           "The number of Errored Seconds encountered by a SONET/SDH
            Line in the last 24 hours.";
          smiv2:max-access "read-only";
          smiv2:oid "1.3.6.1.4.1.9.9.126.1.4.1.1.1";
        }

        leaf cslTotalSESs {
          type yang:gauge32;
          units "severely errored seconds";
          description
           "The number of Severely Errored Seconds encountered by a 
            SONET/SDH Line in the last 24 hours.";
          reference
           " RFC2558 ";
          smiv2:max-access "read-only";
          smiv2:oid "1.3.6.1.4.1.9.9.126.1.4.1.1.2";
        }

        leaf cslTotalCVs {
          type yang:gauge32;
          units "coding violations";
          description
           "The number of Coding Violations encountered by a 
            SONET/SDH Line in the last 24 hours.";
          reference
           " RFC2558 ";
          smiv2:max-access "read-only";
          smiv2:oid "1.3.6.1.4.1.9.9.126.1.4.1.1.3";
        }

        leaf cslTotalUASs {
          type yang:gauge32;
          units "unavailable seconds";
          description
           "The number of Unavailable Seconds encountered by a 
            SONET/SDH Line in the last 24 hours.";
          reference
           " RFC2558 ";
          smiv2:max-access "read-only";
          smiv2:oid "1.3.6.1.4.1.9.9.126.1.4.1.1.4";
        }
      }
    }

    container cslFarEndTotalTable {
      description
       "The SONET/SDH Far End Line Total table. It contains the 
        cumulative sum of the various statistics for the 24 hour 
        period preceding the current interval. The object 
        'sonetMediumValidIntervals' from RFC2558 contains the 
        number of 15 minute intervals that have elapsed since the 
        line is enabled.";
      smiv2:oid "1.3.6.1.4.1.9.9.126.1.4.2";

      list cslFarEndTotalEntry {
        key "ifIndex";
        description
         "An entry in the SONET/SDH Far End Line Total table. Entries
          are created automatically for sonet lines.";
        smiv2:oid "1.3.6.1.4.1.9.9.126.1.4.2.1";

        leaf ifIndex {
          type leafref {
            path "/if-mib:IF-MIB/if-mib:ifTable/if-mib:ifEntry/if-mib:ifIndex";
          }
        }

        leaf cslFarEndTotalESs {
          type yang:gauge32;
          units "errored seconds";
          description
           "The number of Errored Seconds encountered by a SONET/SDH Far
            End Line in the last 24 hours.";
          reference
           " RFC2558 ";
          smiv2:max-access "read-only";
          smiv2:oid "1.3.6.1.4.1.9.9.126.1.4.2.1.1";
        }

        leaf cslFarEndTotalSESs {
          type yang:gauge32;
          units "severely errored seconds";
          description
           "The number of Severely Errored Seconds encountered by a 
            SONET/SDH Far End Line in the last 24 hours.";
          reference
           " RFC2558 ";
          smiv2:max-access "read-only";
          smiv2:oid "1.3.6.1.4.1.9.9.126.1.4.2.1.2";
        }

        leaf cslFarEndTotalCVs {
          type yang:gauge32;
          units "coding violations";
          description
           "The number of Coding Violations encountered by a SONET/SDH 
            Far End Line in the last 24 hours.";
          reference
           " RFC2558 ";
          smiv2:max-access "read-only";
          smiv2:oid "1.3.6.1.4.1.9.9.126.1.4.2.1.3";
        }

        leaf cslFarEndTotalUASs {
          type yang:gauge32;
          units "unavailable seconds";
          description
           "The number of Unavailable Seconds encountered by a 
            SONET/SDH Far End Line in the last 24 hours.";
          reference
           " RFC2558 ";
          smiv2:max-access "read-only";
          smiv2:oid "1.3.6.1.4.1.9.9.126.1.4.2.1.4";
        }
      }
    }

    container cspTotalTable {
      description
       "The SONET/SDH Path Total table. It contains the cumulative 
        sum of the various statistics for the 24 hour period 
        preceding the current interval.The object 
        'sonetMediumValidIntervals' from RFC2558 contains the number
        of 15 minute intervals that have elapsed since the line is 
        enabled.";
      smiv2:oid "1.3.6.1.4.1.9.9.126.1.5.1";

      list cspTotalEntry {
        key "ifIndex";
        description
         "An entry in the SONET/SDH Path Total table. Entries
          are created automatically for sonet lines.";
        smiv2:oid "1.3.6.1.4.1.9.9.126.1.5.1.1";

        leaf ifIndex {
          type leafref {
            path "/if-mib:IF-MIB/if-mib:ifTable/if-mib:ifEntry/if-mib:ifIndex";
          }
        }

        leaf cspTotalESs {
          type yang:gauge32;
          units "errored seconds";
          description
           "The number of Errored Seconds encountered by a SONET/SDH
            Path in the last 24 hours.";
          reference
           " RFC2558 ";
          smiv2:max-access "read-only";
          smiv2:oid "1.3.6.1.4.1.9.9.126.1.5.1.1.1";
        }

        leaf cspTotalSESs {
          type yang:gauge32;
          units "severely errored seconds";
          description
           "The number of Severely Errored Seconds encountered by a 
            SONET/SDH Path in the last 24 hours.";
          reference
           " RFC2558 ";
          smiv2:max-access "read-only";
          smiv2:oid "1.3.6.1.4.1.9.9.126.1.5.1.1.2";
        }

        leaf cspTotalCVs {
          type yang:gauge32;
          units "coding violations";
          description
           "The number of Coding Violations encountered by a 
            SONET/SDH Path in the last 24 hours.";
          reference
           " RFC2558 ";
          smiv2:max-access "read-only";
          smiv2:oid "1.3.6.1.4.1.9.9.126.1.5.1.1.3";
        }

        leaf cspTotalUASs {
          type yang:gauge32;
          units "unavailable seconds";
          description
           "The number of Unavailable Seconds encountered by a 
            SONET/SDH Path in the last 24 hours.";
          reference
           " RFC2558 ";
          smiv2:max-access "read-only";
          smiv2:oid "1.3.6.1.4.1.9.9.126.1.5.1.1.4";
        }
      }
    }

    container cspFarEndTotalTable {
      description
       "The SONET/SDH Far End Path Total table. Far End is the 
        remote end of the line. The table contains the cumulative
        sum of the various statistics for the 24 hour period 
        preceding the current interval. The object 
        'sonetMediumValidIntervals' from RFC2558 contains the
        number of 15 minute intervals that have elapsed since
        the line is enabled. ";
      smiv2:oid "1.3.6.1.4.1.9.9.126.1.5.2";

      list cspFarEndTotalEntry {
        key "ifIndex";
        description
         "An entry in the SONET/SDH Far End Path Total table. 
          Entries are created automatically for sonet lines.";
        smiv2:oid "1.3.6.1.4.1.9.9.126.1.5.2.1";

        leaf ifIndex {
          type leafref {
            path "/if-mib:IF-MIB/if-mib:ifTable/if-mib:ifEntry/if-mib:ifIndex";
          }
        }

        leaf cspFarEndTotalESs {
          type yang:gauge32;
          units "errored seconds";
          description
           "The number of Errored Seconds encountered by a SONET/SDH
            far end path in the last 24 hours.";
          reference
           " RFC2558 ";
          smiv2:max-access "read-only";
          smiv2:oid "1.3.6.1.4.1.9.9.126.1.5.2.1.1";
        }

        leaf cspFarEndTotalSESs {
          type yang:gauge32;
          units "severely errored seconds";
          description
           "The number of Severely Errored Seconds encountered by a 
            SONET/SDH far end path in the last 24 hours.";
          reference
           " RFC2558 ";
          smiv2:max-access "read-only";
          smiv2:oid "1.3.6.1.4.1.9.9.126.1.5.2.1.2";
        }

        leaf cspFarEndTotalCVs {
          type yang:gauge32;
          units "coding violations";
          description
           "The number of Coding Violations encountered by a 
            SONET/SDH far end path in the last 24 hours.";
          reference
           " RFC2558 ";
          smiv2:max-access "read-only";
          smiv2:oid "1.3.6.1.4.1.9.9.126.1.5.2.1.3";
        }

        leaf cspFarEndTotalUASs {
          type yang:gauge32;
          units "unavailable seconds";
          description
           "The number of Unavailable Seconds encountered by a 
            SONET/SDH far end path in the last 24 hours.";
          reference
           " RFC2558 ";
          smiv2:max-access "read-only";
          smiv2:oid "1.3.6.1.4.1.9.9.126.1.5.2.1.4";
        }
      }
    }

    container cspTraceTable {
      description
       "The SONET/SDH Path Trace table. This table contains objects 
        for tracing the sonet path.";
      smiv2:oid "1.3.6.1.4.1.9.9.126.1.5.3";

      list cspTraceEntry {
        key "ifIndex";
        description
         "An entry in the SONET/SDH Path Trace table. The entries 
          exist for active sonet lines. The objects in this table are 
          used to verify continued connection between the two ends of
          the line.";
        smiv2:oid "1.3.6.1.4.1.9.9.126.1.5.3.1";

        leaf ifIndex {
          type leafref {
            path "/if-mib:IF-MIB/if-mib:ifTable/if-mib:ifEntry/if-mib:ifIndex";
          }
        }

        leaf cspTraceToTransmit {
          type binary {
            length "0|16|64";
          }
          description
           "Sonet Path Trace To Transmit. The trace string is 
            repetitively transmited so that a trace receiving terminal 
            can verify its continued receiving terminal can verify its 
            continued connection to the intended transmitter. The 
            default value is a zero-length string. Unless this object 
            is set to a non-zero length string, tracing will not be 
            performed.";
          reference
           "GR-253-CORE";
          smiv2:max-access "read-write";
          smiv2:oid "1.3.6.1.4.1.9.9.126.1.5.3.1.1";
        }

        leaf cspTraceToExpect {
          type binary {
            length "0|16|64";
          }
          description
           "Sonet Path Trace To Expect.  The receiving terminal verifies
            if the incoming string matches this string. The value of 
            'cspTraceFailure' indicates whether a trace mismatch 
            occured. The default value is a zero-length string.";
          reference
           "GR-253-CORE";
          smiv2:max-access "read-write";
          smiv2:oid "1.3.6.1.4.1.9.9.126.1.5.3.1.2";
        }

        leaf cspTraceFailure {
          type boolean;
          description
           "The value of this object is set to 'true' when Sonet Path 
            received trace does not match the 'cspTraceToExpect'.";
          reference
           "GR-253-CORE";
          smiv2:max-access "read-only";
          smiv2:oid "1.3.6.1.4.1.9.9.126.1.5.3.1.3";
        }

        leaf cspTraceReceived {
          type binary {
            length "0|16|64";
          }
          description
           "This object is used to view the Sonet Path Trace that is
            received by the receiving terminal.";
          reference
           "GR-253-CORE";
          smiv2:max-access "read-only";
          smiv2:oid "1.3.6.1.4.1.9.9.126.1.5.3.1.4";
        }
      }
    }

    container csStatsTable {
      description
       "The SONET/SDH Section statistics table. This table 
        maintains the number of times the line encountered Loss of
        Signal(LOS), Loss of frame(LOF), Alarm Indication 
        signals(AISs), Remote failure indications(RFIs).";
      smiv2:oid "1.3.6.1.4.1.9.9.126.1.6.1";

      list csStatsEntry {
        key "ifIndex";
        description
         "An entry in the SONET/SDH statistics table. These are 
          realtime statistics for the Sonet section, line and path
          layers. The statistics are gathered for each sonet line. 
          An entry is created automatically and is indexed by 
          ifIndex.";
        smiv2:oid "1.3.6.1.4.1.9.9.126.1.6.1.1";

        leaf ifIndex {
          type leafref {
            path "/if-mib:IF-MIB/if-mib:ifTable/if-mib:ifEntry/if-mib:ifIndex";
          }
        }

        leaf cssLOSs {
          type yang:counter32;
          units "loss of signals";
          description
           "The number of Loss of signals(LOS) encountered by a 
            SONET/SDH Section. A high value for this object may 
            indicate a problem with the Sonet Section layer.";
          reference
           " RFC2558 ";
          smiv2:max-access "read-only";
          smiv2:oid "1.3.6.1.4.1.9.9.126.1.6.1.1.1";
        }

        leaf cssLOFs {
          type yang:counter32;
          units "loss of frames";
          description
           "The number of Loss of Frames (LOF) encountered by a 
            SONET/SDH Section. A high value for this object may 
            indicate a problem with the Sonet Section layer.";
          reference
           " RFC2558 ";
          smiv2:max-access "read-only";
          smiv2:oid "1.3.6.1.4.1.9.9.126.1.6.1.1.2";
        }

        leaf cslAISs {
          type yang:counter32;
          units "alarm indication signals";
          description
           "The number of alarm indication signals(AIS)  encountered by 
            a SONET/SDH Line. A high value for this object may indicate a
            problem with the Sonet Line layer.";
          reference
           " RFC2558 ";
          smiv2:max-access "read-only";
          smiv2:oid "1.3.6.1.4.1.9.9.126.1.6.1.1.3";
        }

        leaf cslRFIs {
          type yang:counter32;
          units "remote failure indications";
          description
           "The number of remote failure indications (RFI) encountered 
            by a SONET/SDH Line. A high value for this object may 
            indicate a problem with the Sonet Line layer.";
          reference
           " RFC2558 ";
          smiv2:max-access "read-only";
          smiv2:oid "1.3.6.1.4.1.9.9.126.1.6.1.1.4";
        }

        leaf cspAISs {
          type yang:counter32;
          units "alarm indication signals";
          description
           "The  number of alarm indication signals (AIS) encountered
            by a SONET/SDH Path. A high value for this object may 
            indicate a problem with the Sonet Path layer.";
          reference
           " RFC2558 ";
          smiv2:max-access "read-only";
          smiv2:oid "1.3.6.1.4.1.9.9.126.1.6.1.1.5";
        }

        leaf cspRFIs {
          type yang:counter32;
          units "remote failure indications";
          description
           "The number of  remote failure indications (RFI) 
            encountered by a SONET/SDH Path. A high value for this 
            object may indicate a problem with the Sonet Path layer.";
          reference
           " RFC2558 ";
          smiv2:max-access "read-only";
          smiv2:oid "1.3.6.1.4.1.9.9.126.1.6.1.1.6";
        }
      }
    }

    container csAu4Tug3ConfigTable {
      description
       "This table contains objects to configure the VC( Virtual
        Container) related properties of a TUG-3 within a AU-4 
        paths.
        
        This table allows creation of
        following multiplexing structure:
        STM-1/AU-4/TUG-3/TU-3/DS3
        STM-1/AU-4/TUG-3/TU-3/E3
        STM-1/AU-4/TUG-3/TUG-2/TU-11/DS1
        STM-1/AU-4/TUG-3/TUG-2/TU-12/E1
        
        Three entries are created in this table for a given AU-4 
        path when cspSonetPathPayload object is set to one of the 
        following:
            vt15vc11(4),
            vt2vc12(5),
            ds3(3),
            e3(8),
            vtStructured(9)";
      reference
       "ITU-T, G.707";
      smiv2:oid "1.3.6.1.4.1.9.9.126.1.9.1";

      list csAu4Tug3ConfigEntry {
        key "ifIndex csAu4Tug3";
        description
         "There is an entry in this table for each TUG-3 within a 
          AU-4 SDH path that supports SDH virtual container VC-4.
          The ifIndex value represents an entry in ifTable with
          ifType = sonetPath(50).The ifTable entry applicable for
          this entry belongs to AU-4 path.";
        smiv2:oid "1.3.6.1.4.1.9.9.126.1.9.1.1";

        leaf ifIndex {
          type leafref {
            path "/if-mib:IF-MIB/if-mib:ifTable/if-mib:ifEntry/if-mib:ifIndex";
          }
        }

        leaf csAu4Tug3 {
          type int32 {
            range "1..3";
          }
          description
           "This object represents the TUG-3 number.";
          reference
           "ITU-T G.707 for SDH Multiplexing hierarchy.";
          smiv2:max-access "not-accessible";
          smiv2:oid "1.3.6.1.4.1.9.9.126.1.9.1.1.1";
        }

        leaf csAu4Tug3Payload {
          type enumeration {
            enum "other" {
              value "1";
            }
            enum "vc11" {
              value "2";
            }
            enum "vc12" {
              value "3";
            }
            enum "tu3ds3" {
              value "4";
            }
            enum "tu3e3" {
              value "5";
            }
          }
          description
           "This object is used for configuring the payload
            for the tributary group.
            
            The possible values are :
            
            vc11   : When set to 'vc11' following things are done:
                   - 28 entries created in ifTable for TU-11 with 
                     ifType = sonetVT(51)
                   - 28 entries created in ifTable for DS1 with 
                     ifType = ds1(18)
            
                     STM1<-AU-4<-TUG-3<-TUG-2<-TU-11<-VC11
            
            vc12   : When set to 'vc12' following things are done:
                   - 21 entries created in ifTable for TU-12 with 
                     ifType = sonetVT(51)
                   - 21 entries created in ifTable for E1 with 
                     ifType = ds1(18)
            
                     STM1<-AU-4<-TUG-3<-TUG-2<-TU-12<-VC12
            
            tu3ds3 : When set to 'tu3ds3' following things are done:
                   - 1 entry created in ifTable for TU-3 with 
                     ifType = sonetVT(51)
                   - 1 entry created in ifTable for DS3 with 
                     ifType = ds3(30)
            
                     STM1<-AU-4<-TUG-3<-TU-3<-VC3
            
            tu3e3  : When set to 'tu3e3' following things are done:
                   - 1 entry created in ifTable for TU-3 with 
                     ifType = sonetVT(51)
                   - 1 entry created in ifTable for E3 with 
                     ifType = ds3(30)
            
                     STM1<-AU-4<-TUG-3<-TU-3<-VC3
            
            The value 'other' can not be set.";
          smiv2:defval "vc11";
          smiv2:max-access "read-write";
          smiv2:oid "1.3.6.1.4.1.9.9.126.1.9.1.1.2";
        }
      }
    }
  }

  smiv2:alias "csVTConfigTable" {
    description
     "This table contains objects to configure the VT/VC (Virtual
      Tributary / Virtual Container) related properties of 
      SONET/SDH lines.";
    smiv2:oid "1.3.6.1.4.1.9.9.126.1.1.2";
  }

  smiv2:alias "csVTConfigEntry" {
    description
     "There is an entry in this table for each SONET line that 
      supports SONET virtual tributaries or SDH virtual containers.
      Each entry in this table will have a corresponding entry 
      in csConfigTable.";
    smiv2:oid "1.3.6.1.4.1.9.9.126.1.1.2.1";
  }

  augment "/CISCO-SONET-MIB:CISCO-SONET-MIB/CISCO-SONET-MIB:csConfigTable/CISCO-SONET-MIB:csConfigEntry" {
    description
     "There is an entry in this table for each SONET line that 
      supports SONET virtual tributaries or SDH virtual containers.
      Each entry in this table will have a corresponding entry 
      in csConfigTable.";
    smiv2:oid "1.3.6.1.4.1.9.9.126.1.1.2.1";

    leaf csTributaryType {
      type enumeration {
        enum "vt15vc11" {
          value "1";
        }
        enum "vt2vc12" {
          value "2";
        }
      }
      description
       "Type of the tributary carried within the SONET/SDH signal.
        
        vt15vc11    : carries T1 signal
        vt2vc12     : carries E1 signal";
      smiv2:max-access "read-write";
      smiv2:oid "1.3.6.1.4.1.9.9.126.1.1.2.1.1";
    }

    leaf csTributaryMappingType {
      type enumeration {
        enum "asynchronous" {
          value "1";
        }
        enum "byteSynchronous" {
          value "2";
        }
      }
      description
       "This object represents the VT/VC mapping type.
        
        asynchronous:    In this mode, the channel structure of 
                         DS1/E1 is neither visible nor preserved.
        
        byteSynchronous: In this mode, the DS0 signals inside the
                         VT/VC can be found and extracted from the
                         frame.
        
        Default is asynchronous(1).";
      smiv2:max-access "read-write";
      smiv2:oid "1.3.6.1.4.1.9.9.126.1.1.2.1.2";
    }

    leaf csTributaryFramingType {
      type enumeration {
        enum "notApplicable" {
          value "1";
        }
        enum "dsx1D4" {
          value "2";
        }
        enum "dsx1ESF" {
          value "3";
        }
      }
      description
       "This object represents the framing type to be assigned to the
        virtual tributaries in byte sync mapping mode.
        
              notApplicable  :  If VT mapping is not byteSynchronous(2).
              dsx1ESF        :  Extended Superframe Format
              dsx1D4         :  Superframe Format
        
        Default is dsx1ESF(3) if csTributaryMappingType is 
        byteSynchronous(2). For asynchronous(1) mapping, the default is 
        notApplicable(1).
        
        The value notApplicable(1) can not be set.";
      smiv2:max-access "read-write";
      smiv2:oid "1.3.6.1.4.1.9.9.126.1.1.2.1.3";
    }

    leaf csSignallingTransportMode {
      type enumeration {
        enum "notApplicable" {
          value "1";
        }
        enum "signallingTransferMode" {
          value "2";
        }
        enum "clearMode" {
          value "3";
        }
      }
      description
       "This object represents the mode used to transport DS0 
        signalling information for T1 byteSynchronous mapping (GR253).
        In signallingTransferMode(2), the robbed-bit signalling is 
        transferred to the VT header. In clearMode(3), only the 
        framing bit is transferred to the VT header.
             
        Default is signallingTransferMode(2) if csTributaryMappingType 
        is byteSynchronous. For asynchronous mapping, it is 
        notApplicable(1).
        
        The value notApplicable(1) can not be set.";
      smiv2:max-access "read-write";
      smiv2:oid "1.3.6.1.4.1.9.9.126.1.1.2.1.4";
    }

    leaf csTributaryGroupingType {
      type enumeration {
        enum "notApplicable" {
          value "1";
        }
        enum "au3Grouping" {
          value "2";
        }
        enum "au4Grouping" {
          value "3";
        }
      }
      description
       "This object represents the method used to group VCs into an
        STM-1 signal. Applicable only to SDH.
        
          au3Grouping: STM1<-AU-3<-TUG-2<-TU-12<-VC12 or
                       STM1<-AU-3<-TUG-2<-TU-11<-VC11.
        
          au4Grouping: STM1<-AU-4<-TUG-3<-TUG-2<-TU-12<-VC12 or
                       STM1<-AU-4<-TUG-3<-TUG-2<-TU-11<-VC11.
        
        Default is au3Grouping(2) for SDH and notApplicable(1) for SONET.";
      smiv2:max-access "read-write";
      smiv2:oid "1.3.6.1.4.1.9.9.126.1.1.2.1.5";
    }
  }

  smiv2:alias "cspConfigTable" {
    description
     "Cisco extension to SONET Path current table.";
    smiv2:oid "1.3.6.1.4.1.9.9.126.1.7.1";
  }

  smiv2:alias "cspConfigEntry" {
    description
     "An entry in Cisco extension to the SONET path current table.";
    smiv2:oid "1.3.6.1.4.1.9.9.126.1.7.1.1";
  }

  augment "/sonet-mib:SONET-MIB/sonet-mib:sonetPathCurrentTable/sonet-mib:sonetPathCurrentEntry" {
    description
     "An entry in Cisco extension to the SONET path current table.";
    smiv2:oid "1.3.6.1.4.1.9.9.126.1.7.1.1";

    leaf cspSonetPathPayload {
      type enumeration {
        enum "unequipped" {
          value "1";
        }
        enum "unspecified" {
          value "2";
        }
        enum "ds3" {
          value "3";
        }
        enum "vt15vc11" {
          value "4";
        }
        enum "vt2vc12" {
          value "5";
        }
        enum "atmCell" {
          value "6";
        }
        enum "hdlcFr" {
          value "7";
        }
        enum "e3" {
          value "8";
        }
        enum "vtStructured" {
          value "9";
        }
      }
      description
       "Specifies the payload carried by the SONET/SDH Path.
        The payload specification corresponds to C2 (Signal Label)
        overhead byte in SONET/SDH Path Overhead:
        unequipped(1)    : Path is not provisioned to carry any payload.
        unspecified(2)   : Path is carrying an unspecifed payload.
        ds3(3)           : Path is carrying a DS3 path as payload.
        vt15vc11(4)      : Path is carrying SONET-VT1.5/SDH-VC11 payload.
        vt2vc12(5)       : Path is carrying SONET-VT2/SDH-VC12 as payload.
        atmCell(6)       : Path is carrying ATM Cells as payload.
        hdlcFr(7)        : Path is carrying Frame Relay (HDLC) payload.
        e3(8)            : Path is carrying an E3 path as payload.
        vtStructured(9)  : Path is carrying VTGs/TUG3s/TUG2s which may
                           each carry a different payload. 
        A write operation on this object will result in update to
        C2 overhead byte in the Path Overhead.";
      reference
       "Telcordia GR-253, ITU G.707";
      smiv2:max-access "read-write";
      smiv2:oid "1.3.6.1.4.1.9.9.126.1.7.1.1.1";
    }

    leaf cspTributaryMappingType {
      type enumeration {
        enum "asynchronous" {
          value "1";
        }
        enum "byteSynchronous" {
          value "2";
        }
      }
      description
       "This object represents the VT/VC mapping type.
        asynchronous: In this mode, the channel structure of 
                      DS1/E1 is neither visible nor preserved.
        
        byteSynchronous: In this mode, the DS0 signals inside 
                         the VT/VC can be found and extracted 
                         from the frame.
        The initial value is asynchronous(1).";
      smiv2:max-access "read-write";
      smiv2:oid "1.3.6.1.4.1.9.9.126.1.7.1.1.2";
    }

    leaf cspSignallingTransportMode {
      type enumeration {
        enum "notApplicable" {
          value "1";
        }
        enum "signallingTransferMode" {
          value "2";
        }
        enum "clearMode" {
          value "3";
        }
      }
      description
       "This object represents the mode used to transport DS0 
        Signalling information for T1 byteSynchronous mapping
        (GR253).
        In signallingTransferMode(2), the robbed-bit signalling 
        is transferred to the VT header. In clearMode(3), only 
        the framing bit is transferred to the VT header.
                 
        The initial value is signallingTransferMode(2) 
        if csTributaryMappingType is byteSynchronous. 
        For asynchronous mapping, it is 
        notApplicable(1).
        
        The value notApplicable(1) can not be set.";
      smiv2:max-access "read-write";
      smiv2:oid "1.3.6.1.4.1.9.9.126.1.7.1.1.3";
    }

    leaf cspTributaryGroupingType {
      type enumeration {
        enum "notApplicable" {
          value "1";
        }
        enum "au3Grouping" {
          value "2";
        }
        enum "au4Grouping" {
          value "3";
        }
      }
      description
       "This object represents the method used to group VCs into
        an STM-1 signal. Applicable only to SDH.
        
        au3Grouping: STM1<-AU-3<-TUG-2<-TU-12<-VC12 or
                     STM1<-AU-3<-TUG-2<-TU-11<-VC11.
        
        au4Grouping: STM1<-AU-4<-TUG-3<-TUG-2<-TU-12<-VC12 or
                     STM1<-AU-4<-TUG-3<-TUG-2<-TU-11<-VC11.
        
        The initial value is au3Grouping(2) for SDH and 
        notApplicable(1) for SONET.";
      reference
       "ITU-T,G707, Section 6 Basic Multiplexing Priciples";
      smiv2:max-access "read-write";
      smiv2:oid "1.3.6.1.4.1.9.9.126.1.7.1.1.4";
    }
  }

  notification ciscoSonetSectionStatusChange {
    description
     "This notification is generated whenever the value of
      sonetSectionCurrentStatus changes.";
    smiv2:oid "1.3.6.1.4.1.9.9.126.0.1";

    container object-1 {

      leaf ifIndex {
        type leafref {
          path "/if-mib:IF-MIB/if-mib:ifTable/if-mib:ifEntry/if-mib:ifIndex";
        }
      }

      leaf sonetSectionCurrentStatus {
        type leafref {
          path "/sonet-mib:SONET-MIB/sonet-mib:sonetSectionCurrentTable/sonet-mib:sonetSectionCurrentEntry/sonet-mib:sonetSectionCurrentStatus";
        }
      }
    }

    container object-2 {

      leaf ifIndex {
        type leafref {
          path "/if-mib:IF-MIB/if-mib:ifTable/if-mib:ifEntry/if-mib:ifIndex";
        }
      }

      leaf ifDescr {
        type leafref {
          path "/if-mib:IF-MIB/if-mib:ifTable/if-mib:ifEntry/if-mib:ifDescr";
        }
      }
    }
  }

  notification ciscoSonetLineStatusChange {
    description
     "This notification is generated whenever the value of
      sonetLineCurrentStatus changes.";
    smiv2:oid "1.3.6.1.4.1.9.9.126.0.2";

    container object-1 {

      leaf ifIndex {
        type leafref {
          path "/if-mib:IF-MIB/if-mib:ifTable/if-mib:ifEntry/if-mib:ifIndex";
        }
      }

      leaf sonetLineCurrentStatus {
        type leafref {
          path "/sonet-mib:SONET-MIB/sonet-mib:sonetLineCurrentTable/sonet-mib:sonetLineCurrentEntry/sonet-mib:sonetLineCurrentStatus";
        }
      }
    }

    container object-2 {

      leaf ifIndex {
        type leafref {
          path "/if-mib:IF-MIB/if-mib:ifTable/if-mib:ifEntry/if-mib:ifIndex";
        }
      }

      leaf ifDescr {
        type leafref {
          path "/if-mib:IF-MIB/if-mib:ifTable/if-mib:ifEntry/if-mib:ifDescr";
        }
      }
    }
  }

  notification ciscoSonetPathStatusChange {
    description
     "This notification is generated whenever the value of
      sonetPathCurrentStatus changes.";
    smiv2:oid "1.3.6.1.4.1.9.9.126.0.3";

    container object-1 {

      leaf ifIndex {
        type leafref {
          path "/if-mib:IF-MIB/if-mib:ifTable/if-mib:ifEntry/if-mib:ifIndex";
        }
      }

      leaf sonetPathCurrentStatus {
        type leafref {
          path "/sonet-mib:SONET-MIB/sonet-mib:sonetPathCurrentTable/sonet-mib:sonetPathCurrentEntry/sonet-mib:sonetPathCurrentStatus";
        }
      }
    }

    container object-2 {

      leaf ifIndex {
        type leafref {
          path "/if-mib:IF-MIB/if-mib:ifTable/if-mib:ifEntry/if-mib:ifIndex";
        }
      }

      leaf ifDescr {
        type leafref {
          path "/if-mib:IF-MIB/if-mib:ifTable/if-mib:ifEntry/if-mib:ifDescr";
        }
      }
    }
  }

  notification ciscoSonetVTStatusChange {
    description
     "This notification is generated whenever the value of
      sonetVTCurrentStatus changes.";
    smiv2:oid "1.3.6.1.4.1.9.9.126.0.4";

    container object-1 {

      leaf ifIndex {
        type leafref {
          path "/if-mib:IF-MIB/if-mib:ifTable/if-mib:ifEntry/if-mib:ifIndex";
        }
      }

      leaf sonetVTCurrentStatus {
        type leafref {
          path "/sonet-mib:SONET-MIB/sonet-mib:sonetVTCurrentTable/sonet-mib:sonetVTCurrentEntry/sonet-mib:sonetVTCurrentStatus";
        }
      }
    }

    container object-2 {

      leaf ifIndex {
        type leafref {
          path "/if-mib:IF-MIB/if-mib:ifTable/if-mib:ifEntry/if-mib:ifIndex";
        }
      }

      leaf ifDescr {
        type leafref {
          path "/if-mib:IF-MIB/if-mib:ifTable/if-mib:ifEntry/if-mib:ifDescr";
        }
      }
    }
  }

  smiv2:alias "ciscoSonetMIB" {
    smiv2:oid "1.3.6.1.4.1.9.9.126";
  }

  smiv2:alias "ciscoSonetMIBNotifs" {
    smiv2:oid "1.3.6.1.4.1.9.9.126.0";
  }

  smiv2:alias "ciscoSonetMIBObjects" {
    smiv2:oid "1.3.6.1.4.1.9.9.126.1";
  }

  smiv2:alias "csConfig" {
    smiv2:oid "1.3.6.1.4.1.9.9.126.1.1";
  }

  smiv2:alias "csApsConfig" {
    smiv2:oid "1.3.6.1.4.1.9.9.126.1.2";
  }

  smiv2:alias "csSection" {
    smiv2:oid "1.3.6.1.4.1.9.9.126.1.3";
  }

  smiv2:alias "csLine" {
    smiv2:oid "1.3.6.1.4.1.9.9.126.1.4";
  }

  smiv2:alias "csPath" {
    smiv2:oid "1.3.6.1.4.1.9.9.126.1.5";
  }

  smiv2:alias "csStats" {
    smiv2:oid "1.3.6.1.4.1.9.9.126.1.6";
  }

  smiv2:alias "cspConfig" {
    smiv2:oid "1.3.6.1.4.1.9.9.126.1.7";
  }

  smiv2:alias "csNotifications" {
    smiv2:oid "1.3.6.1.4.1.9.9.126.1.8";
  }

  smiv2:alias "csAu4Tug3Config" {
    smiv2:oid "1.3.6.1.4.1.9.9.126.1.9";
  }

  smiv2:alias "ciscoSonetMIBConformance" {
    smiv2:oid "1.3.6.1.4.1.9.9.126.3";
  }

  smiv2:alias "ciscoSonetMIBCompliances" {
    smiv2:oid "1.3.6.1.4.1.9.9.126.3.1";
  }

  smiv2:alias "ciscoSonetMIBGroups" {
    smiv2:oid "1.3.6.1.4.1.9.9.126.3.2";
  }

}
