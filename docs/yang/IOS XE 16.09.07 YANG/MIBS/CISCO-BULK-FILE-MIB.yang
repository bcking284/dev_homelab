/*
 * Generated by confdc --mib2yang-std
 * Source: mgmt/dmi/model/mib/src/CISCO-BULK-FILE-MIB.mib
 */
/*
 * This YANG module has been generated by smidump 0.5.0:
 *
 *      smidump -f yang CISCO-BULK-FILE-MIB
 *
 * Do not edit. Edit the source file instead!
 */

module CISCO-BULK-FILE-MIB {

  namespace "urn:ietf:params:xml:ns:yang:smiv2:CISCO-BULK-FILE-MIB";
  prefix CISCO-BULK-FILE-MIB;

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-snmp@cisco.com";

  description
   "The MIB module for creating and deleting bulk files of
    SNMP data for file transfer.";

  revision 2002-06-10 {
    description
     "Added enum 'forcedCreate' for object 'cbfDefineFileNow'
      for forced creation of configuration files.";
  }

  revision 2002-05-15 {
    description
     "Added default values for all read-write objects in table to
      simplify creation of table rows.";
  }

  revision 2001-08-22 {
    description
     "Modified description of objects 
      cbfDefineObjectTableInstance and
      cbfDefineObjectLastPolledInst in cbfDefineObjectTable
      to accept/represent Full OIDs instead of partial OIDs.";
  }

  revision 2001-08-01 {
    description
     "Enhanced the MIB for selective row transfer from
      MIBS. Added a notification to indicate bulk file creation 
      or error(during creation of the file).
      
      Added object cbfDefineFileNotifyOnCompletion to
      cbfDefineFileTable.
      Added the objects cbfDefineObjectTableInstance,
      cbfDefineObjectLastPolledInst and 
      cbfDefineObjectNumEntries to cbfDefineObjectTable.
      Added cbfDefineFileCompletion notification.";
  }

  revision 2001-06-26 {
    description
     "Added the following enumerations variantBERWithCksum(4) and 
      variantBinWithCksum(5) in cbfDefineFileFormat";
  }

  revision 1998-10-29 {
    description
     "Initial version of this MIB module.";
  }


  container CISCO-BULK-FILE-MIB {
    config false;

    container cbfDefine {
      smiv2:oid "1.3.6.1.4.1.9.9.81.1.1";

      leaf cbfDefineMaxFiles {
        type uint32 {
          range "0..4294967295";
        }
        description
         "The maximum number of file definitions this system
          can hold in cbfDefineFileTable.  A value of 0 indicates no
          configured limit.
          
          This object may be read-only on some systems.
          
          Changing this number does not disturb existing entries.";
        smiv2:max-access "read-write";
        smiv2:oid "1.3.6.1.4.1.9.9.81.1.1.1";
      }

      leaf cbfDefineFiles {
        type yang:gauge32;
        description
         "The current number of file definitions in cbfDefineFileTable.";
        smiv2:max-access "read-only";
        smiv2:oid "1.3.6.1.4.1.9.9.81.1.1.2";
      }

      leaf cbfDefineHighFiles {
        type yang:gauge32;
        description
         "The maximum value of cbfDefineFiles since system 
          initialization.";
        smiv2:max-access "read-only";
        smiv2:oid "1.3.6.1.4.1.9.9.81.1.1.3";
      }

      leaf cbfDefineFilesRefused {
        type yang:counter32;
        description
         "The number of attempts to create a file definition that
          failed due to exceeding cbfDefineMaxFiles.";
        smiv2:max-access "read-only";
        smiv2:oid "1.3.6.1.4.1.9.9.81.1.1.4";
      }

      leaf cbfDefineMaxObjects {
        type uint32 {
          range "0..4294967295";
        }
        description
         "The maximum total number of object selections to go with
          file definitions this system, that is, the total number
          of objects this system can hold in cbfDefineObjectTable.  A
          value of 0 indicates no configured limit.
          
          This object may be read-only on some systems.
          
          Changing this number does not disturb existing entries.";
        smiv2:max-access "read-write";
        smiv2:oid "1.3.6.1.4.1.9.9.81.1.1.5";
      }

      leaf cbfDefineObjects {
        type yang:gauge32;
        description
         "The current number of object selections in 
          cbfDefineObjectTable.";
        smiv2:max-access "read-only";
        smiv2:oid "1.3.6.1.4.1.9.9.81.1.1.6";
      }

      leaf cbfDefineHighObjects {
        type yang:gauge32;
        description
         "The maximum value of cbfDefineObjects since system 
          initialization.";
        smiv2:max-access "read-only";
        smiv2:oid "1.3.6.1.4.1.9.9.81.1.1.7";
      }

      leaf cbfDefineObjectsRefused {
        type yang:counter32;
        description
         "The number of attempts to create an object selection that
          failed due to exceeding cbfDefineMaxObjects.";
        smiv2:max-access "read-only";
        smiv2:oid "1.3.6.1.4.1.9.9.81.1.1.8";
      }
    }

    container cbfStatus {
      smiv2:oid "1.3.6.1.4.1.9.9.81.1.2";

      leaf cbfStatusMaxFiles {
        type uint32 {
          range "0..4294967295";
        }
        description
         "The maximum number of file statuses this system
          can hold in cbfStatusFileTable.  A value of 0 indicates no
          configured limit.
          
          This object may be read-only on some systems.
          
          Changing this number deletes the oldest finished entries until
          the new limit is satisfied.";
        smiv2:max-access "read-write";
        smiv2:oid "1.3.6.1.4.1.9.9.81.1.2.1";
      }

      leaf cbfStatusFiles {
        type yang:gauge32;
        description
         "The current number of file statuses in cbfStatusFileTable.";
        smiv2:max-access "read-only";
        smiv2:oid "1.3.6.1.4.1.9.9.81.1.2.2";
      }

      leaf cbfStatusHighFiles {
        type yang:gauge32;
        description
         "The maximum value of cbfStatusFiles since system 
          initialization.";
        smiv2:max-access "read-only";
        smiv2:oid "1.3.6.1.4.1.9.9.81.1.2.3";
      }

      leaf cbfStatusFilesBumped {
        type yang:counter32;
        description
         "The number times the oldest entry was deleted due to exceeding
          cbfStatusMaxFiles.";
        smiv2:max-access "read-only";
        smiv2:oid "1.3.6.1.4.1.9.9.81.1.2.4";
      }
    }

    container cbfDefineFileTable {
      description
       "A table of bulk file definition and creation controls.";
      smiv2:oid "1.3.6.1.4.1.9.9.81.1.1.9";

      list cbfDefineFileEntry {
        key "cbfDefineFileIndex";
        description
         "Information for creation of a bulk file.
          
          To creat a bulk file an application creates an entry in this
          table and corresponding entries in cbfDefineObjectTable.
          
          When the entry in this table and the corresponding
          entries in cbfDefineObjectTable are 'active' the
          appliction uses cbfDefineFileNow to create the file
          and a corresponding entry in cbfStatusFileTable.
          
          Deleting an entry in cbfDefineFileTable deletes all
          corresponding entries in cbfDefineObjectTable and
          cbfStatusFileTable.
          
          An entry may not be modified or deleted while its
          cbfDefineFileNow has the value 'running'.";
        smiv2:oid "1.3.6.1.4.1.9.9.81.1.1.9.1";

        leaf cbfDefineFileIndex {
          type uint32 {
            range "1..4294967295";
          }
          description
           "An arbitrary integer to uniquely identify this entry.  To
            create an entry a management application should pick a
            random number.";
          smiv2:max-access "not-accessible";
          smiv2:oid "1.3.6.1.4.1.9.9.81.1.1.9.1.1";
        }

        leaf cbfDefineFileName {
          type snmpv2-tc:DisplayString {
            length "0..255";
          }
          description
           "The file name which is to be created.
            
            Explicit device or path choices in the value of this object
            override cbfDefineFileStorage.";
          smiv2:defval "";
          smiv2:max-access "read-write";
          smiv2:oid "1.3.6.1.4.1.9.9.81.1.1.9.1.2";
        }

        leaf cbfDefineFileStorage {
          type enumeration {
            enum "ephemeral" {
              value "1";
            }
            enum "volatile" {
              value "2";
            }
            enum "permanent" {
              value "3";
            }
          }
          description
           "The type of file storage to use:
            
            ephemeral        data exists in small amounts until read
            volatile        data exists in volatile memory
            permanent        data survives reboot
            
            An ephemeral file is suitable to be read only one time.
            
            Note that this value is taken as advisory and may be overridden
            by explicit device or path choices in cbfDefineFile.
            
            A given system may support any or all of these.";
          smiv2:defval "ephemeral";
          smiv2:max-access "read-write";
          smiv2:oid "1.3.6.1.4.1.9.9.81.1.1.9.1.3";
        }

        leaf cbfDefineFileFormat {
          type enumeration {
            enum "standardBER" {
              value "1";
            }
            enum "bulkBinary" {
              value "2";
            }
            enum "bulkASCII" {
              value "3";
            }
            enum "variantBERWithCksum" {
              value "4";
            }
            enum "variantBinWithCksum" {
              value "5";
            }
          }
          description
           "The format of the data in the file:
            
            StandardBER        standard SNMP ASN.1 BER
            bulkBinary        a binary format specified with this MIB
            bulkASCII        a human-readable form of bulkBinary
            variantBERWithCksum ASN.1 BER encoding with checksum
            variantBinWithCksum a binary format with checksum
            
                A given system may support any or all of these.";
          smiv2:defval "bulkBinary";
          smiv2:max-access "read-write";
          smiv2:oid "1.3.6.1.4.1.9.9.81.1.1.9.1.4";
        }

        leaf cbfDefineFileNow {
          type enumeration {
            enum "notActive" {
              value "1";
            }
            enum "ready" {
              value "2";
            }
            enum "create" {
              value "3";
            }
            enum "running" {
              value "4";
            }
            enum "forcedCreate" {
              value "5";
            }
          }
          description
           "The control to cause file creation.  The only values that can
            be set are 'create' and 'forcedCreate'. These can be set only 
            when the value is 'ready'.  Setting it to 'create' begins a 
            file creation and creates a corresponding entry in 
            cbfStatusFileTable. The system may choose to use an already 
            existing copy of the file instead of creating a new one. This
            may happen if there has been no configuration change on the 
            system and a request to recreate the file is received. 
            Setting this object to 'forcedCreate' forces the system to 
            create a new copy of the file.
            
            The value is 'notActve' as long as cbfDefineFileEntryStatus or
            any corresponding cbfDefineObjectEntryStatus is not active.
            
            When cbfDefineFileEntryStatus becomes active and all
            corresponding cbfDefineObjectEntryStatuses are active this 
            object automatically goes to 'ready'.";
          smiv2:defval "notActive";
          smiv2:max-access "read-write";
          smiv2:oid "1.3.6.1.4.1.9.9.81.1.1.9.1.5";
        }

        leaf cbfDefineFileEntryStatus {
          type snmpv2-tc:RowStatus;
          description
           "The control that allows creation, modification, and deletion
            of entries.  For detailed rules see the DESCRIPTION for
            cbfDefineFileEntry.";
          smiv2:max-access "read-write";
          smiv2:oid "1.3.6.1.4.1.9.9.81.1.1.9.1.6";
        }

        leaf cbfDefineFileNotifyOnCompletion {
          type boolean;
          description
           "This controls the cbfDefineFileCompletion notification.
            
            If true, cbfDefineFileCompletion notification
            will be generated. It is the responsibility of the 
            management entity to ensure that the SNMP administrative 
            model is configured in such a way as to allow the 
            notification to be delivered.";
          smiv2:defval "false";
          smiv2:max-access "read-write";
          smiv2:oid "1.3.6.1.4.1.9.9.81.1.1.9.1.7";
        }
      }
    }

    container cbfDefineObjectTable {
      description
       "A table of objects to go in bulk files.";
      smiv2:oid "1.3.6.1.4.1.9.9.81.1.1.10";

      list cbfDefineObjectEntry {
        key "cbfDefineFileIndex cbfDefineObjectIndex";
        description
         "Information about one object for a particular file.
          
          An application uses cbfDefineObjectEntryStatus to create entries
          in this table in correspondence with entries in
          cbfDefineFileTable, which must be created first.
          
          Entries in this table may not be changed, created or deleted
          while the corresponding value of cbfDefineFileNow is 'running'.";
        smiv2:oid "1.3.6.1.4.1.9.9.81.1.1.10.1";

        leaf cbfDefineFileIndex {
          type leafref {
            path "/CISCO-BULK-FILE-MIB:CISCO-BULK-FILE-MIB/CISCO-BULK-FILE-MIB:cbfDefineFileTable/CISCO-BULK-FILE-MIB:cbfDefineFileEntry/CISCO-BULK-FILE-MIB:cbfDefineFileIndex";
          }
        }

        leaf cbfDefineObjectIndex {
          type uint32 {
            range "1..4294967295";
          }
          description
           "An arbitrary integer to uniquely identify this entry.
            
            The numeric order of the entries controls the order of
            the objects in the file.";
          smiv2:max-access "not-accessible";
          smiv2:oid "1.3.6.1.4.1.9.9.81.1.1.10.1.1";
        }

        leaf cbfDefineObjectClass {
          type enumeration {
            enum "object" {
              value "1";
            }
            enum "lexicalTable" {
              value "2";
            }
            enum "leastCpuTable" {
              value "3";
            }
          }
          description
           "The meaning of each object class is given below:
            
            object          a single MIB object is retrieved.
            
            lexicalTable    an entire table or partial table
                            is retrieved in lexical order of rows.
            
            leastCpuTable   an entire table is retrieved with
                            lowest CPU utilization.
                            Lexical ordering of rows may not be 
                            maintained and is dependent upon 
                            individual MIB implementation.";
          smiv2:defval "leastCpuTable";
          smiv2:max-access "read-write";
          smiv2:oid "1.3.6.1.4.1.9.9.81.1.1.10.1.2";
        }

        leaf cbfDefineObjectID {
          type yang:object-identifier-128;
          description
           "The object identifier of a MIB object to be included in
            the file.
            
            If cbfDefineObjectClass is 'object' this must be a full OID,
            including all instance information.
            
            If cbfDefineObjectClass is 'lexicalTable' or 'leastCpuTable'
            this must be the OID of the table-defining SEQUENCE OF
            registration point.";
          smiv2:defval "zeroDotZero";
          smiv2:max-access "read-write";
          smiv2:oid "1.3.6.1.4.1.9.9.81.1.1.10.1.3";
        }

        leaf cbfDefineObjectEntryStatus {
          type snmpv2-tc:RowStatus;
          description
           "The control that allows creation, modification, and deletion
            of entries.  For detailed rules see the DESCRIPTION for
            cbfDefineObjectEntry.";
          smiv2:max-access "read-write";
          smiv2:oid "1.3.6.1.4.1.9.9.81.1.1.10.1.4";
        }

        leaf cbfDefineObjectTableInstance {
          type yang:object-identifier-128;
          description
           "If cbfDefineObjectClass is 'lexicalTable', then this object
            represents the starting instance in the cbfDefineObjectID
            table. The file created will have entries starting from
            the lexicographically next instance of the OID represented
            by this object. 
            
            For Eg: 
            -------
            
                   Let us  assume we are polling ifTable and we
                   have information till the second row(ifIndex.2). Now
                   we may be interested in 10 rows lexically following
                   the second row.
                   
                   So, we set cbfDefineObjectTableInstance as ifIndex.2 
                   and cbfDefineObjectNumEntries as 10. 
            
                   We will get information for the next 10 rows or
                   if there are less than 10 populated rows, we will
                   receive information till the end of the table is 
                   reached.
            
            The default value for this object is zeroDotZero.
            
            If this object has the value of zeroDotZero and 
            cbfDefineObjectNumEntries has value 0, then the whole
            table(represented by cbfDefineObjectID) is retrieved.
            
            If this object has the value of zeroDotZero,  
            cbfDefineObjectNumEntries has value n (>0) and there are 
            m(>0) entries in the table(represented by cbfDefineObjectID)
            then the first n entries in the table are retrieved if n < m. 
            If n >= m, then the whole table is retrieved.
            
            When the value of cbfDefineObjectNumEntries is 0, 
            it means all the entries in the table(represented 
            by cbfDefineObjectID) which lexicographically follow 
            cbfDefineObjectTableInstance are retrieved.
            
            This object is irrelevent if cbfDefineObjectClass is not
            'lexicalTable'.";
          smiv2:defval "zeroDotZero";
          smiv2:max-access "read-write";
          smiv2:oid "1.3.6.1.4.1.9.9.81.1.1.10.1.5";
        }

        leaf cbfDefineObjectNumEntries {
          type uint32 {
            range "0..4294967295";
          }
          description
           "If cbfDefineObjectClass is 'lexicalTable', then this object
            represents the maximum number of entries which will be 
            populated in the file starting from the lexicographically
            next instance of the OID represented by 
            cbfDefineObjectTableInstance. 
            
            This object is irrelevent if cbfDefineObjectClass is not
            'lexicalTable'.
            
            Refer to the description of cbfDefineObjectTableInstance for
            examples and different scenarios relating to this object.";
          smiv2:defval "0";
          smiv2:max-access "read-write";
          smiv2:oid "1.3.6.1.4.1.9.9.81.1.1.10.1.6";
        }

        leaf cbfDefineObjectLastPolledInst {
          type yang:object-identifier-128;
          description
           "This object represents the last polled instance in the
            table.
            
            The value represented by this object will be relevent only
            if the corresponding cbfStatusFileState is emptied(3) for 
            ephemeral files or ready(2) for volatile or permanent files.
            
            A value of zeroDotZero indicates an absence of last polled 
            object.
            
            An NMS can use the value of this object and populate the
            cbfDefineObjectTableInstance to retrieve a contiguous set
            of rows in a table.";
          smiv2:max-access "read-only";
          smiv2:oid "1.3.6.1.4.1.9.9.81.1.1.10.1.7";
        }
      }
    }

    container cbfStatusFileTable {
      description
       "A table of bulk file status.";
      smiv2:oid "1.3.6.1.4.1.9.9.81.1.2.5";

      list cbfStatusFileEntry {
        key "cbfDefineFileIndex cbfStatusFileIndex";
        description
         "Status for a particular file.
          
          An entry exists in this table for each time cbfDefineFileNow
          has been set to 'create' and the corresponding entry here
          has not been explicitly deleted by the application or bumped
          to make room for a new entry.
          
          Deleting an entry with cbfStatusFileState 'running' aborts
          the file creation attempt.
          
          It is implementation and file-system specific whether deleting
          the entry also deletes the file.";
        smiv2:oid "1.3.6.1.4.1.9.9.81.1.2.5.1";

        leaf cbfDefineFileIndex {
          type leafref {
            path "/CISCO-BULK-FILE-MIB:CISCO-BULK-FILE-MIB/CISCO-BULK-FILE-MIB:cbfDefineFileTable/CISCO-BULK-FILE-MIB:cbfDefineFileEntry/CISCO-BULK-FILE-MIB:cbfDefineFileIndex";
          }
        }

        leaf cbfStatusFileIndex {
          type uint32 {
            range "1..4294967295";
          }
          description
           "An arbitrary integer to uniquely identify this file.
            
            The numeric order of the entries implies the creation
            order of the files.";
          smiv2:max-access "not-accessible";
          smiv2:oid "1.3.6.1.4.1.9.9.81.1.2.5.1.1";
        }

        leaf cbfStatusFileState {
          type enumeration {
            enum "running" {
              value "1";
            }
            enum "ready" {
              value "2";
            }
            enum "emptied" {
              value "3";
            }
            enum "noSpace" {
              value "4";
            }
            enum "badName" {
              value "5";
            }
            enum "writeErr" {
              value "6";
            }
            enum "noMem" {
              value "7";
            }
            enum "buffErr" {
              value "8";
            }
            enum "aborted" {
              value "9";
            }
          }
          description
           "The file state:
            
            running    data is being written to the file
            ready      the file is ready to be read
            emptied    an ephemeral file was successfully consumed
            noSpace    no data due to insufficient file space
            badName    no data due to a name or path problem
            writeErr   no data due to fatal file write error
            noMem      no data due to insufficient dynamic memory
            buffErr    implementation buffer too small
            aborted    short terminated by operator command
            
            Only the 'ready' state implies that the file is available
            for transfer.
            
            The disposition of files after an error is implementation
            and file-syste specific.";
          smiv2:max-access "read-only";
          smiv2:oid "1.3.6.1.4.1.9.9.81.1.2.5.1.2";
        }

        leaf cbfStatusFileCompletionTime {
          type yang:timestamp;
          description
           "The value of sysUpTime when the creation attempt completed.
            A value of 0 indicates not complete.  For ephemeral files this
            is the time when cbfStatusFileState goes to 'emptied'.  For
            others this is the time when the state leaves 'running'.";
          smiv2:max-access "read-only";
          smiv2:oid "1.3.6.1.4.1.9.9.81.1.2.5.1.3";
        }

        leaf cbfStatusFileEntryStatus {
          type snmpv2-tc:RowStatus;
          description
           "The control that allows deletion of entries. For detailed rules
            see the DESCRIPTION for cbfStatusFileEntry.
            
            This object may not be set to any value other than 'destroy'.";
          smiv2:max-access "read-write";
          smiv2:oid "1.3.6.1.4.1.9.9.81.1.2.5.1.4";
        }
      }
    }
  }

  notification cbfDefineFileCompletion {
    description
     "A cbfDefineFileCompletion notification is sent on 
      the following conditions :
      - completion of a file consumption operation in case of
        ephemeral files.
      - completion of file creation operation in case of 
        volatile or permanent files.
      - any error during file creation.";
    smiv2:oid "1.3.6.1.4.1.9.9.81.2.0.1";

    container object-1 {

      leaf cbfDefineFileIndex {
        type leafref {
          path "/CISCO-BULK-FILE-MIB:CISCO-BULK-FILE-MIB/CISCO-BULK-FILE-MIB:cbfDefineFileTable/CISCO-BULK-FILE-MIB:cbfDefineFileEntry/CISCO-BULK-FILE-MIB:cbfDefineFileIndex";
        }
      }

      leaf cbfStatusFileIndex {
        type leafref {
          path "/CISCO-BULK-FILE-MIB:CISCO-BULK-FILE-MIB/CISCO-BULK-FILE-MIB:cbfStatusFileTable/CISCO-BULK-FILE-MIB:cbfStatusFileEntry/CISCO-BULK-FILE-MIB:cbfStatusFileIndex";
        }
      }

      leaf cbfStatusFileState {
        type leafref {
          path "/CISCO-BULK-FILE-MIB:CISCO-BULK-FILE-MIB/CISCO-BULK-FILE-MIB:cbfStatusFileTable/CISCO-BULK-FILE-MIB:cbfStatusFileEntry/CISCO-BULK-FILE-MIB:cbfStatusFileState";
        }
      }
    }

    container object-2 {

      leaf cbfDefineFileIndex {
        type leafref {
          path "/CISCO-BULK-FILE-MIB:CISCO-BULK-FILE-MIB/CISCO-BULK-FILE-MIB:cbfDefineFileTable/CISCO-BULK-FILE-MIB:cbfDefineFileEntry/CISCO-BULK-FILE-MIB:cbfDefineFileIndex";
        }
      }

      leaf cbfStatusFileIndex {
        type leafref {
          path "/CISCO-BULK-FILE-MIB:CISCO-BULK-FILE-MIB/CISCO-BULK-FILE-MIB:cbfStatusFileTable/CISCO-BULK-FILE-MIB:cbfStatusFileEntry/CISCO-BULK-FILE-MIB:cbfStatusFileIndex";
        }
      }

      leaf cbfStatusFileCompletionTime {
        type leafref {
          path "/CISCO-BULK-FILE-MIB:CISCO-BULK-FILE-MIB/CISCO-BULK-FILE-MIB:cbfStatusFileTable/CISCO-BULK-FILE-MIB:cbfStatusFileEntry/CISCO-BULK-FILE-MIB:cbfStatusFileCompletionTime";
        }
      }
    }
  }

  smiv2:alias "ciscoBulkFileMIB" {
    smiv2:oid "1.3.6.1.4.1.9.9.81";
  }

  smiv2:alias "ciscoBulkFileMIBObjects" {
    smiv2:oid "1.3.6.1.4.1.9.9.81.1";
  }

  smiv2:alias "cbfDefine" {
    smiv2:oid "1.3.6.1.4.1.9.9.81.1.1";
  }

  smiv2:alias "cbfStatus" {
    smiv2:oid "1.3.6.1.4.1.9.9.81.1.2";
  }

  smiv2:alias "ciscoBulkFileMIBNotificationPrefix" {
    smiv2:oid "1.3.6.1.4.1.9.9.81.2";
  }

  smiv2:alias "ciscoBulkFileMIBNotifications" {
    smiv2:oid "1.3.6.1.4.1.9.9.81.2.0";
  }

  smiv2:alias "ciscoBulkFileMIBConformance" {
    smiv2:oid "1.3.6.1.4.1.9.9.81.3";
  }

  smiv2:alias "ciscoBulkFileMIBCompliances" {
    smiv2:oid "1.3.6.1.4.1.9.9.81.3.1";
  }

  smiv2:alias "ciscoBulkFileMIBGroups" {
    smiv2:oid "1.3.6.1.4.1.9.9.81.3.2";
  }

}
