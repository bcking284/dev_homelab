/*
 * Generated by confdc --mib2yang-std
 * Source: mgmt/dmi/model/mib/src/CISCO-IETF-MPLS-TE-EXT-STD-03-MIB.mib
 */
/*
 * This YANG module has been generated by smidump 0.5.0:
 *
 *      smidump -f yang CISCO-IETF-MPLS-TE-EXT-STD-03-MIB
 *
 * Do not edit. Edit the source file instead!
 */

module CISCO-IETF-MPLS-TE-EXT-STD-03-MIB {

  namespace "urn:ietf:params:xml:ns:yang:smiv2:CISCO-IETF-MPLS-TE-EXT-STD-03-MIB";
  prefix CISCO-IETF-MPLS-TE-EXT-STD-03-MIB;

  import CISCO-MPLS-TC-EXT-STD-MIB {
    prefix "cisco-mpls";
  }

  import MPLS-TC-STD-MIB {
    prefix "mpls-tc";
  }

  import MPLS-TE-STD-MIB {
    prefix "mpls-te";
  }

  import SNMPv2-TC {
    prefix "snmpv2-tc";
  }

  import ietf-yang-smiv2 {
    prefix "smiv2";
  }

  import ietf-yang-types {
    prefix "yang";
  }

  organization
   "Multiprotocol Label Switching (MPLS) Working Group";

  contact
   "Venkatesan Mahalingam
    Dell Inc,
    350 Holger way, San Jose, CA, USA
    Email: venkat.mahalingams@gmail.com
    
    Kannan KV Sampath
    Aricent,
    India
    Email: Kannan.Sampath@aricent.com
    
    Sam Aldrin
    Huawei Technologies
    2330 Central Express Way,
    Santa Clara, CA 95051, USA
    Email:  aldrin.ietf@gmail.com
    
    Thomas D. Nadeau
    Juniper Networks
    10 Technology Park Drive, Westford, MA 01886
    Email: tnadeau@juniper.net";

  description
   "Copyright (c) 2012 IETF Trust and the persons identified
    as the document authors.  All rights reserved.
    This MIB module contains generic object definitions for
    MPLS Traffic Engineering in transport networks.This module is a
    cisco-ized version of the IETF draft:
    draft-ietf-mpls-tp-te-mib-03";

  revision 2012-06-06 {
    description
     "[Revision added by libsmi due to a LAST-UPDATED clause.]";
  }

  revision 2012-04-08 {
    description
     "MPLS TE mib objects extension";
  }


  container CISCO-IETF-MPLS-TE-EXT-STD-03-MIB {
    config false;

    container cmplsNodeConfigTable {
      description
       "This table allows the administrator to map a node or
        LSR Identifier (IP compatible [Global_Node_ID] or ICC)
        with a local identifier.
        
        
        This table is created to reuse the existing
        mplsTunnelTable for MPLS based transport network
        tunnels also.
        Since the MPLS tunnel's Ingress/Egress LSR identifiers'
        size (Unsigned32) value is not compatible for
        MPLS-TP tunnel i.e. Global_Node_Id of size 8 bytes and
        ICC of size 6 bytes, there exists a need to map the
        Global_Node_ID or ICC with the local identifier of size
        4 bytes (Unsigned32) value in order
        to index (Ingress/Egress LSR identifier)
        the existing mplsTunnelTable.";
      smiv2:oid "1.3.6.1.4.1.9.10.146.1.1";

      list cmplsNodeConfigEntry {
        key "cmplsNodeConfigLocalId";
        description
         "An entry in this table represents a mapping
          identification for the operator or service provider
          with node or LSR.
          
          As per [RFC6370], this mapping is
          
          represented as Global_Node_ID or ICC.
          
          Note: Each entry in this table should have a unique
          Global_ID and Node_ID combination.";
        smiv2:oid "1.3.6.1.4.1.9.10.146.1.1.1";

        leaf cmplsNodeConfigLocalId {
          type cisco-mpls:CMplsLocalId;
          description
           "This object allows the administrator to assign a unique
            local identifier to map Global_Node_ID or ICC.";
          smiv2:max-access "not-accessible";
          smiv2:oid "1.3.6.1.4.1.9.10.146.1.1.1.1";
        }

        leaf cmplsNodeConfigGlobalId {
          type cisco-mpls:CMplsGlobalId;
          description
           "This object indicates the Global Operator Identifier.
            This object value should be zero when
            mplsNodeConfigIccId is configured with non-null value.";
          reference
           "MPLS-TP Identifiers [RFC6370].";
          smiv2:max-access "read-write";
          smiv2:oid "1.3.6.1.4.1.9.10.146.1.1.1.2";
        }

        leaf cmplsNodeConfigNodeId {
          type cisco-mpls:CMplsNodeId;
          description
           "This object indicates the Node_ID within the operator.
            This object value should be zero when mplsNodeConfigIccId
            is configured with non-null value.";
          reference
           "MPLS-TP Identifiers [RFC6370].";
          smiv2:max-access "read-write";
          smiv2:oid "1.3.6.1.4.1.9.10.146.1.1.1.3";
        }

        leaf cmplsNodeConfigIccId {
          type cisco-mpls:CMplsIccId;
          description
           "This object allows the operator or service provider to
            configure a unique MPLS-TP ITU-T Carrier Code (ICC)
            either for Ingress ID or Egress ID.
            
            This object value should be zero when
            mplsNodeConfigGlobalId and mplsNodeConfigNodeId are
            assigned with non-zero value.";
          reference
           "MPLS-TP Identifiers [RFC6370].";
          smiv2:max-access "read-write";
          smiv2:oid "1.3.6.1.4.1.9.10.146.1.1.1.4";
        }

        leaf cmplsNodeConfigRowStatus {
          type snmpv2-tc:RowStatus;
          description
           "This object allows the administrator to create, modify,
            and/or delete a row in this table.";
          smiv2:max-access "read-write";
          smiv2:oid "1.3.6.1.4.1.9.10.146.1.1.1.5";
        }

        leaf cmplsNodeConfigStorageType {
          type snmpv2-tc:StorageType;
          description
           "This variable indicates the storage type for this
            object.
            Conceptual rows having the value 'permanent'
            need not allow write-access to any columnar
            objects in the row.";
          smiv2:defval "volatile";
          smiv2:max-access "read-write";
          smiv2:oid "1.3.6.1.4.1.9.10.146.1.1.1.6";
        }
      }
    }

    container cmplsNodeIpMapTable {
      description
       "This read-only table allows the administrator to retrieve
        the local identifier for a given Global_Node_ID in an IP
        compatible operator environment.
        
        This table MAY be used in on-demand and/or proactive
        OAM operations to get the Ingress/Egress LSR identifier
        (Local Identifier) from Src-Global_Node_ID
        or Dst-Global_Node_ID and the Ingress and Egress LSR
        identifiers are used to retrieve the tunnel entry.
        
        This table returns nothing when the associated entry
        is not defined in mplsNodeConfigTable.";
      smiv2:oid "1.3.6.1.4.1.9.10.146.1.2";

      list cmplsNodeIpMapEntry {
        key "cmplsNodeIpMapGlobalId cmplsNodeIpMapNodeId";
        description
         "An entry in this table represents a mapping of
          Global_Node_ID with the local identifier.
          
          An entry in this table is created automatically when
          the Local identifier is associated with Global_ID and
          Node_Id in the mplsNodeConfigTable.
          Note: Each entry in this table should have a unique
          Global_ID and Node_ID combination.";
        smiv2:oid "1.3.6.1.4.1.9.10.146.1.2.1";

        leaf cmplsNodeIpMapGlobalId {
          type cisco-mpls:CMplsGlobalId;
          description
           "This object indicates the Global_ID.";
          smiv2:max-access "not-accessible";
          smiv2:oid "1.3.6.1.4.1.9.10.146.1.2.1.1";
        }

        leaf cmplsNodeIpMapNodeId {
          type cisco-mpls:CMplsNodeId;
          description
           "This object indicates the Node_ID within the
            operator.";
          smiv2:max-access "not-accessible";
          smiv2:oid "1.3.6.1.4.1.9.10.146.1.2.1.2";
        }

        leaf cmplsNodeIpMapLocalId {
          type cisco-mpls:CMplsLocalId;
          description
           "This object contains an IP compatible local identifier
            which is defined in mplsNodeConfigTable.";
          smiv2:max-access "read-only";
          smiv2:oid "1.3.6.1.4.1.9.10.146.1.2.1.3";
        }
      }
    }

    container cmplsNodeIccMapTable {
      description
       "This read-only table allows the administrator to retrieve
        the local identifier for a given ICC operator in an ICC
        operator environment.
        
        This table MAY be used in on-demand and/or proactive
        OAM operations to get the Ingress/Egress LSR
        identifier (Local Identifier) from Src-ICC
        or Dst-ICC and the Ingress and Egress LSR
        identifiers are used to retrieve the tunnel entry.
        This table returns nothing when the associated entry
        is not defined in mplsNodeConfigTable.";
      smiv2:oid "1.3.6.1.4.1.9.10.146.1.3";

      list cmplsNodeIccMapEntry {
        key "cmplsNodeIccMapIccId";
        description
         "An entry in this table represents a mapping of ICC with
          the local identifier.
          
          An entry in this table is created automatically when
          the Local identifier is associated with ICC in
          the mplsNodeConfigTable.";
        smiv2:oid "1.3.6.1.4.1.9.10.146.1.3.1";

        leaf cmplsNodeIccMapIccId {
          type cisco-mpls:CMplsIccId;
          description
           "This object allows the operator or service provider to
            configure a unique MPLS-TP ITU-T Carrier Code (ICC)
            either for Ingress or Egress LSR ID.
            
            The ICC is a string of one to six characters, each
            character being either alphabetic (i.e.  A-Z) or
            numeric (i.e. 0-9) characters. Alphabetic characters
            in the ICC should be represented with upper case
            letters.";
          smiv2:max-access "not-accessible";
          smiv2:oid "1.3.6.1.4.1.9.10.146.1.3.1.1";
        }

        leaf cmplsNodeIccMapLocalId {
          type cisco-mpls:CMplsLocalId;
          description
           "This object contains an ICC based local identifier
            which is defined in mplsNodeConfigTable.";
          smiv2:max-access "read-only";
          smiv2:oid "1.3.6.1.4.1.9.10.146.1.3.1.2";
        }
      }
    }

    container cmplsTunnelExtTable {
      description
       "This table represents MPLS-TP specific extensions to
        mplsTunnelTable.
        
        As per MPLS-TP Identifiers [RFC6370], LSP_ID for IP based
        co-routed bidirectional tunnel,
        
        A1-{Global_ID::Node_ID::Tunnel_Num}::Z9-{Global_ID::
        Node_ID::Tunnel_Num}::LSP_Num
        
        LSP_ID for IP based associated bidirectional tunnel,
        A1-{Global_ID::Node_ID::Tunnel_Num::LSP_Num}::
        Z9-{Global_ID::Node_ID::Tunnel_Num::LSP_Num}
        
        mplsTunnelTable is reused for forming the LSP_ID
        as follows,
        
        Source Tunnel_Num is mapped with mplsTunnelIndex,
        Source Node_ID is mapped with
        mplsTunnelIngressLSRId, Destination Node_ID is
        mapped with mplsTunnelEgressLSRId LSP_Num is mapped with
        mplsTunnelInstance.
        
        Source Global_Node_ID and/or ICC and Destination
        Global_Node_ID and/or ICC are maintained in the
        mplsNodeConfigTable and mplsNodeConfigLocalId is
        used to create an entry in mplsTunnelTable.";
      reference
       "MPLS-TP Identifiers [RFC6370].";
      smiv2:oid "1.3.6.1.4.1.9.10.146.1.4";

      list cmplsTunnelExtEntry {
        key "mplsTunnelIndex mplsTunnelInstance mplsTunnelIngressLSRId mplsTunnelEgressLSRId";
        description
         "An entry in this table represents MPLS-TP
          specific additional tunnel configurations.";
        smiv2:oid "1.3.6.1.4.1.9.10.146.1.4.1";

        leaf mplsTunnelIndex {
          type leafref {
            path "/mpls-te:MPLS-TE-STD-MIB/mpls-te:mplsTunnelTable/mpls-te:mplsTunnelEntry/mpls-te:mplsTunnelIndex";
          }
        }

        leaf mplsTunnelInstance {
          type leafref {
            path "/mpls-te:MPLS-TE-STD-MIB/mpls-te:mplsTunnelTable/mpls-te:mplsTunnelEntry/mpls-te:mplsTunnelInstance";
          }
        }

        leaf mplsTunnelIngressLSRId {
          type leafref {
            path "/mpls-te:MPLS-TE-STD-MIB/mpls-te:mplsTunnelTable/mpls-te:mplsTunnelEntry/mpls-te:mplsTunnelIngressLSRId";
          }
        }

        leaf mplsTunnelEgressLSRId {
          type leafref {
            path "/mpls-te:MPLS-TE-STD-MIB/mpls-te:mplsTunnelTable/mpls-te:mplsTunnelEntry/mpls-te:mplsTunnelEgressLSRId";
          }
        }

        leaf cmplsTunnelOppositeDirPtr {
          type snmpv2-tc:RowPointer;
          description
           "This object is applicable only for the bidirectional
            tunnel that has the forward and reverse LSPs in the
            same tunnel or in the different tunnels.
            
            This object holds the opposite direction tunnel entry
            if the bidirectional tunnel is setup by configuring two
            tunnel entries in mplsTunnelTable.
            
            The value of zeroDotZero indicates single tunnel entry
            is used for bidirectional tunnel setup.";
          smiv2:defval "zeroDotZero";
          smiv2:max-access "read-write";
          smiv2:oid "1.3.6.1.4.1.9.10.146.1.4.1.1";
        }

        leaf cmplsTunnelExtOppositeDirTnlValid {
          type boolean;
          description
           "Denotes whether or not this tunnel uses
            mplsTunnelOppositeDirPtr for identifying the opposite
            direction tunnel information. Note that if this variable
            is set to true then the mplsTunnelOppositeDirPtr should
            point to the first accessible row of the opposite
            direction tunnel.";
          smiv2:defval "false";
          smiv2:max-access "read-write";
          smiv2:oid "1.3.6.1.4.1.9.10.146.1.4.1.2";
        }

        leaf cmplsTunnelExtDestTnlIndex {
          type mpls-tc:MplsTunnelIndex;
          description
           "This object is applicable only for the bidirectional
            tunnel that has the forward and reverse LSPs in the
            same tunnel or in the different tunnels.
            
            This object holds the same value as that of the
            mplsTunnelIndex of mplsTunnelEntry if the forward and
            reverse LSPs are in the same tunnel. Otherwise,
            this object holds the value of the other direction
            associated LSP's mplsTunnelIndex from a different
            tunnel.
            
            The values of this object and the
            mplsTunnelExtDestTnlLspIndex object together can be used
            to identify an opposite direction LSP i.e. if the
            mplsTunnelIndex and mplsTunnelInstance hold the value
            for forward LSP, this object and
            mplsTunnelExtDestTnlLspIndex can be used to retrieve
            the reverse direction LSP and vice versa.
            
            This object and mplsTunnelExtDestTnlLspIndex values
            provide the first two indices of tunnel entry and
            the remaining indices can be derived as follows,
            if both the forward and reverse LSPs are present in
            the same tunnel, the opposite direction LSP's Ingress
            and Egress Identifier will be same for both the LSPs,
            else the Ingress and Egress Identifiers should be
            swapped in order to index the other direction tunnel.";
          smiv2:max-access "read-write";
          smiv2:oid "1.3.6.1.4.1.9.10.146.1.4.1.3";
        }

        leaf cmplsTunnelExtDestTnlLspIndex {
          type mpls-tc:MplsTunnelInstanceIndex;
          description
           "This object is applicable only for the bidirectional
            tunnel that has the forward and reverse LSPs in the
            same tunnel or in the different tunnels.
            
            This object should contain different value if both the
            forward and reverse LSPs present in the same tunnel.
            
            This object can contain same value or different values
            if the forward and reverse LSPs present in the different
            tunnels.";
          smiv2:max-access "read-write";
          smiv2:oid "1.3.6.1.4.1.9.10.146.1.4.1.4";
        }

        leaf cmplsTunnelExtDestTnlValid {
          type boolean;
          description
           "Denotes whether or not this tunnel uses
            mplsTunnelExtDestTnlIndex and
            mplsTunnelExtDestTnlLspIndex for identifying
            the opposite direction tunnel information. Note that if
            this variable is set to true then the
            mplsTunnelExtDestTnlIndex and
            mplsTunnelExtDestTnlLspIndex objects should have
            the valid opposite direction tunnel indices.";
          smiv2:defval "false";
          smiv2:max-access "read-write";
          smiv2:oid "1.3.6.1.4.1.9.10.146.1.4.1.5";
        }
      }
    }

    container cmplsTunnelReversePerfTable {
      description
       "This table extends the mplsTunnelTable to provide
        per-tunnel packet performance information for the reverse
        direction of a bidirectional tunnel.  It can be seen as
        supplementing the mplsTunnelPerfTable, which augments the
        mplsTunnelTable.
        
        For links that do not transport packets, these packet
        counters cannot be maintained.  For such links, attempts
        to read the objects in this table will return
        noSuchInstance.";
      reference
       "1. Multiprotocol Label Switching (MPLS) Traffic
        Engineering (TE)Management Information Base (MIB),
        RFC 3812.";
      smiv2:oid "1.3.6.1.4.1.9.10.146.1.5";

      list cmplsTunnelReversePerfEntry {
        key "mplsTunnelIndex mplsTunnelInstance mplsTunnelIngressLSRId mplsTunnelEgressLSRId";
        description
         "An entry in this table is created by the LSR for every
          bidirectional MPLS tunnel where packets are visible to the
          LSR.";
        smiv2:oid "1.3.6.1.4.1.9.10.146.1.5.1";

        leaf mplsTunnelIndex {
          type leafref {
            path "/mpls-te:MPLS-TE-STD-MIB/mpls-te:mplsTunnelTable/mpls-te:mplsTunnelEntry/mpls-te:mplsTunnelIndex";
          }
        }

        leaf mplsTunnelInstance {
          type leafref {
            path "/mpls-te:MPLS-TE-STD-MIB/mpls-te:mplsTunnelTable/mpls-te:mplsTunnelEntry/mpls-te:mplsTunnelInstance";
          }
        }

        leaf mplsTunnelIngressLSRId {
          type leafref {
            path "/mpls-te:MPLS-TE-STD-MIB/mpls-te:mplsTunnelTable/mpls-te:mplsTunnelEntry/mpls-te:mplsTunnelIngressLSRId";
          }
        }

        leaf mplsTunnelEgressLSRId {
          type leafref {
            path "/mpls-te:MPLS-TE-STD-MIB/mpls-te:mplsTunnelTable/mpls-te:mplsTunnelEntry/mpls-te:mplsTunnelEgressLSRId";
          }
        }

        leaf cmplsTunnelReversePerfPackets {
          type yang:counter32;
          description
           "Number of packets forwarded on the tunnel in the reverse
            direction if it is bidirectional.
            
            This object represents the 32-bit value of the least
            significant part of the 64-bit value if both
            mplsTunnelReversePerfHCPackets and this object
            are returned.
            
            For links that do not transport packets, this packet
            counter cannot be maintained.  For such links, this value
            will return noSuchInstance.";
          smiv2:max-access "read-only";
          smiv2:oid "1.3.6.1.4.1.9.10.146.1.5.1.1";
        }

        leaf cmplsTunnelReversePerfHCPackets {
          type yang:counter64;
          description
           "High-capacity counter for number of packets forwarded on
            the tunnel in the reverse direction if it is
            bidirectional.
            
            For links that do not transport packets, this packet
            counter cannot be maintained.  For such links, this value
            will return noSuchInstance.";
          smiv2:max-access "read-only";
          smiv2:oid "1.3.6.1.4.1.9.10.146.1.5.1.2";
        }

        leaf cmplsTunnelReversePerfErrors {
          type yang:counter32;
          description
           "Number of errored packets received on the tunnel in
            the reverse direction if it is bidirectional.  For links
            that do not transport packets, this packet counter cannot
            be maintained.  For such links, this value will return
            noSuchInstance.";
          smiv2:max-access "read-only";
          smiv2:oid "1.3.6.1.4.1.9.10.146.1.5.1.3";
        }

        leaf cmplsTunnelReversePerfBytes {
          type yang:counter32;
          description
           "Number of bytes forwarded on the tunnel in the reverse
            direction if it is bidirectional.
            
            This object represents the 32-bit value of the least
            significant part of the 64-bit value if both
            mplsTunnelReversePerfHCBytes and this object are returned.
            
            For links that do not transport packets, this packet
            counter cannot be maintained.  For such links, this value
            will return noSuchInstance.";
          smiv2:max-access "read-only";
          smiv2:oid "1.3.6.1.4.1.9.10.146.1.5.1.4";
        }

        leaf cmplsTunnelReversePerfHCBytes {
          type yang:counter64;
          description
           "High-capacity counter for number of bytes forwarded on the
            tunnel in the reverse direction if it is bidirectional.
            
            For links that do not transport packets, this packet
            counter cannot be maintained.  For such links, this value
            will return noSuchInstance.";
          smiv2:max-access "read-only";
          smiv2:oid "1.3.6.1.4.1.9.10.146.1.5.1.5";
        }
      }
    }
  }

  smiv2:alias "cmplsTeExtStdMIB" {
    smiv2:oid "1.3.6.1.4.1.9.10.146";
  }

  smiv2:alias "cmplsTeExtNotifications" {
    smiv2:oid "1.3.6.1.4.1.9.10.146.0";
  }

  smiv2:alias "cmplsTeExtObjects" {
    smiv2:oid "1.3.6.1.4.1.9.10.146.1";
  }

  smiv2:alias "cmplsTeExtConformance" {
    smiv2:oid "1.3.6.1.4.1.9.10.146.2";
  }

  smiv2:alias "cmplsTeExtGroups" {
    smiv2:oid "1.3.6.1.4.1.9.10.146.2.1";
  }

  smiv2:alias "cmplsTeExtCompliances" {
    smiv2:oid "1.3.6.1.4.1.9.10.146.2.2";
  }

}
