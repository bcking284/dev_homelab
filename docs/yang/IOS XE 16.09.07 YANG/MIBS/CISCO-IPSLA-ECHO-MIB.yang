/*
 * Generated by confdc --mib2yang-std
 * Source: mgmt/dmi/model/mib/src/CISCO-IPSLA-ECHO-MIB.mib
 */
/*
 * This YANG module has been generated by smidump 0.5.0:
 *
 *      smidump -f yang CISCO-IPSLA-ECHO-MIB
 *
 * Do not edit. Edit the source file instead!
 */

module CISCO-IPSLA-ECHO-MIB {

  namespace "urn:ietf:params:xml:ns:yang:smiv2:CISCO-IPSLA-ECHO-MIB";
  prefix CISCO-IPSLA-ECHO-MIB;

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  organization
   "Cisco Systems, Inc.";

  contact
   "Cisco Systems, Inc.
    Customer Service
    
    Postal: 170 W Tasman Drive
    San Jose, CA 95134
    
    Tel: +1 800 553 NETS
    Email: cs-ipsla@cisco.com";

  description
   "This MIB module defines the templates for IP SLA operations of
    ICMP echo, UDP echo and TCP connect.
    
    The ICMP echo operation measures end-to-end response time between 
    a Cisco router and any IP enabled device by computing the time
    taken between sending an ICMP echo request message to the 
    destination and receiving an ICMP echo reply.
    
    
    The UDP echo operation measures end-to-end response time between 
    a Cisco router and any IP enabled device by computing the time
    taken between sending an UDP echo request message to the 
    destination and receiving an UDP echo reply.
    
    The TCP connect operation measures end-to-end response time between 
    a Cisco router and any IP enabled device by computing the time
    taken to perform a TCP connect operation.";

  revision 2007-08-16 {
    description
     "Initial version of this MIB module.";
  }


  container CISCO-IPSLA-ECHO-MIB {
    config false;

    container cipslaIcmpEchoTmplTable {
      description
       "A table that contains ICMP echo template definitions.";
      smiv2:oid "1.3.6.1.4.1.9.9.636.1.1";

      list cipslaIcmpEchoTmplEntry {
        key "cipslaIcmpEchoTmplName";
        description
         "A row entry representing an IPSLA ICMP echo template.";
        smiv2:oid "1.3.6.1.4.1.9.9.636.1.1.1";

        leaf cipslaIcmpEchoTmplName {
          type snmp-framework:SnmpAdminString {
            length "1..64";
          }
          description
           "This field is used to specify the ICMP echo template name.";
          smiv2:max-access "not-accessible";
          smiv2:oid "1.3.6.1.4.1.9.9.636.1.1.1.1";
        }

        leaf cipslaIcmpEchoTmplDescription {
          type snmp-framework:SnmpAdminString {
            length "0..128";
          }
          description
           "This field is used to provide description for the ICMP echo
            template.";
          smiv2:defval "";
          smiv2:max-access "read-write";
          smiv2:oid "1.3.6.1.4.1.9.9.636.1.1.1.2";
        }

        leaf cipslaIcmpEchoTmplSrcAddrType {
          type inet-address:InetAddressType;
          description
           "An enumerated value which specifies the IP address type
            of the source. It must be used along with the
            cipslaIcmpEchoTmplSrcAddr object.";
          smiv2:defval "ipv4";
          smiv2:max-access "read-write";
          smiv2:oid "1.3.6.1.4.1.9.9.636.1.1.1.3";
        }

        leaf cipslaIcmpEchoTmplSrcAddr {
          type inet-address:InetAddress;
          description
           "A string which specifies the IP address of the source.";
          smiv2:max-access "read-write";
          smiv2:oid "1.3.6.1.4.1.9.9.636.1.1.1.4";
        }

        leaf cipslaIcmpEchoTmplTimeOut {
          type uint32 {
            range "0..604800000";
          }
          units "milliseconds";
          description
           "Specifies the duration to wait for a IP SLA operation
            completion. 
            
            For connection oriented protocols, this may cause the
            connection to be closed by the operation.  Once closed, it
            will be assumed that the connection reestablishment
            will be performed.  To prevent unwanted closure of
            connections, be sure to set this value to a realistic
            connection timeout.";
          smiv2:defval "5000";
          smiv2:max-access "read-write";
          smiv2:oid "1.3.6.1.4.1.9.9.636.1.1.1.5";
        }

        leaf cipslaIcmpEchoTmplVerifyData {
          type boolean;
          description
           "When set to true, the resulting data in each IP SLA
            operation is compared with the expected data.  This
            includes checking header information (if possible) and
            exact packet size.";
          smiv2:defval "false";
          smiv2:max-access "read-write";
          smiv2:oid "1.3.6.1.4.1.9.9.636.1.1.1.6";
        }

        leaf cipslaIcmpEchoTmplReqDataSize {
          type uint32 {
            range "0..16384";
          }
          units "octets";
          description
           "This object represents the number of octets to be
            placed into the ARR Data portion of the request
            message, when using SNA protocols.
            
            For non-ARR protocols' IP SLA request/responses,
            this value represents the native payload size.
            
            REMEMBER:  The ARR Header overhead is not included
                       in this value.";
          smiv2:defval "28";
          smiv2:max-access "read-write";
          smiv2:oid "1.3.6.1.4.1.9.9.636.1.1.1.7";
        }

        leaf cipslaIcmpEchoTmplTOS {
          type uint32 {
            range "0..255";
          }
          description
           "This object represents the type of service octet in an
            IP header.";
          reference
           "Refer to the following documents for TOS definition.
            RFC791/1349  for IPv4, IPv6, draft-ietf-diffserv-header-02.txt";
          smiv2:defval "0";
          smiv2:max-access "read-write";
          smiv2:oid "1.3.6.1.4.1.9.9.636.1.1.1.8";
        }

        leaf cipslaIcmpEchoTmplVrfName {
          type snmp-framework:SnmpAdminString {
            length "0..32";
          }
          description
           "This field is used to specify the VRF name with
            which the IP SLA operation will be used. For regular IP SLA
            operation this field should not be configured. The agent
            will use this field to identify the VRF routing table for
            this operation.";
          smiv2:defval "";
          smiv2:max-access "read-write";
          smiv2:oid "1.3.6.1.4.1.9.9.636.1.1.1.9";
        }

        leaf cipslaIcmpEchoTmplThreshold {
          type uint32 {
            range "0..2147483647";
          }
          units "milliseconds";
          description
           "This object defines an administrative threshold limit.
            If the IP SLA operation time exceeds this limit and if the
            condition specified in cipslaIcmpEchoTmplHistFilter is
            satisfied, one threshold crossing occurrence will be counted.";
          smiv2:defval "5000";
          smiv2:max-access "read-write";
          smiv2:oid "1.3.6.1.4.1.9.9.636.1.1.1.10";
        }

        leaf cipslaIcmpEchoTmplHistLives {
          type uint32 {
            range "0..2";
          }
          description
           "The maximum number of history lives to record.  A life
            is defined by the countdown (or transition) to zero 
            by the cipslaAutoGroupScheduleLife object.  A new life is
            created when the same conceptual control row is
            restarted via the transition of the 
            cipslaAutoGroupScheduleLife object and its subsequent 
            countdown.
            
            The value of zero will shut off all data collection.";
          smiv2:defval "0";
          smiv2:max-access "read-write";
          smiv2:oid "1.3.6.1.4.1.9.9.636.1.1.1.11";
        }

        leaf cipslaIcmpEchoTmplHistBuckets {
          type uint32 {
            range "1..60";
          }
          description
           "The maximum number of history buckets to record.
            This value is set to the number of operations 
            to keep per lifetime.
            
            After cipslaIcmpEchoTmplHistBuckets are filled, the 
            oldest entries are deleted and the most recent
            cipslaIcmpEchoTmplHistBuckets buckets are retained.";
          smiv2:defval "15";
          smiv2:max-access "read-write";
          smiv2:oid "1.3.6.1.4.1.9.9.636.1.1.1.12";
        }

        leaf cipslaIcmpEchoTmplHistFilter {
          type enumeration {
            enum "none" {
              value "1";
            }
            enum "all" {
              value "2";
            }
            enum "overThreshold" {
              value "3";
            }
            enum "failures" {
              value "4";
            }
          }
          description
           "Defines a filter for adding RTT results to the history
            buffer:
            
            none(1)          - no history is recorded
            all(2)           - the results of all completion times 
                               and failed completions are recorded
            overThreshold(3) - the results of completion times
                               over cipslaIcmpEchoTmplThreshold are 
                               recorded.
            failures(4)      - the results of failed operations (only) 
                               are recorded.";
          smiv2:defval "none";
          smiv2:max-access "read-write";
          smiv2:oid "1.3.6.1.4.1.9.9.636.1.1.1.13";
        }

        leaf cipslaIcmpEchoTmplStatsHours {
          type uint32 {
            range "0..25";
          }
          units "hours";
          description
           "The maximum number of hours for which statistics are
            maintained. Specifically this is the number of hourly 
            groups to keep before rolling over.
            
            The value of one is not advisable because the hourly
            group will close and immediately be deleted before
            the network management station will have the
            opportunity to retrieve the statistics.
            
            The value of zero will shut off data collection.";
          smiv2:defval "2";
          smiv2:max-access "read-write";
          smiv2:oid "1.3.6.1.4.1.9.9.636.1.1.1.14";
        }

        leaf cipslaIcmpEchoTmplDistBuckets {
          type uint32 {
            range "1..20";
          }
          description
           "The maximum number of statistical distribution
            buckets to accumulate.
            
            Since this index does not rollover, only the first
            cipslaIcmpEchoTmplStatsNumDistBuckets will be kept.
            
            The last cipslaIcmpEchoTmplStatsNumDistBucket will
            contain all entries from its distribution interval
            start point to infinity.";
          smiv2:defval "1";
          smiv2:max-access "read-write";
          smiv2:oid "1.3.6.1.4.1.9.9.636.1.1.1.15";
        }

        leaf cipslaIcmpEchoTmplDistInterval {
          type uint32 {
            range "1..100";
          }
          units "milliseconds";
          description
           "The statistical distribution buckets interval.
            
            Distribution Bucket Example:
            
            cipslaIcmpEchoTmplDistBuckets = 5 buckets
            cipslaIcmpEchoTmplDistInterval = 10 milliseconds
            
            | Bucket 1 | Bucket 2 | Bucket 3 | Bucket 4 | Bucket 5  |
            |  0-9 ms  | 10-19 ms | 20-29 ms | 30-39 ms | 40-Inf ms |
            
            Odd Example:
            
            cipslaIcmpEchoTmplDistBuckets = 1 buckets
            cipslaIcmpEchoTmplDistInterval = 10 milliseconds
            
            | Bucket 1  |
            |  0-Inf ms |
            
            Thus, this odd example shows that the value of
            cipslaIcmpEchoTmplDistInterval does not apply when
            cipslaIcmpEchoTmplDistBuckets is one.";
          smiv2:defval "20";
          smiv2:max-access "read-write";
          smiv2:oid "1.3.6.1.4.1.9.9.636.1.1.1.16";
        }

        leaf cipslaIcmpEchoTmplStorageType {
          type snmpv2-tc:StorageType;
          description
           "The storage type of this conceptual row.";
          smiv2:defval "nonVolatile";
          smiv2:max-access "read-write";
          smiv2:oid "1.3.6.1.4.1.9.9.636.1.1.1.17";
        }

        leaf cipslaIcmpEchoTmplRowStatus {
          type snmpv2-tc:RowStatus;
          description
           "The status of the conceptual ICMP echo template control row.
            When the status is active, all the read-create objects in that 
            row can be modified.";
          smiv2:max-access "read-write";
          smiv2:oid "1.3.6.1.4.1.9.9.636.1.1.1.18";
        }
      }
    }

    container cipslaUdpEchoTmplTable {
      description
       "A table that contains UDP echo template specific definitions.";
      smiv2:oid "1.3.6.1.4.1.9.9.636.1.2";

      list cipslaUdpEchoTmplEntry {
        key "cipslaUdpEchoTmplName";
        description
         "A row entry representing an IPSLA UDP echo template.";
        smiv2:oid "1.3.6.1.4.1.9.9.636.1.2.1";

        leaf cipslaUdpEchoTmplName {
          type snmp-framework:SnmpAdminString {
            length "1..64";
          }
          description
           "A string which specifies the UDP echo template name.";
          smiv2:max-access "not-accessible";
          smiv2:oid "1.3.6.1.4.1.9.9.636.1.2.1.1";
        }

        leaf cipslaUdpEchoTmplDescription {
          type snmp-framework:SnmpAdminString {
            length "0..128";
          }
          description
           "A string which provides description to the UDP echo template.";
          smiv2:defval "";
          smiv2:max-access "read-write";
          smiv2:oid "1.3.6.1.4.1.9.9.636.1.2.1.2";
        }

        leaf cipslaUdpEchoTmplControlEnable {
          type boolean;
          description
           "If this object is enabled, then the IP SLA application
            will send control messages to a responder, residing on the
            target router to respond to the data request packets being
            sent by the source router.";
          smiv2:defval "true";
          smiv2:max-access "read-write";
          smiv2:oid "1.3.6.1.4.1.9.9.636.1.2.1.3";
        }

        leaf cipslaUdpEchoTmplSrcAddrType {
          type inet-address:InetAddressType;
          description
           "An enumerated value which specifies the IP address type
            of the source. It must be used along with the
            cipslaUdpEchoTmplSrcAddr object.";
          smiv2:defval "ipv4";
          smiv2:max-access "read-write";
          smiv2:oid "1.3.6.1.4.1.9.9.636.1.2.1.4";
        }

        leaf cipslaUdpEchoTmplSrcAddr {
          type inet-address:InetAddress;
          description
           "A string which specifies the IP address of the source.";
          smiv2:max-access "read-write";
          smiv2:oid "1.3.6.1.4.1.9.9.636.1.2.1.5";
        }

        leaf cipslaUdpEchoTmplSrcPort {
          type inet:port-number;
          description
           "This object represents the source's port number. If this
            object is not specified, the application will get a
            port allocated by the system.";
          smiv2:defval "0";
          smiv2:max-access "read-write";
          smiv2:oid "1.3.6.1.4.1.9.9.636.1.2.1.6";
        }

        leaf cipslaUdpEchoTmplTimeOut {
          type uint32 {
            range "0..604800000";
          }
          units "milliseconds";
          description
           "Specifies the duration to wait for an IP SLA operation
            completion.
            
            For connection oriented protocols, this may cause the
            connection to be closed by the operation.  Once closed, it
            will be assumed that the connection reestablishment
            will be performed.  To prevent unwanted closure of
            connections, be sure to set this value to a realistic
            connection timeout.";
          smiv2:defval "5000";
          smiv2:max-access "read-write";
          smiv2:oid "1.3.6.1.4.1.9.9.636.1.2.1.7";
        }

        leaf cipslaUdpEchoTmplVerifyData {
          type boolean;
          description
           "When set to true, the resulting data in each IP SLA
            operation is compared with the expected data.  This
            includes checking header information (if possible) and
            exact packet size.";
          smiv2:defval "false";
          smiv2:max-access "read-write";
          smiv2:oid "1.3.6.1.4.1.9.9.636.1.2.1.8";
        }

        leaf cipslaUdpEchoTmplReqDataSize {
          type uint32 {
            range "4..1500";
          }
          units "octets";
          description
           "This object represents the number of octets to be
            placed into the ARR Data portion of the request
            message, when using SNA protocols.
            
            For non-ARR protocols' RTT request/responses,
            this value represents the native payload size.
            
            REMEMBER:  The ARR Header overhead is not included
                       in this value.";
          smiv2:defval "16";
          smiv2:max-access "read-write";
          smiv2:oid "1.3.6.1.4.1.9.9.636.1.2.1.9";
        }

        leaf cipslaUdpEchoTmplTOS {
          type uint32 {
            range "0..255";
          }
          description
           "This object represents the type of service octet in an
            IP header.";
          reference
           "Refer to the following documents for TOS definition.
            RFC791/1349  for IPv4, IPv6, draft-ietf-diffserv-header-02.txt";
          smiv2:defval "0";
          smiv2:max-access "read-write";
          smiv2:oid "1.3.6.1.4.1.9.9.636.1.2.1.10";
        }

        leaf cipslaUdpEchoTmplVrfName {
          type snmp-framework:SnmpAdminString {
            length "0..32";
          }
          description
           "This field is used to specify the VRF name with
            which the IP SLA operation will be used. For regular IP SLA
            operation this field should not be configured. The agent
            will use this field to identify the VRF routing Table for
            this operation.";
          smiv2:defval "";
          smiv2:max-access "read-write";
          smiv2:oid "1.3.6.1.4.1.9.9.636.1.2.1.11";
        }

        leaf cipslaUdpEchoTmplThreshold {
          type uint32 {
            range "0..2147483647";
          }
          units "milliseconds";
          description
           "This object defines an administrative threshold limit.
            If the IP SLA operation time exceeds this limit and if the
            condition specified in cipslaUdpEchoTmplHistFilter is 
            satisfied, one threshold crossing occurrence will be counted.";
          smiv2:defval "5000";
          smiv2:max-access "read-write";
          smiv2:oid "1.3.6.1.4.1.9.9.636.1.2.1.12";
        }

        leaf cipslaUdpEchoTmplHistLives {
          type uint32 {
            range "0..2";
          }
          description
           "The maximum number of history lives to record.  A life
            is defined by the countdown (or transition) to zero 
            by the cipslaAutoGroupScheduleLife object.  A new life is
            created when the same conceptual control row is
            restarted via the transition of the 
            cipslaAutoGroupScheduleLife object and its subsequent 
            countdown.
            
            The value of zero will shut off all data collection.";
          smiv2:defval "0";
          smiv2:max-access "read-write";
          smiv2:oid "1.3.6.1.4.1.9.9.636.1.2.1.13";
        }

        leaf cipslaUdpEchoTmplHistBuckets {
          type uint32 {
            range "1..60";
          }
          description
           "The maximum number of history buckets to record.
            This value should be set to the number of operations 
            to keep per lifetime.
            
            After cipslaUdpEchoTmplHistBuckets are filled, the 
            oldest entries are deleted and the most recent
            cipslaUdpEchoTmplHistBuckets buckets are retained.";
          smiv2:defval "15";
          smiv2:max-access "read-write";
          smiv2:oid "1.3.6.1.4.1.9.9.636.1.2.1.14";
        }

        leaf cipslaUdpEchoTmplHistFilter {
          type enumeration {
            enum "none" {
              value "1";
            }
            enum "all" {
              value "2";
            }
            enum "overThreshold" {
              value "3";
            }
            enum "failures" {
              value "4";
            }
          }
          description
           "Defines a filter for adding RTT results to the history
            buffer:
            
            none(1)          - no history is recorded
            all(2)           - the results of all completion times 
                               and failed completions are recorded
            overThreshold(3) - the results of completion times
                               over cipslaUdpEchoTmplThreshold are 
                               recorded.
            failures(4)      - the results of failed operations (only) 
                               are recorded.";
          smiv2:defval "none";
          smiv2:max-access "read-write";
          smiv2:oid "1.3.6.1.4.1.9.9.636.1.2.1.15";
        }

        leaf cipslaUdpEchoTmplStatsHours {
          type uint32 {
            range "0..25";
          }
          units "hours";
          description
           "The maximum number of hours for which statistics are
            maintained. Specifically this is the number of hourly 
            groups to keep before rolling over.
            
            The value of one is not advisable because the hourly
            group will close and immediately be deleted before
            the network management station will have the
            opportunity to retrieve the statistics.
            
            The value of zero will shut off data collection.";
          smiv2:defval "2";
          smiv2:max-access "read-write";
          smiv2:oid "1.3.6.1.4.1.9.9.636.1.2.1.16";
        }

        leaf cipslaUdpEchoTmplDistBuckets {
          type uint32 {
            range "1..20";
          }
          description
           "The maximum number of statistical distribution
            buckets to accumulate.
            
            Since this index does not rollover, only the first
            cipslaUdpEchoTmplStatsNumDistBuckets will be kept.
            
            The last cipslaUdpEchoTmplStatsNumDistBuckets will
            contain all entries from its distribution interval
            start point to infinity.";
          smiv2:defval "1";
          smiv2:max-access "read-write";
          smiv2:oid "1.3.6.1.4.1.9.9.636.1.2.1.17";
        }

        leaf cipslaUdpEchoTmplDistInterval {
          type uint32 {
            range "1..100";
          }
          units "milliseconds";
          description
           "The statistical distribution buckets interval.
            
            Distribution Bucket Example:
            
            cipslaUdpEchoTmplDistBuckets = 5 buckets
            cipslaUdpEchoTmplDistInterval = 10 milliseconds
            
            | Bucket 1 | Bucket 2 | Bucket 3 | Bucket 4 | Bucket 5  |
            |  0-9 ms  | 10-19 ms | 20-29 ms | 30-39 ms | 40-Inf ms |
            
            Odd Example:
            
            cipslaUdpEchoTmplDistBuckets = 1 buckets
            cipslaUdpEchoTmplDistInterval = 10 milliseconds
            
            | Bucket 1  |
            |  0-Inf ms |
            
            Thus, this odd example shows that the value of
            cipslaUdpEchoTmplDistInterval does not apply when
            cipslaUdpEchoTmplDistBuckets is one.";
          smiv2:defval "20";
          smiv2:max-access "read-write";
          smiv2:oid "1.3.6.1.4.1.9.9.636.1.2.1.18";
        }

        leaf cipslaUdpEchoTmplStorageType {
          type snmpv2-tc:StorageType;
          description
           "The storage type of this conceptual row.";
          smiv2:defval "nonVolatile";
          smiv2:max-access "read-write";
          smiv2:oid "1.3.6.1.4.1.9.9.636.1.2.1.19";
        }

        leaf cipslaUdpEchoTmplRowStatus {
          type snmpv2-tc:RowStatus;
          description
           "The status of the conceptual UDP echo template control row.
            When the status is active, all the read-create objects in 
            that row can be modified.";
          smiv2:max-access "read-write";
          smiv2:oid "1.3.6.1.4.1.9.9.636.1.2.1.20";
        }
      }
    }

    container cipslaTcpConnTmplTable {
      description
       "A table that contains TCP connect template specific definitions.";
      smiv2:oid "1.3.6.1.4.1.9.9.636.1.3";

      list cipslaTcpConnTmplEntry {
        key "cipslaTcpConnTmplName";
        description
         "A row entry representing an IPSLA TCP connect template.";
        smiv2:oid "1.3.6.1.4.1.9.9.636.1.3.1";

        leaf cipslaTcpConnTmplName {
          type snmp-framework:SnmpAdminString {
            length "1..64";
          }
          description
           "A string which specifies the TCP connect template name.";
          smiv2:max-access "not-accessible";
          smiv2:oid "1.3.6.1.4.1.9.9.636.1.3.1.1";
        }

        leaf cipslaTcpConnTmplDescription {
          type snmp-framework:SnmpAdminString {
            length "0..128";
          }
          description
           "A string which provides description for the TCP connect template.";
          smiv2:defval "";
          smiv2:max-access "read-write";
          smiv2:oid "1.3.6.1.4.1.9.9.636.1.3.1.2";
        }

        leaf cipslaTcpConnTmplControlEnable {
          type boolean;
          description
           "If this object is enabled, then the IP SLA application
            will send control messages to a responder, residing on the
            target router to respond to the data request packets being
            sent by the source router.";
          smiv2:defval "true";
          smiv2:max-access "read-write";
          smiv2:oid "1.3.6.1.4.1.9.9.636.1.3.1.3";
        }

        leaf cipslaTcpConnTmplSrcAddrType {
          type inet-address:InetAddressType;
          description
           "An enumerated value which specifies the IP address type
            of the source. It must be used along with the
            cipslaTcpConnTmplSrcAddr object.";
          smiv2:defval "ipv4";
          smiv2:max-access "read-write";
          smiv2:oid "1.3.6.1.4.1.9.9.636.1.3.1.4";
        }

        leaf cipslaTcpConnTmplSrcAddr {
          type inet-address:InetAddress;
          description
           "A string which specifies the IP address of the source.";
          smiv2:max-access "read-write";
          smiv2:oid "1.3.6.1.4.1.9.9.636.1.3.1.5";
        }

        leaf cipslaTcpConnTmplSrcPort {
          type inet:port-number;
          description
           "This object represents the source's port number. If this
            object is not specified, the application will get a
            port allocated by the system.";
          smiv2:defval "0";
          smiv2:max-access "read-write";
          smiv2:oid "1.3.6.1.4.1.9.9.636.1.3.1.6";
        }

        leaf cipslaTcpConnTmplTimeOut {
          type uint32 {
            range "0..604800000";
          }
          units "milliseconds";
          description
           "Specifies the duration to wait for an IP SLA operation
            completion.
            
            For connection oriented protocols, this may cause the
            connection to be closed by the operation.  Once closed, it
            will be assumed that the connection reestablishment
            will be performed.  To prevent unwanted closure of
            connections, be sure to set this value to a realistic
            connection timeout.";
          smiv2:defval "5000";
          smiv2:max-access "read-write";
          smiv2:oid "1.3.6.1.4.1.9.9.636.1.3.1.7";
        }

        leaf cipslaTcpConnTmplVerifyData {
          type boolean;
          description
           "When set to true, the resulting data in each IP SLA
            operation is compared with the expected data.  This
            includes checking header information (if possible) and
            exact packet size.";
          smiv2:defval "false";
          smiv2:max-access "read-write";
          smiv2:oid "1.3.6.1.4.1.9.9.636.1.3.1.8";
        }

        leaf cipslaTcpConnTmplTOS {
          type uint32 {
            range "0..255";
          }
          description
           "This object represents the type of service octet in an
            IP header.";
          reference
           "Refer to the following documents for TOS definition.
            RFC791/1349  for IPv4, IPv6, draft-ietf-diffserv-header-02.txt";
          smiv2:defval "0";
          smiv2:max-access "read-write";
          smiv2:oid "1.3.6.1.4.1.9.9.636.1.3.1.9";
        }

        leaf cipslaTcpConnTmplThreshold {
          type uint32 {
            range "0..2147483647";
          }
          units "milliseconds";
          description
           "This object defines an administrative threshold limit.
            If the IP SLA operation time exceeds this limit and if the
            condition specified in cipslaTcpConnTmplHistFilter is 
            satisfied, one threshold crossing occurrence will be counted.";
          smiv2:defval "5000";
          smiv2:max-access "read-write";
          smiv2:oid "1.3.6.1.4.1.9.9.636.1.3.1.10";
        }

        leaf cipslaTcpConnTmplHistLives {
          type uint32 {
            range "0..2";
          }
          description
           "The maximum number of history lives to record.  A life
            is defined by the countdown (or transition) to zero 
            by the cipslaAutoGroupScheduleLife object.  A new life is
            created when the same conceptual control row is
            restarted via the transition of the 
            cipslaAutoGroupScheduleLife object and its subsequent 
            countdown.
            
            The value of zero will shut off all data collection.";
          smiv2:defval "0";
          smiv2:max-access "read-write";
          smiv2:oid "1.3.6.1.4.1.9.9.636.1.3.1.11";
        }

        leaf cipslaTcpConnTmplHistBuckets {
          type uint32 {
            range "1..60";
          }
          description
           "The maximum number of history buckets to record.
            This value should be set to the number of operations 
            to keep per lifetime.
            
            After cipslaTcpConnTmplHistBuckets are filled, the 
            oldest entries are deleted and the most recent
            cipslaTcpConnTmplHistBuckets buckets are retained.";
          smiv2:defval "15";
          smiv2:max-access "read-write";
          smiv2:oid "1.3.6.1.4.1.9.9.636.1.3.1.12";
        }

        leaf cipslaTcpConnTmplHistFilter {
          type enumeration {
            enum "none" {
              value "1";
            }
            enum "all" {
              value "2";
            }
            enum "overThreshold" {
              value "3";
            }
            enum "failures" {
              value "4";
            }
          }
          description
           "Defines a filter for adding RTT results to the history
            buffer:
            
            none(1)          - no history is recorded
            all(2)           - the results of all completion times 
                               and failed completions are recorded
            overThreshold(3) - the results of completion times
                               over cipslaTcpConnTmplThreshold are 
                               recorded.
            failures(4)      - the results of failed operations (only) 
                               are recorded.";
          smiv2:defval "none";
          smiv2:max-access "read-write";
          smiv2:oid "1.3.6.1.4.1.9.9.636.1.3.1.13";
        }

        leaf cipslaTcpConnTmplStatsHours {
          type uint32 {
            range "0..25";
          }
          units "hours";
          description
           "The maximum number of hours for which statistics are
            maintained. Specifically this is the number of hourly 
            groups to keep before rolling over.
            
            The value of one is not advisable because the hourly
            group will close and immediately be deleted before
            the network management station will have the
            opportunity to retrieve the statistics.
            
            The value of zero will shut off data collection.";
          smiv2:defval "2";
          smiv2:max-access "read-write";
          smiv2:oid "1.3.6.1.4.1.9.9.636.1.3.1.14";
        }

        leaf cipslaTcpConnTmplDistBuckets {
          type uint32 {
            range "1..20";
          }
          description
           "The maximum number of statistical distribution
            buckets to accumulate.
            
            Since this index does not rollover, only the first
            cipslaTcpConnTmplDistBuckets will be kept.
            
            The last cipslaTcpConnTmplDistBuckets will
            contain all entries from its distribution interval
            start point to infinity.";
          smiv2:defval "1";
          smiv2:max-access "read-write";
          smiv2:oid "1.3.6.1.4.1.9.9.636.1.3.1.15";
        }

        leaf cipslaTcpConnTmplDistInterval {
          type uint32 {
            range "1..100";
          }
          units "milliseconds";
          description
           "The statistical distribution buckets interval.
            
            Distribution Bucket Example:
            
            cipslaTcpConnTmplDistBuckets = 5 buckets
            cipslaTcpConnTmplDistInterval = 10 milliseconds
            
            | Bucket 1 | Bucket 2 | Bucket 3 | Bucket 4 | Bucket 5  |
            |  0-9 ms  | 10-19 ms | 20-29 ms | 30-39 ms | 40-Inf ms |
            
            Odd Example:
            
            cipslaTcpConnTmplDistBuckets = 1 buckets
            cipslaTcpConnTmplDistInterval = 10 milliseconds
            
            | Bucket 1  |
            |  0-Inf ms |
            
            Thus, this odd example shows that the value of
            cipslaTcpConnTmplDistInterval does not apply when
            cipslaTcpConnTmplDistBuckets is one.";
          smiv2:defval "20";
          smiv2:max-access "read-write";
          smiv2:oid "1.3.6.1.4.1.9.9.636.1.3.1.16";
        }

        leaf cipslaTcpConnTmplStorageType {
          type snmpv2-tc:StorageType;
          description
           "The storage type of this conceptual row.";
          smiv2:defval "nonVolatile";
          smiv2:max-access "read-write";
          smiv2:oid "1.3.6.1.4.1.9.9.636.1.3.1.17";
        }

        leaf cipslaTcpConnTmplRowStatus {
          type snmpv2-tc:RowStatus;
          description
           "The status of the conceptual tcp connect control row.
            When the status is active, all the read-create objects 
            in that row can be modified.";
          smiv2:max-access "read-write";
          smiv2:oid "1.3.6.1.4.1.9.9.636.1.3.1.18";
        }
      }
    }
  }

  smiv2:alias "ciscoIpSlaEchoMIB" {
    smiv2:oid "1.3.6.1.4.1.9.9.636";
  }

  smiv2:alias "ciscoIpSlaEchoMIBNotifs" {
    smiv2:oid "1.3.6.1.4.1.9.9.636.0";
  }

  smiv2:alias "ciscoIpSlaEchoMIBObjects" {
    smiv2:oid "1.3.6.1.4.1.9.9.636.1";
  }

  smiv2:alias "ciscoIpSlaEchoMIBConform" {
    smiv2:oid "1.3.6.1.4.1.9.9.636.2";
  }

  smiv2:alias "ciscoIpSlaEchoMIBCompliances" {
    smiv2:oid "1.3.6.1.4.1.9.9.636.2.1";
  }

  smiv2:alias "ciscoIpSlaEchoMIBGroups" {
    smiv2:oid "1.3.6.1.4.1.9.9.636.2.2";
  }

}
