/*
 * Generated by confdc --mib2yang-std
 * Source: mgmt/dmi/model/mib/src/DOCS-QOS-MIB.mib
 */
/*
 * This YANG module has been generated by smidump 0.5.0:
 *
 *      smidump -f yang DOCS-QOS-MIB
 *
 * Do not edit. Edit the source file instead!
 */

module DOCS-QOS-MIB {

  namespace "urn:ietf:params:xml:ns:yang:smiv2:DOCS-QOS-MIB";
  prefix DOCS-QOS-MIB;

  import IF-MIB {
    prefix "if-mib";
  }

  import INET-ADDRESS-MIB {
    prefix "inet-address";
  }

  import SNMPv2-TC {
    prefix "snmpv2-tc";
  }

  import ietf-inet-types {
    prefix "inet";
  }

  import ietf-yang-smiv2 {
    prefix "smiv2";
  }

  import ietf-yang-types {
    prefix "yang";
  }

  organization
   "IETF IPCDN Working Group";

  contact
   "
    Co-Author: Michael Patrick
    Postal:    Motorola ISG
               20 Cabot Blvd, MS M4-30
               Mansfield, MA 02048-1193
               U.S.A.
    Phone:     +1 508 261 5707
    E-mail:    michael.patrick@motorola.com
    
    Co-Author: William Murwin
    Postal:    Motorola BCS
               20 Cabot Blvd, MS M4-25
               Mansfield, MA 02048-1193
               U.S.A.
    Phone:     +1 508 261 5578
    E-mail:    w.murwin@motorola.com";

  description
   "This is the management information for
    Quality Of Service (QOS) for DOCSIS 1.1.";

  revision 2001-11-09 {
    description
     "Published as draft-ietf-ipcdn-qos-mib-06.txt.
      
      Changes from qos-mib-05 include:
      -Deprecated objects that were of type IpAddress
       and added new objects that were of type
       InetAddressType and InetAddress, to support both
       IPv4 and IPv6 in the docsQosPktClassTable.
      -Clarified the default value of the
       docsQosPktClassIpDestMask and
       docsQosPktClassIpSourceMask.
      -Corrected the description of the individual bits
       that make up the docsQosParamsSetRequestPolicyOct.
      -Corrected the spelling of docsCableMaclayer in the
       description of the docsQosServiceFlowLogIfIndex.
      -Clarified that some of counters from the
       docsQosDynamicServiceStatsTable, include retries.
      -Changed references to the latest Data-Over-Cable
       Service Interface Specifications: Radio Frequency
       Interface Specification.
      -Added objects that were removed from earlier
       revisions of the mib, as obsolete.
      -Clarified the Cable Modem's implementation of the
       docsQosParamSetTosAndMask.
      -Change the description of objects within the
       docsQosServiceClassTable, so that they were no longer
       templates for obsolete objects.";
  }

  typedef IfDirection {
    type enumeration {
      enum "downstream" {
        value "1";
      }
      enum "upstream" {
        value "2";
      }
    }
    description
     "Indicates a direction on an RF MAC interface. 
      
      The value downstream(1) is from Cable Modem 
      Termination System to Cable Modem.  
      
      The value upstream(2) is from Cable Modem to 
      Cable Modem Termination System.";
  }

  typedef DOCSQOSBitRate {
    type uint32;
    description
     "The rate of traffic in unit of bits per second.
      Used to specify traffic rate for QOS.";
    smiv2:display-hint "d";
  }

  typedef SchedulingType {
    type enumeration {
      enum "undefined" {
        value "1";
      }
      enum "bestEffort" {
        value "2";
      }
      enum "nonRealTimePollingService" {
        value "3";
      }
      enum "realTimePollingService" {
        value "4";
      }
      enum "unsolictedGrantServiceWithAD" {
        value "5";
      }
      enum "unsolictedGrantService" {
        value "6";
      }
    }
    description
     "The scheduling service provided by a CMTS for an
      upstream service flow. If the parameter is omitted
      from an upstream QOS Parameter Set, this object takes
      the value of bestEffort (2). This parameter must be
      reported as undefined (1) for downstream QOS Parameter
      Sets.";
  }


  container DOCS-QOS-MIB {
    config false;

    container docsQosPktClassTable {
      description
       "This table describes the packet classification
        configured on the CM or CMTS.  
        The model is that a packet either received
        as input from an interface or transmitted 
        for output on an interface may be compared 
        against an ordered list of rules pertaining to
        the packet contents. Each rule is a row of this
        table. A matching rule provides a service flow
        id to to which the packet is classified. 
        All rules need to match for a packet to match 
        a classifier. 
        
        The objects in this row correspond to a set of
        Classifier Encoding parameters in a DOCSIS
        MAC management message. The docsQosPktClassBitMap
        indicates which particular parameters were present
        in the classifier as signalled in the DOCSIS message.
        If the referenced parameter was not present
        in the signalled DOCSIS 1.1 Classifier, the
        corresponding object in this row reports a 
        value as specified in the DESCRIPTION section.";
      smiv2:oid "1.3.6.1.2.1.10.127.7.1.1";

      list docsQosPktClassEntry {
        key "ifIndex docsQosServiceFlowId docsQosPktClassId";
        description
         "An entry in this table provides a single packet
          classifier rule. The index ifIndex is an ifType
          of docsCableMaclayer(127).";
        smiv2:oid "1.3.6.1.2.1.10.127.7.1.1.1";

        leaf ifIndex {
          type leafref {
            path "/if-mib:IF-MIB/if-mib:ifTable/if-mib:ifEntry/if-mib:ifIndex";
          }
        }

        leaf docsQosServiceFlowId {
          type leafref {
            path "/DOCS-QOS-MIB:DOCS-QOS-MIB/DOCS-QOS-MIB:docsQosServiceFlowTable/DOCS-QOS-MIB:docsQosServiceFlowEntry/DOCS-QOS-MIB:docsQosServiceFlowId";
          }
        }

        leaf docsQosPktClassId {
          type int32 {
            range "1..65535";
          }
          description
           "Index assigned to packet classifier entry by 
            the CMTS which is unique per service flow.";
          reference
           "SP-RFIv1.1-I07-010829, Appendix C.2.1.3.2";
          smiv2:max-access "not-accessible";
          smiv2:oid "1.3.6.1.2.1.10.127.7.1.1.1.1";
        }

        leaf docsQosPktClassDirection {
          type DOCS-QOS-MIB:IfDirection;
          description
           "Indicates the direction to which the classifier 
            is applied.";
          smiv2:max-access "read-only";
          smiv2:oid "1.3.6.1.2.1.10.127.7.1.1.1.2";
        }

        leaf docsQosPktClassPriority {
          type int32 {
            range "0..255";
          }
          description
           "The value specifies the order of evaluation
            of the classifiers.
            The higher the value the higher the priority.
            The value of 0 is used as default in 
            provisioned service flows classifiers. 
            The default value of 64 is used for dynamic 
            service flow classifiers.
            If the referenced parameter is not present
            in a classifier, this object reports the default value
            as defined above.";
          reference
           "SP-RFIv1.1-I07-010829, Appendix C.2.1.3.5";
          smiv2:max-access "read-only";
          smiv2:oid "1.3.6.1.2.1.10.127.7.1.1.1.3";
        }

        leaf docsQosPktClassIpTosLow {
          type binary {
            length "1";
          }
          description
           "The low value of a range of TOS byte values.
            If the referenced parameter is not present
            in a classifier, this object reports the value of 0.";
          reference
           "SP-RFIv1.1-I07-010829, Appendix C.2.1.5.1";
          smiv2:max-access "read-only";
          smiv2:oid "1.3.6.1.2.1.10.127.7.1.1.1.4";
        }

        leaf docsQosPktClassIpTosHigh {
          type binary {
            length "1";
          }
          description
           "The 8-bit high value of a range of TOS byte
            values.
            
            If the referenced parameter is not present
            in a classifier, this object reports the value of 0.";
          reference
           "SP-RFIv1.1-I07-010829, Appendix C.2.1.5.1";
          smiv2:max-access "read-only";
          smiv2:oid "1.3.6.1.2.1.10.127.7.1.1.1.5";
        }

        leaf docsQosPktClassIpTosMask {
          type binary {
            length "1";
          }
          description
           "The mask value is bitwise ANDed with TOS byte 
            in an IP packet and this value is used check 
            range checking of TosLow and TosHigh.
            
            If the referenced parameter is not present
            in a classifier, this object reports the value of 0.";
          reference
           "SP-RFIv1.1-I07-010829, Appendix C.2.1.5.1";
          smiv2:max-access "read-only";
          smiv2:oid "1.3.6.1.2.1.10.127.7.1.1.1.6";
        }

        leaf docsQosPktClassIpProtocol {
          type int32 {
            range "0..258";
          }
          description
           "This object indicates the value of the IP
            Protocol field required for IP packets to match
            this rule. 
            
            The value 256 matches traffic with any IP Protocol 
            value. The value 257 by convention matches both TCP
            and UDP. 
            
            If the referenced parameter is not present
            in a classifier, this object reports the value of 258.";
          reference
           "SP-RFIv1.1-I07-010829, Appendix C.2.1.5.2";
          smiv2:max-access "read-only";
          smiv2:oid "1.3.6.1.2.1.10.127.7.1.1.1.7";
        }

        leaf docsQosPktClassIpSourceAddr {
          type inet:ipv4-address;
          status deprecated;
          description
           "This object is deprecated in favor of the
            object pair docsQosPktClassInetSourceAddrType
            and docsQosPktClassInetSourceAddr. Agents that
            choose to implement this object MUST report
            an address that matches docsQosPktClassInetSourceAddr
            object as long as docsQosPktClassInetSourceAddrType is
            ipv4(1). Otherwise, the value of this object shall be
            0.0.0.0.";
          reference
           "SP-RFIv1.1-I07-010829, Appendix C.2.1.5.3";
          smiv2:max-access "read-only";
          smiv2:oid "1.3.6.1.2.1.10.127.7.1.1.1.8";
        }

        leaf docsQosPktClassIpSourceMask {
          type inet:ipv4-address;
          status deprecated;
          description
           "This object is deprecated in favor of the
            object pair docsQosPktClassInetSourceMaskType
            and docsQosPktClassInetSourceMask. Agents that
            choose to implement this object MUST report
            an address that matches docsQosPktClassInetSourceMask
            object as long as docsQosPktClassInetSourceMaskType is
            ipv4(1). Otherwise, the value of this object shall be
            255.255.255.255.
            
            SNMP mangers should note that agent implementation
            of previous versions of this MIB report 0.0.0.0 as the
            value when the reference parameter is not present,
            rather than 255.255.255.255.";
          reference
           "SP-RFIv1.1-I07-010829, Appendix C.2.1.5.4";
          smiv2:max-access "read-only";
          smiv2:oid "1.3.6.1.2.1.10.127.7.1.1.1.9";
        }

        leaf docsQosPktClassIpDestAddr {
          type inet:ipv4-address;
          status deprecated;
          description
           "This object is deprecated in favor of the
            object pair docsQosPktClassInetDestAddrType
            and docsQosPktClassInetDestAddr. Agents that
            choose to implement this object MUST report
            an address that matches docsQosPktClassInetDestAddr
            object as long as docsQosPktClassInetDestAddrType is
            ipv4(1). Otherwise, the value of this object shall be
            0.0.0.0.";
          reference
           "SP-RFIv1.1-I07-010829, Appendix C.2.1.5.5";
          smiv2:max-access "read-only";
          smiv2:oid "1.3.6.1.2.1.10.127.7.1.1.1.10";
        }

        leaf docsQosPktClassIpDestMask {
          type inet:ipv4-address;
          status deprecated;
          description
           "This object is deprecated in favor of the
            object pair docsQosPktClassInetDestMaskType
            and docsQosPktClassInetDestMask. Agents that
            choose to implement this object MUST report
            an address that matches docsQosPktClassInetDestMask
            object as long as docsQosPktClassInetDestMaskType is
            ipv4(1). Otherwise, the value of this object shall be
            255.255.255.255.
            
            SNMP mangers should note that agent implementation
            of previous versions of this MIB report 0.0.0.0 as the
            value when the reference parameter is not present,
            rather than 255.255.255.255.";
          reference
           "SP-RFIv1.1-I07-010829, Appendix C.2.1.5.6";
          smiv2:max-access "read-only";
          smiv2:oid "1.3.6.1.2.1.10.127.7.1.1.1.11";
        }

        leaf docsQosPktClassSourcePortStart {
          type int32 {
            range "0..65535";
          }
          description
           "This object specifies the low end inclusive
            range of TCP/UDP source port numbers to which
            a packet is compared. This object is irrelevant
            for non-TCP/UDP IP packets.
            
            If the referenced parameter is not present
            in a classifier, this object reports the value of 0.";
          reference
           "SP-RFIv1.1-I07-010829, Appendix C.2.1.5.7";
          smiv2:max-access "read-only";
          smiv2:oid "1.3.6.1.2.1.10.127.7.1.1.1.12";
        }

        leaf docsQosPktClassSourcePortEnd {
          type int32 {
            range "0..65535";
          }
          description
           "This object specifies the high end inclusive
            range of TCP/UDP source port numbers to which
            a packet is compared. This object is irrelevant
            for non-TCP/UDP IP packets.
            
            If the referenced parameter is not present
            in a classifier, this object reports the value of 
            65535.";
          reference
           "SP-RFIv1.1-I07-010829, Appendix C.2.1.5.8";
          smiv2:max-access "read-only";
          smiv2:oid "1.3.6.1.2.1.10.127.7.1.1.1.13";
        }

        leaf docsQosPktClassDestPortStart {
          type int32 {
            range "0..65535";
          }
          description
           "This object specifies the low end inclusive
            range of TCP/UDP destination port numbers to
            which a packet is compared.
            
            If the referenced parameter is not present
            in a classifier, this object reports the value of 0.";
          reference
           "SP-RFIv1.1-I07-010829, Appendix C.2.1.5.9";
          smiv2:max-access "read-only";
          smiv2:oid "1.3.6.1.2.1.10.127.7.1.1.1.14";
        }

        leaf docsQosPktClassDestPortEnd {
          type int32 {
            range "0..65535";
          }
          description
           "This object specifies the high end inclusive
            range of TCP/UDP destination port numbers to which
            a packet is compared.
            
            If the referenced parameter is not present
            in a classifier, this object reports the value of 
            65535.";
          reference
           "SP-RFIv1.1-I07-010829, Appendix C.2.1.5.10";
          smiv2:max-access "read-only";
          smiv2:oid "1.3.6.1.2.1.10.127.7.1.1.1.15";
        }

        leaf docsQosPktClassDestMacAddr {
          type yang:mac-address;
          description
           "An Ethernet packet matches an entry when its 
            destination MAC address bitwise ANDed with 
            docsQosPktClassDestMacMask equals the value of 
            docsQosPktClassDestMacAddr.
            
            
            If the referenced parameter is not present
            in a classifier, this object reports the value of 
            '000000000000'H.";
          reference
           "SP-RFIv1.1-I07-010829, Appendix C.2.1.6.1";
          smiv2:max-access "read-only";
          smiv2:oid "1.3.6.1.2.1.10.127.7.1.1.1.16";
        }

        leaf docsQosPktClassDestMacMask {
          type yang:mac-address;
          description
           "An Ethernet packet matches an entry when its 
            destination MAC address bitwise ANDed with 
            docsQosPktClassDestMacMask equals the value of 
            docsQosPktClassDestMacAddr.
            
            If the referenced parameter is not present
            in a classifier, this object reports the value of 
            '000000000000'H.";
          reference
           "SP-RFIv1.1-I07-010829, Appendix C.2.1.6.1";
          smiv2:max-access "read-only";
          smiv2:oid "1.3.6.1.2.1.10.127.7.1.1.1.17";
        }

        leaf docsQosPktClassSourceMacAddr {
          type yang:mac-address;
          description
           "An Ethernet packet matches this entry when its 
            source MAC address equals the value of 
            this object.
            
            If the referenced parameter is not present
            in a classifier, this object reports the value of 
            'FFFFFFFFFFFF'H.";
          reference
           "SP-RFIv1.1-I07-010829, Appendix C.2.1.6.2";
          smiv2:max-access "read-only";
          smiv2:oid "1.3.6.1.2.1.10.127.7.1.1.1.18";
        }

        leaf docsQosPktClassEnetProtocolType {
          type enumeration {
            enum "none" {
              value "0";
            }
            enum "ethertype" {
              value "1";
            }
            enum "dsap" {
              value "2";
            }
            enum "mac" {
              value "3";
            }
            enum "all" {
              value "4";
            }
          }
          description
           "This object indicates the format of the layer 3 
            protocol id in the Ethernet packet. A value of 
            none(0) means that the rule does not use the 
            layer 3 protocol type as a matching criteria.
            
            A value of ethertype(1) means that the rule
            applies only to frames which contains an 
            EtherType value. Ethertype values are contained
            in packets using the Dec-Intel-Xerox (DIX)
            encapsulation or the RFC1042 Sub-Network Access
            Protocol (SNAP) encapsulation formats.
            
            A value of dsap(2) means that the rule applies
            only to frames using the IEEE802.3
            encapsulation format with a Destination Service
            Access Point (DSAP) other 
            than 0xAA (which is reserved for SNAP).
            
            A value of mac(3) means that the rule applies 
            only to MAC management messages for MAC management
            messages.
            
            A value of all(4) means that the rule matches
            all Ethernet packets. 
            
            If the Ethernet frame contains an 802.1P/Q Tag 
            header (i.e. EtherType 0x8100), this object
            applies to the embedded EtherType field within 
            the 802.1P/Q header.
            
            If the referenced parameter is not present
            in a classifier, this object reports the value of 0.";
          reference
           "SP-RFIv1.1-I07-010829, Appendix C.2.1.6.3";
          smiv2:max-access "read-only";
          smiv2:oid "1.3.6.1.2.1.10.127.7.1.1.1.19";
        }

        leaf docsQosPktClassEnetProtocol {
          type int32 {
            range "0..65535";
          }
          description
           "If docsQosEthPktClassProtocolType is none(0), 
            this object is ignored when considering whether 
            a packet matches the current rule.
            
            If dosQosPktClassEnetProtocolType is ethertype(1),
            this object gives the 16-bit value of the
            EtherType that the packet must match in order to
            match the rule.
            
            If docsQosPktClassEnetProtocolType is dsap(2), the
            lower 8 bits of this object's value must match the
            DSAP byte of the packet in order to match the
            rule.
            
            If docsQosPktClassEnetProtocolType is mac(3), the
            lower 8 bits of this object value represent a
            lower bound (inclusive) of MAC management message
            type codes matched, and the upper 8 bits of this
            object value represent the upper bound (inclusive)
            of matched MAC message type codes.  Certain
            message type codes are excluded from matching, as
            specified in the reference.
            
            If the Ethernet frame contains an 802.1P/Q Tag header 
            (i.e. EtherType 0x8100), this object applies to the 
            embedded EtherType field within the 802.1P/Q header.
            
            If the referenced parameter is not present in the
            classifier, the value of this object is reported as 0.";
          reference
           "SP-RFIv1.1-I07-010829, Appendix C.2.1.6.3";
          smiv2:max-access "read-only";
          smiv2:oid "1.3.6.1.2.1.10.127.7.1.1.1.20";
        }

        leaf docsQosPktClassUserPriApplies {
          type int32 {
            range "0..1";
          }
          status obsolete;
          description
           "This object is obsolete.";
          smiv2:max-access "read-only";
          smiv2:oid "1.3.6.1.2.1.10.127.7.1.1.1.21";
        }

        leaf docsQosPktClassUserPriLow {
          type int32 {
            range "0..7";
          }
          description
           "This object applies only to Ethernet frames 
            using the 802.1P/Q tag header (indicated with 
            EtherType 0x8100). Such frames include a 16-bit 
            Tag that contains a 3 bit Priority field and
            a 12 bit VLAN number.
            
            Tagged Ethernet packets must have a 3-bit
            Priority field within the range of 
            docsQosPktClassPriLow and docsQosPktClassPriHigh in 
            order to match this rule.
            
            If the referenced parameter is not present in the
            classifier, the value of this object is reported as 0.";
          reference
           "SP-RFIv1.1-I07-010829, Appendix C.2.1.7.1";
          smiv2:max-access "read-only";
          smiv2:oid "1.3.6.1.2.1.10.127.7.1.1.1.22";
        }

        leaf docsQosPktClassUserPriHigh {
          type int32 {
            range "0..7";
          }
          description
           "This object applies only to Ethernet frames 
            using the 802.1P/Qtag header (indicated with 
            EtherType 0x8100). Such frames include a 16-bit 
            Tag that contains a 3 bit Priority field and
            a 12 bit VLAN number.
            
            Tagged Ethernet packets must have a 3-bit
            Priority field within the range of 
            docsQosPktClassPriLow and 
            docsQosPktClassPriHigh in order to match this
            rule.
            
            If the referenced parameter is not present in the
            classifier, the value of this object is reported 
            as 7.";
          reference
           "SP-RFIv1.1-I07-010829, Appendix C.2.1.7.1";
          smiv2:max-access "read-only";
          smiv2:oid "1.3.6.1.2.1.10.127.7.1.1.1.23";
        }

        leaf docsQosPktClassVlanId {
          type int32 {
            range "0..4095";
          }
          description
           "This object applies only to Ethernet frames 
            using the 802.1P/Q tag header.
            
            If this object's value is nonzero, tagged
            packets must have a VLAN Identifier that matches
            the value in order to match the rule.
            
            Only the least significant 12 bits of this object's
            value are valid. 
            
            If the referenced parameter is not present in the
            classifier, the value of this object is reported 
            as 0.";
          reference
           "SP-RFIv1.1-I07-010829, Appendix C.2.1.7.2";
          smiv2:max-access "read-only";
          smiv2:oid "1.3.6.1.2.1.10.127.7.1.1.1.24";
        }

        leaf docsQosPktClassState {
          type enumeration {
            enum "active" {
              value "1";
            }
            enum "inactive" {
              value "2";
            }
          }
          description
           "This object indicates whether or not the classifier
            is enabled to classify packets to a Service Flow.
            
            If the referenced parameter is not present in the
            classifier, the value of this object is reported 
            as active(1).";
          reference
           "SP-RFIv1.1-I07-010829, Appendix C.2.1.3.6";
          smiv2:max-access "read-only";
          smiv2:oid "1.3.6.1.2.1.10.127.7.1.1.1.25";
        }

        leaf docsQosPktClassPkts {
          type yang:counter32;
          description
           "This object counts the number of packets that have
            been classified using this entry.";
          smiv2:max-access "read-only";
          smiv2:oid "1.3.6.1.2.1.10.127.7.1.1.1.26";
        }

        leaf docsQosPktClassBitMap {
          type bits {
            bit rulePriority {
              position "0";
            }
            bit activationState {
              position "1";
            }
            bit ipTos {
              position "2";
            }
            bit ipProtocol {
              position "3";
            }
            bit ipSourceAddr {
              position "4";
            }
            bit ipSourceMask {
              position "5";
            }
            bit ipDestAddr {
              position "6";
            }
            bit ipDestMask {
              position "7";
            }
            bit sourcePortStart {
              position "8";
            }
            bit sourcePortEnd {
              position "9";
            }
            bit destPortStart {
              position "10";
            }
            bit destPortEnd {
              position "11";
            }
            bit destMac {
              position "12";
            }
            bit sourceMac {
              position "13";
            }
            bit ethertype {
              position "14";
            }
            bit userPri {
              position "15";
            }
            bit vlanId {
              position "16";
            }
          }
          description
           "This object indicates which parameter encodings were
            actually present in the DOCSIS packet classifier
            encoding signaled in the DOCSIS message that
            created or modified the classifier. Note that
            Dynamic Service Change messages have replace
            semantics, so that all non-default parameters must
            be present whether the classifier is being created
            or changed.
            
            A bit of of this object is set to 1 if the parameter
            indicated by the comment was present in the classifier 
            encoding, and 0 otherwise.
            
            Note that BITS are encoded most significant bit
            first, so that if e.g. bits 6 and 7 are set, this object
            is encoded as the octet string '030000'H.";
          smiv2:max-access "read-only";
          smiv2:oid "1.3.6.1.2.1.10.127.7.1.1.1.27";
        }

        leaf docsQosPktClassInetSourceAddrType {
          type inet-address:InetAddressType;
          description
           "The type of the internet address for
            docsQosPktClassInetSourceAddr. This type must be
            the same as the docsQosPktClassInetSourceMaskType.
            
            If the referenced parameter is not present
            in a classifier, this object reports the value of
            ipv4(1).";
          reference
           "SP-RFIv1.1-I07-010829, Appendix C.2.1.5.3";
          smiv2:max-access "read-only";
          smiv2:oid "1.3.6.1.2.1.10.127.7.1.1.1.28";
        }

        leaf docsQosPktClassInetSourceAddr {
          type inet-address:InetAddress;
          description
           "This object specifies the value of the IP
            Source Address required for packets to match
            this rule. An IP packet matches the rule when
            the packet ip source address bitwise ANDed
            with the docsQosPktClassInetSourceMask value
            equals the docsQosPktClassInetSourceAddr value.
            
            If the referenced parameter is not present
            in a classifier, this object reports the value of
            '00000000'H.";
          reference
           "SP-RFIv1.1-I07-010829, Appendix C.2.1.5.3";
          smiv2:max-access "read-only";
          smiv2:oid "1.3.6.1.2.1.10.127.7.1.1.1.29";
        }

        leaf docsQosPktClassInetSourceMaskType {
          type inet-address:InetAddressType;
          description
           "The type of the internet address for
            docsQosPktClassInetSourceMask. This type must be
            the same as the docsQosPktClassInetSourceAddrType.
            
            If the referenced parameter is not present
            in a classifier, this object reports the value of
            ipv4(1).";
          reference
           "SP-RFIv1.1-I07-010829, Appendix C.2.1.5.4";
          smiv2:max-access "read-only";
          smiv2:oid "1.3.6.1.2.1.10.127.7.1.1.1.30";
        }

        leaf docsQosPktClassInetSourceMask {
          type inet-address:InetAddress;
          description
           "This object specifies which bits of a packet's
            IP Source Address that are compared to match
            this rule.
            An IP packet matches the rule when the packet
            source address bitwise ANDed with the
            docsQosPktClassInetSourceMask value equals the
            docsQosIpPktClassInetSourceAddr value.
            
            If the referenced parameter is not present
            in a classifier, this object reports the value of
            'FFFFFFFF'H.";
          reference
           "SP-RFIv1.1-I07-010829, Appendix C.2.1.5.4";
          smiv2:max-access "read-only";
          smiv2:oid "1.3.6.1.2.1.10.127.7.1.1.1.31";
        }

        leaf docsQosPktClassInetDestAddrType {
          type inet-address:InetAddressType;
          description
           "The type of the internet address for
            docsQosPktClassInetDestAddr. This type must be
            the same as the docsQosPktClassInetDestMaskType.
            
            If the referenced parameter is not present
            in a classifier, this object reports the value of
            ipv4(1).";
          reference
           "SP-RFIv1.1-I07-010829, Appendix C.2.1.5.5";
          smiv2:max-access "read-only";
          smiv2:oid "1.3.6.1.2.1.10.127.7.1.1.1.32";
        }

        leaf docsQosPktClassInetDestAddr {
          type inet-address:InetAddress;
          description
           "This object specifies the value of the IP
            Destination Address required for packets to match
            this rule. An IP packet matches the rule when
            the packet ip destination address
            bitwise ANDed with the
            docsQosPktClassInetDestMask value
            equals the docsQosPktClassInetDestAddr value.
            
            If the referenced parameter is not present
            in a classifier, this object reports the value of
            '00000000'H.";
          reference
           "SP-RFIv1.1-I07-010829, Appendix C.2.1.5.5";
          smiv2:max-access "read-only";
          smiv2:oid "1.3.6.1.2.1.10.127.7.1.1.1.33";
        }

        leaf docsQosPktClassInetDestMaskType {
          type inet-address:InetAddressType;
          description
           "The type of the internet address for
            docsQosPktClassInetDestMask. This type must be
            the same as the docsQosPktClassInetDestAddrType.
            
            If the referenced parameter is not present
            in a classifier, this object reports the value of
            ipv4(1).";
          reference
           "SP-RFIv1.1-I07-010829, Appendix C.2.1.5.6";
          smiv2:max-access "read-only";
          smiv2:oid "1.3.6.1.2.1.10.127.7.1.1.1.34";
        }

        leaf docsQosPktClassInetDestMask {
          type inet-address:InetAddress;
          description
           "This object specifies which bits of a packet's
            IP Destination Address that are compared to
            match this rule.
            An IP packet matches the rule when the packet
            destination address bitwise ANDed with the
            docsQosPktClassInetDestMask value equals the
            docsQosIpPktClassInetDestAddr value.
            
            If the referenced parameter is not present
            in a classifier, this object reports the value of
            'FFFFFFFF'H.";
          reference
           "SP-RFIv1.1-I07-010829, Appendix C.2.1.5.6";
          smiv2:max-access "read-only";
          smiv2:oid "1.3.6.1.2.1.10.127.7.1.1.1.35";
        }
      }
    }

    container docsQosParamSetTable {
      description
       "This table describes the set of DOCSIS 1.1 QOS 
        parameters defined in a managed device.
        
        The ifIndex index specifies a DOCSIS MAC Domain.
        The docsQosServiceFlowId index specifies a particular
        Service Flow. 
        The docsQosParamSetType index indicates whether
        the active, admitted, or provisioned QOS Parameter 
        Set is being described by the row.
        
        Only the QOS Parameter Sets of Docsis 1.1 service
        flows are represented in this table.  Docsis 1.0
        QOS service profiles are not represented in this
        table.
        
        Each row corresponds to a DOCSIS QOS Parameter Set
        as signaled via DOCSIS MAC management messages.
        Each object in the row corresponds to one or 
        part of one DOCSIS 1.1 Service Flow Encoding.
        The docsQosParamSetBitMap object in the row indicates
        which particular parameters were signalled in 
        the original registration or dynamic service
        request message that created the QOS Parameter Set.
        
        In many cases, even if a QOS Parameter Set parameter
        was not signalled, the DOCSIS specification calls
        for a default value to be used. That default value
        is reported as the value of the corresponding object
        in this row.
        
        Many objects are not applicable depending on
        the service flow direction or upstream scheduling
        type.  The object value reported in this case
        is specified in the DESCRIPTION clause.";
      smiv2:oid "1.3.6.1.2.1.10.127.7.1.2";

      list docsQosParamSetEntry {
        key "ifIndex docsQosServiceFlowId docsQosParamSetType";
        description
         "A unique set of QOS parameters.";
        smiv2:oid "1.3.6.1.2.1.10.127.7.1.2.2";

        leaf ifIndex {
          type leafref {
            path "/if-mib:IF-MIB/if-mib:ifTable/if-mib:ifEntry/if-mib:ifIndex";
          }
        }

        leaf docsQosServiceFlowId {
          type leafref {
            path "/DOCS-QOS-MIB:DOCS-QOS-MIB/DOCS-QOS-MIB:docsQosServiceFlowTable/DOCS-QOS-MIB:docsQosServiceFlowEntry/DOCS-QOS-MIB:docsQosServiceFlowId";
          }
        }

        leaf docsQosParamSetServiceClassName {
          type snmpv2-tc:DisplayString;
          description
           "Refers to the Service Class Name that the 
            parameter set values were derived.
            
            If the referenced parameter is not present in the
            corresponding DOCSIS QOS Parameter Set, the default 
            value of this object is a zero length string.";
          reference
           "SP-RFIv1.1-I07-010829, Appendix C.2.2.3.4";
          smiv2:max-access "read-only";
          smiv2:oid "1.3.6.1.2.1.10.127.7.1.2.2.4";
        }

        leaf docsQosParamSetPriority {
          type int32 {
            range "0..7";
          }
          description
           "The relative priority of a service flow.
            Higher numbers indicate higher priority.
            This priority should only be used to differentiate
            service flow with identical parameter sets.
            
            If the referenced parameter is not present in the
            corresponding DOCSIS QOS Parameter Set, the default 
            value of this object is 0.  If the parameter is
            not applicable, the reported value is 0.";
          reference
           "SP-RFIv1.1-I07-010829, Appendix C.2.2.5.1";
          smiv2:max-access "read-only";
          smiv2:oid "1.3.6.1.2.1.10.127.7.1.2.2.5";
        }

        leaf docsQosParamSetMaxTrafficRate {
          type DOCS-QOS-MIB:DOCSQOSBitRate;
          description
           "Maximum sustained traffic rate allowed for this 
            service flow in bits/sec. Must count all MAC frame 
            data PDU from the bytes following the MAC header HCS to
            the end of the CRC. The number of bytes 
            forwarded is limited during any time interval.
            The value 0 means no maximum traffic rate is 
            enforced. This object applies to both upstream and
            downstream service flows.
            
            If the referenced parameter is not present in the
            corresponding DOCSIS QOS Parameter Set, the default
            value of this object is 0. If the parameter is
            not applicable, it is reported as 0.";
          reference
           "SP-RFIv1.1-I07-010829, Appendix C.2.2.5.2";
          smiv2:max-access "read-only";
          smiv2:oid "1.3.6.1.2.1.10.127.7.1.2.2.6";
        }

        leaf docsQosParamSetMaxTrafficBurst {
          type uint32;
          description
           "Specifies the token bucket size in bytes
            for this parameter set. The value is calculated 
            from the byte following the MAC header HCS to 
            the end of the CRC. This object is applied in 
            conjunction with docsQosParamSetMaxTrafficRate to 
            calculate maximum sustained traffic rate.
            
            If the referenced parameter is not present in the
            corresponding DOCSIS QOS Parameter Set, the default
            value of this object for scheduling types
            bestEffort (2), nonRealTimePollingService(3),
            and realTimePollingService(4) is 1522. 
            
            If this parameter is not applicable, it is reported
            as 0.";
          reference
           "SP-RFIv1.1-I07-010829, Appendix C.2.2.5.3";
          smiv2:max-access "read-only";
          smiv2:oid "1.3.6.1.2.1.10.127.7.1.2.2.7";
        }

        leaf docsQosParamSetMinReservedRate {
          type DOCS-QOS-MIB:DOCSQOSBitRate;
          description
           "Specifies the guaranteed minimum rate in
            bits/sec for this parameter set. The value is 
            calculated from the byte following the MAC 
            header HCS to the end of the CRC. The default
            value of 0 has the meaning that no bandwidth 
            is reserved.
            If the referenced parameter is not present in the
            corresponding DOCSIS QOS Parameter Set, the default
            value of this object is 0. If the parameter
            is not applicable, it is reported as 0.";
          reference
           "SP-RFIv1.1-I07-010829, Appendix C.2.2.5.4";
          smiv2:max-access "read-only";
          smiv2:oid "1.3.6.1.2.1.10.127.7.1.2.2.8";
        }

        leaf docsQosParamSetMinReservedPkt {
          type int32 {
            range "0..65535";
          }
          description
           "Specifies an assumed minimum packet size in 
            bytes for which the docsQosParamSetMinReservedRate 
            will be provided. The value is calculated from
            the byte following the MAC header HCS to the 
            end of the CRC. 
                
            If the referenced parameter is omitted from a
            DOCSIS QOS parameter set, the default value is
            CMTS implementation dependent. In this case, the
            CMTS reports the default value it is using and the
            CM reports a value of 0. If the referenced
            parameter is not applicable to the direction or
            scheduling type of the service flow, both CMTS and
            CM report this object's value as 0.";
          reference
           "SP-RFIv1.1-I07-010829, Appendix C.2.2.5.5";
          smiv2:max-access "read-only";
          smiv2:oid "1.3.6.1.2.1.10.127.7.1.2.2.9";
        }

        leaf docsQosParamSetActiveTimeout {
          type int32 {
            range "0..65535";
          }
          units "seconds";
          description
           "Specifies the maximum duration in seconds that 
            resources remain unused on an active service
            flow before CMTS signals that both active and
            admitted parameters set are null.
            The default value of 0 signifies an
            infinite amount of time.
            
            If the referenced parameter is not present in the
            corresponding DOCSIS QOS Parameter Set, the default
            value of this object is 0.";
          reference
           "SP-RFIv1.1-I07-010829, Appendix C.2.2.5.6";
          smiv2:max-access "read-only";
          smiv2:oid "1.3.6.1.2.1.10.127.7.1.2.2.10";
        }

        leaf docsQosParamSetAdmittedTimeout {
          type int32 {
            range "0..65535";
          }
          units "seconds";
          description
           "Specifies the maximum duration in seconds that 
            resources remain in admitted state before 
            resources must be released.
            The value of 0 signifies an infinite amount 
            of time.
            
            If the referenced parameter is not present in the
            corresponding DOCSIS QOS Parameter Set, the 
            default value of this object is 200.";
          reference
           "SP-RFIv1.1-I07-010829, Appendix C.2.2.5.7";
          smiv2:defval "200";
          smiv2:max-access "read-only";
          smiv2:oid "1.3.6.1.2.1.10.127.7.1.2.2.11";
        }

        leaf docsQosParamSetMaxConcatBurst {
          type int32 {
            range "0..65535";
          }
          description
           "Specifies the maximum concatenated burst in
            bytes which an upstream  service flow is allowed. 
            The value is calculated from the FC byte of the
            Concatenation MAC Header to the last CRC byte in 
            of the last concatenated MAC frame, inclusive.
            The value of 0 specifies no maximum burst.
            
            If the referenced parameter is not present in the
            corresponding DOCSIS QOS Parameter Set, the default
            value of this object is 0. If the parameter is
            not applicable, this object's value is reported
            as 0.";
          reference
           "SP-RFIv1.1-I07-010829, Appendix C.2.2.6.1";
          smiv2:max-access "read-only";
          smiv2:oid "1.3.6.1.2.1.10.127.7.1.2.2.12";
        }

        leaf docsQosParamSetSchedulingType {
          type DOCS-QOS-MIB:SchedulingType;
          description
           "Specifies the upstream scheduling service used for 
            upstream service flow. 
            
            If the referenced parameter is not present in the
            corresponding DOCSIS QOS Parameter Set of an
            upstream service flow, the default value of this
            object is bestEffort(2). For QOS parameter sets of
            downstream service flows, this object's value is
            reported as undefined(1).";
          reference
           "SP-RFIv1.1-I07-010829, Appendix C.2.2.6.2";
          smiv2:max-access "read-only";
          smiv2:oid "1.3.6.1.2.1.10.127.7.1.2.2.13";
        }

        leaf docsQosParamSetNomPollInterval {
          type uint32;
          units "microseconds";
          description
           "Specifies the nominal interval in microseconds 
            between successive unicast request
            opportunities on an upstream service flow.
            
            This object applies only to upstream service flows
            with schedulingType of value
            nonRealTimePollingService(3),
            realTimePollingService(4), and
            unsolictedGrantServiceWithAD(5).  The parameter is
            mandatory for realTimePollingService(4).  If the
            parameter is omitted with
            nonRealTimePollingService(3), the CMTS uses an
            implementation dependent value.  If the parameter
            is omitted with unsolictedGrantServiceWithAD(5),
            the CMTS uses as a default value the value of the
            Nominal Grant Interval parameter.  In all cases,
            the CMTS reports the value it is using when the
            parameter is applicable.  The CM reports the 
            signaled parameter value if it was signaled, 
            and 0 otherwise.
            
            If the referenced parameter is not applicable to
            the direction or scheduling type of the
            corresponding DOCSIS QOS Parameter Set, both
            CMTS and CM report this object's value as 0.";
          reference
           "SP-RFIv1.1-I07-010829, Appendix C.2.2.6.4";
          smiv2:max-access "read-only";
          smiv2:oid "1.3.6.1.2.1.10.127.7.1.2.2.15";
        }

        leaf docsQosParamSetTolPollJitter {
          type uint32;
          units "microseconds";
          description
           "Specifies the maximum amount of time in
            microseconds that the unicast request interval
            may be delayed from the nominal periodic
            schedule on an upstream service flow.
            
            This parameter is applicable only to upstream
            service flows with a Schedulingtype of
            realTimePollingService(4) or
            unsolictedGrantServiceWithAD(5).
            
            If the referenced parameter is applicable but not
            present in the corresponding DOCSIS QOS Parameter
            Set, the CMTS uses an implementation dependent 
            value and reports the value it is using.
            The CM reports a value of 0 in this case.
            
            If the parameter is not applicable to the
            direction or upstream scheduling type of the
            service flow, both CMTS and CM report this
            object's value as 0.";
          reference
           "SP-RFIv1.1-I07-010829, Appendix C.2.2.6.5";
          smiv2:max-access "read-only";
          smiv2:oid "1.3.6.1.2.1.10.127.7.1.2.2.16";
        }

        leaf docsQosParamSetUnsolicitGrantSize {
          type int32 {
            range "0..65535";
          }
          description
           "Specifies the unsolicited grant size in bytes. 
            The grant size includes the entire MAC frame 
            data PDU from the Frame Control byte to end of
            the MAC frame.
            
            The referenced parameter is applicable only 
            for upstream flows with a SchedulingType of
            of unsolicitedGrantServicewithAD(5) or
            unsolicitedGrantService(6), and is mandatory
            when applicable. Both CMTS and CM report
            the signaled value of the parameter in this
            case.                
            
            If the referenced parameter is not applicable to
            the direction or scheduling type of the
            corresponding DOCSIS QOS Parameter Set, both
            CMTS and CM report this object's value as 0.";
          reference
           "SP-RFIv1.1-I07-010829, Appendix C.2.2.6.6";
          smiv2:max-access "read-only";
          smiv2:oid "1.3.6.1.2.1.10.127.7.1.2.2.17";
        }

        leaf docsQosParamSetNomGrantInterval {
          type uint32;
          units "microseconds";
          description
           "Specifies the nominal interval in microseconds 
            between successive data grant opportunities 
            on an upstream service flow.
            
            The referenced parameter is applicable only 
            for upstream flows with a SchedulingType of
            of unsolicitedGrantServicewithAD(5) or
            unsolicitedGrantService(6), and is mandatory
            when applicable. Both CMTS and CM report the
            signaled value of the parameter in this case.
            
            If the referenced parameter is not applicable to
            the direction or scheduling type of the
            corresponding DOCSIS QOS Parameter Set, both
            CMTS and CM report this object's value as 0.";
          reference
           "SP-RFIv1.1-I07-010829, Appendix C.2.2.6.7";
          smiv2:max-access "read-only";
          smiv2:oid "1.3.6.1.2.1.10.127.7.1.2.2.18";
        }

        leaf docsQosParamSetTolGrantJitter {
          type uint32;
          units "microseconds";
          description
           "Specifies the maximum amount of time in
            microseconds that the transmission opportunities
            may be delayed from the nominal periodic schedule. 
            
            The referenced parameter is applicable only 
            for upstream flows with a SchedulingType of
            of unsolicitedGrantServicewithAD(5) or
            unsolicitedGrantService(6), and is mandatory
            when applicable. Both CMTS and CM report the
            signaled value of the parameter in this case.
            
            If the referenced parameter is not applicable to
            the direction or scheduling type of the
            corresponding DOCSIS QOS Parameter Set, both
            CMTS and CM report this object's value as 0.";
          reference
           "SP-RFIv1.1-I07-010829, Appendix C.2.2.6.8";
          smiv2:max-access "read-only";
          smiv2:oid "1.3.6.1.2.1.10.127.7.1.2.2.19";
        }

        leaf docsQosParamSetGrantsPerInterval {
          type int32 {
            range "0..127";
          }
          description
           "Specifies the number of data grants per Nominal 
            Grant Interval 
            (docsQosParamSetNomGrantInterval).
            
            The referenced parameter is applicable only 
            for upstream flows with a SchedulingType of
            of unsolicitedGrantServicewithAD(5) or
            unsolicitedGrantService(6), and is mandatory
            when applicable. Both CMTS and CM report the
            signaled value of the parameter in this case.
            
            If the referenced parameter is not applicable to
            the direction or scheduling type of the
            corresponding DOCSIS QOS Parameter Set, both
            CMTS and CM report this object's value as 0.";
          reference
           "SP-RFIv1.1-I07-010829, Appendix C.2.2.6.9";
          smiv2:max-access "read-only";
          smiv2:oid "1.3.6.1.2.1.10.127.7.1.2.2.20";
        }

        leaf docsQosParamSetTosAndMask {
          type binary {
            length "1";
          }
          description
           "Specifies the AND mask for IP TOS byte for overwriting
            IP packets TOS value.  The IP packets TOS byte is 
            bitwise ANDed with docsQosParamSetTosAndMask and 
            result is bitwise ORed with docsQosParamSetTosORMask
            and result is written to IP packet TOS byte. 
            A value of 'FF'H for docsQosParamSetTosAndMask and
            a value of '00'H for docsQosParamSetTosOrMask means 
            that IP Packet TOS byte is not overwritten.
            
            Even though the this object is only enforced by the
            Cable Modem Termination System (CMTS),
            Cable Modems must report the value as signaled in
            the referenced parameter.
            
            This combination is reported if the referenced
            parameter is not present in a QOS Parameter Set.";
          reference
           "SP-RFIv1.1-I07-010829, Appendix C.2.2.6.10";
          smiv2:max-access "read-only";
          smiv2:oid "1.3.6.1.2.1.10.127.7.1.2.2.21";
        }

        leaf docsQosParamSetTosOrMask {
          type binary {
            length "1";
          }
          description
           "Specifies the OR mask for IP TOS byte.
            See the description of docsQosParamSetTosAndMask
            for further details.";
          reference
           "SP-RFIv1.1-I07-010829, Appendix C.2.2.6.10";
          smiv2:max-access "read-only";
          smiv2:oid "1.3.6.1.2.1.10.127.7.1.2.2.22";
        }

        leaf docsQosParamSetMaxLatency {
          type uint32;
          units "microseconds";
          description
           "Specifies the maximum latency between the
            reception of a packet by the CMTS on its NSI 
            and the forwarding of the packet to the RF
            interface. A value of 0 signifies no maximum
            latency enforced. This object only applies to
            downstream service flows.
            
            If the referenced parameter is not present in the
            corresponding downstream DOCSIS QOS Parameter Set, 
            the default value is 0. This parameter is
            not applicable to upstream DOCSIS QOS Parameter Sets,
            and its value is reported as 0 in this case.";
          reference
           "SP-RFIv1.1-I07-010829, Appendix C.2.2.7.1";
          smiv2:max-access "read-only";
          smiv2:oid "1.3.6.1.2.1.10.127.7.1.2.2.23";
        }

        leaf docsQosParamSetType {
          type enumeration {
            enum "active" {
              value "1";
            }
            enum "admitted" {
              value "2";
            }
            enum "provisioned" {
              value "3";
            }
          }
          description
           "Defines the type of the QOS parameter set defined
            by this row. active(1) indicates the Active QOS
            parameter set, describing the service currently
            being provided by the Docsis MAC domain to the 
            service flow. admitted(2) indicates the Admitted
            QOS Parameter Set, describing services reserved by
            by the Docsis MAC domain for use by the service flow.
            provisioned (3) describes the QOS Parameter Set
            defined in the DOCSIS CM Configuration file for
            the service flow.";
          reference
           "SP-RFIv1.1-I07-010829, 8.1.5";
          smiv2:max-access "not-accessible";
          smiv2:oid "1.3.6.1.2.1.10.127.7.1.2.2.24";
        }

        leaf docsQosParamSetRequestPolicyOct {
          type binary {
            length "4";
          }
          description
           "Specifies which transmit interval opportunities 
            the CM omits for upstream transmission requests and 
            packet transmissions. This object takes its
            default value for downstream service flows.
            
            Unless otherwise indicated, a bit value of 1 means
            that a CM must *not* use that opportunity for 
            upstream transmission.
            
            Calling bit 0 the least significant bit of the 
            least significant (4th) octet, and increasing
            bit number with significance, the bit definitions
            are as defined below:
            
            broadcastReqOpp(0):
                 all CMs broadcast request opportunities
            
            priorityReqMulticastReq(1):
                 priority request multicast request opportunities
            
            reqDataForReq(2):
                 request/data opportunities for requests
            
            reqDataForData(3):
                 request/data opportunities for data
            
            piggybackReqWithData(4):
                 piggyback requests with data
            
            concatenateData(5):
                 concatenate data
            
            fragmentData(6):
                 fragment data
            
            suppresspayloadheaders(7): 
                 suppress payload headers
            
            dropPktsExceedUGSize(8):
                 A value of 1 mean that service flow must drop
                 packet that do not fit in the Unsolicited 
                 Grant size 
            
            If the referenced parameter is not present in 
            a QOS Parameter Set, the value of this object is
            reported as '00000000'H.";
          reference
           "SP-RFIv1.1-I07-010829, Appendix C.2.2.6.3";
          smiv2:max-access "read-only";
          smiv2:oid "1.3.6.1.2.1.10.127.7.1.2.2.25";
        }

        leaf docsQosParamSetBitMap {
          type bits {
            bit trafficPriority {
              position "0";
            }
            bit maxTrafficRate {
              position "1";
            }
            bit maxTrafficBurst {
              position "2";
            }
            bit minReservedRate {
              position "3";
            }
            bit minReservedPkt {
              position "4";
            }
            bit activeTimeout {
              position "5";
            }
            bit admittedTimeout {
              position "6";
            }
            bit maxConcatBurst {
              position "7";
            }
            bit schedulingType {
              position "8";
            }
            bit requestPolicy {
              position "9";
            }
            bit nomPollInterval {
              position "10";
            }
            bit tolPollJitter {
              position "11";
            }
            bit unsolicitGrantSize {
              position "12";
            }
            bit nomGrantInterval {
              position "13";
            }
            bit tolGrantJitter {
              position "14";
            }
            bit grantsPerInterval {
              position "15";
            }
            bit tosOverwrite {
              position "16";
            }
            bit maxLatency {
              position "17";
            }
          }
          description
           "This object indicates the set of QOS Parameter
            Set parameters actually signaled in the 
            DOCSIS registration or dynamic service request
            message that created or modified the QOS Parameter Set. 
            A bit is set to 1 when the parameter described
            by the indicated reference section is present
            in the original request.  
            
            Note that when Service Class names are expanded,
            the registration or dynamic response message may
            contain parameters as expanded by the CMTS based
            on a stored service class. These expanded
            parameters are *not* indicated by a 1 bit in this
            object.
            
            Note that even though some QOS Parameter Set 
            parameters may not be signalled in a message
            (so that the paramater's bit in this object is 0)
            the DOCSIS specification calls for default
            values to be used. These default values are
            reported as the corresponding object's value in
            the row. 
            
            Note that BITS objects are encoded most
            significant bit first. For example, if bits
            1 and 16 are set, the value of this object 
            is the octet string '400080'H.";
          smiv2:max-access "read-only";
          smiv2:oid "1.3.6.1.2.1.10.127.7.1.2.2.26";
        }
      }
    }

    container docsQosServiceFlowTable {
      description
       "This table describes the set of Docsis-QOS 
        Service Flows in a managed device. ";
      smiv2:oid "1.3.6.1.2.1.10.127.7.1.3";

      list docsQosServiceFlowEntry {
        key "ifIndex docsQosServiceFlowId";
        description
         "Describes a service flow.
          An entry in the table exists for each 
          Service Flow ID. The ifIndex is an  
          ifType of docsCableMaclayer(127).";
        smiv2:oid "1.3.6.1.2.1.10.127.7.1.3.1";

        leaf ifIndex {
          type leafref {
            path "/if-mib:IF-MIB/if-mib:ifTable/if-mib:ifEntry/if-mib:ifIndex";
          }
        }

        leaf docsQosServiceFlowId {
          type uint32 {
            range "1..4294967295";
          }
          description
           "An index assigned to a service flow by CMTS.";
          reference
           "SP-RFIv1.1-I07-010829, Appendix C.2.2.3.2";
          smiv2:max-access "not-accessible";
          smiv2:oid "1.3.6.1.2.1.10.127.7.1.3.1.1";
        }

        leaf docsQosServiceFlowProvisionedParamSetIndex {
          type uint32 {
            range "0..4294967295";
          }
          status obsolete;
          description
           "This object is obsolete.";
          smiv2:max-access "read-only";
          smiv2:oid "1.3.6.1.2.1.10.127.7.1.3.1.3";
        }

        leaf docsQosServiceFlowAdmittedParamSetIndex {
          type uint32 {
            range "0..4294967295";
          }
          status obsolete;
          description
           "This object is obsolete.";
          smiv2:max-access "read-only";
          smiv2:oid "1.3.6.1.2.1.10.127.7.1.3.1.4";
        }

        leaf docsQosServiceFlowActiveParamSetIndex {
          type uint32 {
            range "0..4294967295";
          }
          status obsolete;
          description
           "This object is obsolete.";
          smiv2:max-access "read-only";
          smiv2:oid "1.3.6.1.2.1.10.127.7.1.3.1.5";
        }

        leaf docsQosServiceFlowSID {
          type uint32 {
            range "0..16383";
          }
          description
           "Service Identifier (SID) assigned to an 
            admitted or active service flow. This object
            reports a value of 0 if a Service Id is not 
            associated with the service flow. Only active 
            or admitted upstream service flows will have a
            Service Id (SID).";
          reference
           "SP-RFIv1.1-I07-010829, Appendix C.2.2.3.3";
          smiv2:max-access "read-only";
          smiv2:oid "1.3.6.1.2.1.10.127.7.1.3.1.6";
        }

        leaf docsQosServiceFlowDirection {
          type DOCS-QOS-MIB:IfDirection;
          description
           "The direction of the service flow.";
          reference
           "SP-RFIv1.1-I07-010829, Appendix C.2.1.1/2";
          smiv2:max-access "read-only";
          smiv2:oid "1.3.6.1.2.1.10.127.7.1.3.1.7";
        }

        leaf docsQosServiceFlowPrimary {
          type boolean;
          description
           "Object reflects whether service flow is the primary 
            or a secondary service flow.
            
            A primary service flow is the default service flow
            for otherwise unclassified traffic and all MAC 
            messages.";
          reference
           "SP-RFIv1.1-I07-010829, Section 8.1 ";
          smiv2:max-access "read-only";
          smiv2:oid "1.3.6.1.2.1.10.127.7.1.3.1.8";
        }

        leaf docsQosServiceFlowActiveTimeout {
          type int32 {
            range "0..65535";
          }
          units "seconds";
          status obsolete;
          description
           "This object is obsolete.";
          smiv2:max-access "read-only";
          smiv2:oid "1.3.6.1.2.1.10.127.7.1.3.1.9";
        }

        leaf docsQosServiceFlowAdmittedTimeout {
          type int32 {
            range "0..65535";
          }
          units "seconds";
          status obsolete;
          description
           "This object is obsolete.";
          smiv2:max-access "read-only";
          smiv2:oid "1.3.6.1.2.1.10.127.7.1.3.1.10";
        }

        leaf docsQosServiceFlowSchedulingType {
          type DOCS-QOS-MIB:SchedulingType;
          status obsolete;
          description
           "This object is obsolete.";
          smiv2:max-access "read-only";
          smiv2:oid "1.3.6.1.2.1.10.127.7.1.3.1.11";
        }

        leaf docsQosServiceFlowRequestPolicy {
          type binary {
            length "4";
          }
          status obsolete;
          description
           "This object is obsolete.";
          smiv2:max-access "read-only";
          smiv2:oid "1.3.6.1.2.1.10.127.7.1.3.1.12";
        }

        leaf docsQosServiceFlowTosAndMask {
          type binary {
            length "1";
          }
          status obsolete;
          description
           "This object is obsolete.";
          smiv2:max-access "read-only";
          smiv2:oid "1.3.6.1.2.1.10.127.7.1.3.1.13";
        }

        leaf docsQosServiceFlowTosOrMask {
          type binary {
            length "1";
          }
          status obsolete;
          description
           "This object is obsolete.";
          smiv2:max-access "read-only";
          smiv2:oid "1.3.6.1.2.1.10.127.7.1.3.1.14";
        }
      }
    }

    container docsQosServiceFlowStatsTable {
      description
       "This table describes statistics associated with the  
        Service Flows in a managed device. ";
      smiv2:oid "1.3.6.1.2.1.10.127.7.1.4";

      list docsQosServiceFlowStatsEntry {
        key "ifIndex docsQosServiceFlowId";
        description
         "Describes a set of service flow statistics.
          An entry in the table exists for each 
          Service Flow ID. The ifIndex is an  
          ifType of docsCableMaclayer(127).";
        smiv2:oid "1.3.6.1.2.1.10.127.7.1.4.1";

        leaf ifIndex {
          type leafref {
            path "/if-mib:IF-MIB/if-mib:ifTable/if-mib:ifEntry/if-mib:ifIndex";
          }
        }

        leaf docsQosServiceFlowId {
          type leafref {
            path "/DOCS-QOS-MIB:DOCS-QOS-MIB/DOCS-QOS-MIB:docsQosServiceFlowTable/DOCS-QOS-MIB:docsQosServiceFlowEntry/DOCS-QOS-MIB:docsQosServiceFlowId";
          }
        }

        leaf docsQosServiceFlowPkts {
          type yang:counter32;
          description
           "The number of Packet Data PDUs classified to this
            service flow. This object does not count MAC-specific
            management messages.
            CMs not classifying downstream packets may report
            this object's value as 0. ";
          smiv2:max-access "read-only";
          smiv2:oid "1.3.6.1.2.1.10.127.7.1.4.1.1";
        }

        leaf docsQosServiceFlowOctets {
          type yang:counter32;
          description
           "The number of octets transmitted on the Docsis RF network
            from the byte after the MAC header HCS to the end
            of the CRC for all packets counted in the
            docsQosServiceFlowPkts object for this row. Note that
            this counts the octets after payload header suppression
            has been applied. CMs not classifying to a downstream
            service flow may report this object's value as 0 for that
            flow. ";
          smiv2:max-access "read-only";
          smiv2:oid "1.3.6.1.2.1.10.127.7.1.4.1.2";
        }

        leaf docsQosServiceFlowTimeCreated {
          type yang:timestamp;
          description
           "The value of sysUpTime when the service flow 
            was created.";
          smiv2:max-access "read-only";
          smiv2:oid "1.3.6.1.2.1.10.127.7.1.4.1.3";
        }

        leaf docsQosServiceFlowTimeActive {
          type yang:counter32;
          units "seconds";
          description
           "The total time that service flow has been active.";
          smiv2:max-access "read-only";
          smiv2:oid "1.3.6.1.2.1.10.127.7.1.4.1.4";
        }

        leaf docsQosServiceFlowPHSUnknowns {
          type yang:counter32;
          description
           "The number of packets received on the service flow
            with an unknown payload header suppression index.";
          smiv2:max-access "read-only";
          smiv2:oid "1.3.6.1.2.1.10.127.7.1.4.1.5";
        }

        leaf docsQosServiceFlowPolicedDropPkts {
          type yang:counter32;
          description
           "The number of packets dropped due to policing of 
            the service flow, especially to limit the maximum 
            rate of the flow.";
          smiv2:max-access "read-only";
          smiv2:oid "1.3.6.1.2.1.10.127.7.1.4.1.6";
        }

        leaf docsQosServiceFlowPolicedDelayPkts {
          type yang:counter32;
          description
           "The number of packet delayed due to policing of 
            the service flow, especially to limit the maximum
            rate of the flow.";
          smiv2:max-access "read-only";
          smiv2:oid "1.3.6.1.2.1.10.127.7.1.4.1.7";
        }
      }
    }

    container docsQosUpstreamStatsTable {
      description
       "This table describes statistics associated with  
        upstream service flows. All counted frames must 
        be received without an FCS error.";
      smiv2:oid "1.3.6.1.2.1.10.127.7.1.5";

      list docsQosUpstreamStatsEntry {
        key "ifIndex docsQosSID";
        description
         "Describes a set of upstream service flow statistics.
          An entry in the table exists for each 
          upstream Service Flow in a managed device. 
          The ifIndex is an ifType of docsCableMaclayer(127).";
        smiv2:oid "1.3.6.1.2.1.10.127.7.1.5.1";

        leaf ifIndex {
          type leafref {
            path "/if-mib:IF-MIB/if-mib:ifTable/if-mib:ifEntry/if-mib:ifIndex";
          }
        }

        leaf docsQosSID {
          type int32 {
            range "1..16383";
          }
          description
           "Identifies a service id for an admitted or active 
            upstream service flow.";
          smiv2:max-access "not-accessible";
          smiv2:oid "1.3.6.1.2.1.10.127.7.1.5.1.1";
        }

        leaf docsQosUpstreamFragments {
          type yang:counter32;
          description
           "The number of fragmentation headers received on an
            upstream  service flow, regardless of whether
            the fragment was correctly reassembled into a 
            valid packet. ";
          smiv2:max-access "read-only";
          smiv2:oid "1.3.6.1.2.1.10.127.7.1.5.1.2";
        }

        leaf docsQosUpstreamFragDiscards {
          type yang:counter32;
          description
           "The number of upstream fragments discarded and not 
            assembled into a valid upstream packet.";
          smiv2:max-access "read-only";
          smiv2:oid "1.3.6.1.2.1.10.127.7.1.5.1.3";
        }

        leaf docsQosUpstreamConcatBursts {
          type yang:counter32;
          description
           "The number of concatenation headers received on an 
            upstream service flow.";
          smiv2:max-access "read-only";
          smiv2:oid "1.3.6.1.2.1.10.127.7.1.5.1.4";
        }
      }
    }

    container docsQosDynamicServiceStatsTable {
      description
       "This table describes statistics associated with the  
        Dynamic Service Flows in a managed device. ";
      smiv2:oid "1.3.6.1.2.1.10.127.7.1.6";

      list docsQosDynamicServiceStatsEntry {
        key "ifIndex docsQosIfDirection";
        description
         "Describes a set of dynamic service flow statistics.
          Two entries exist for each Docsis mac layer 
          interface for the upstream and downstream direction.
          On the CMTS, the downstream direction row indicates
          messages transmitted or transactions originated
          by the CMTS. The upstream direction row indicates
          messages received or transaction originated by the
          CM. On the CM, the downstream direction row 
          indicates messages received or transactions
          originated by the CMTS. The upstream direction 
          row indicates messages transmitted by the CM or
          transactions originated by the CM.
          The ifIndex is an ifType of docsCableMaclayer(127).";
        smiv2:oid "1.3.6.1.2.1.10.127.7.1.6.1";

        leaf ifIndex {
          type leafref {
            path "/if-mib:IF-MIB/if-mib:ifTable/if-mib:ifEntry/if-mib:ifIndex";
          }
        }

        leaf docsQosIfDirection {
          type DOCS-QOS-MIB:IfDirection;
          description
           "The direction of interface.";
          smiv2:max-access "not-accessible";
          smiv2:oid "1.3.6.1.2.1.10.127.7.1.6.1.1";
        }

        leaf docsQosDSAReqs {
          type yang:counter32;
          description
           "The number of Dynamic Service Addition Requests,
            including retries.";
          smiv2:max-access "read-only";
          smiv2:oid "1.3.6.1.2.1.10.127.7.1.6.1.2";
        }

        leaf docsQosDSARsps {
          type yang:counter32;
          description
           "The number of Dynamic Service Addition Responses,
            including retries.";
          smiv2:max-access "read-only";
          smiv2:oid "1.3.6.1.2.1.10.127.7.1.6.1.3";
        }

        leaf docsQosDSAAcks {
          type yang:counter32;
          description
           "The number of Dynamic Service Addition Acknowledgements,
            including retries.";
          smiv2:max-access "read-only";
          smiv2:oid "1.3.6.1.2.1.10.127.7.1.6.1.4";
        }

        leaf docsQosDSCReqs {
          type yang:counter32;
          description
           "The number of Dynamic Service Change Requests,
            including retries.";
          smiv2:max-access "read-only";
          smiv2:oid "1.3.6.1.2.1.10.127.7.1.6.1.5";
        }

        leaf docsQosDSCRsps {
          type yang:counter32;
          description
           "The number of Dynamic Service Change Responses,
            including retries.";
          smiv2:max-access "read-only";
          smiv2:oid "1.3.6.1.2.1.10.127.7.1.6.1.6";
        }

        leaf docsQosDSCAcks {
          type yang:counter32;
          description
           "The number of Dynamic Service Change Acknowledgements,
            including retries.";
          smiv2:max-access "read-only";
          smiv2:oid "1.3.6.1.2.1.10.127.7.1.6.1.7";
        }

        leaf docsQosDSDReqs {
          type yang:counter32;
          description
           "The number of Dynamic Service Delete Requests,
            including retries.";
          smiv2:max-access "read-only";
          smiv2:oid "1.3.6.1.2.1.10.127.7.1.6.1.8";
        }

        leaf docsQosDSDRsps {
          type yang:counter32;
          description
           "The number of Dynamic Service Delete Responses,
            including retries.";
          smiv2:max-access "read-only";
          smiv2:oid "1.3.6.1.2.1.10.127.7.1.6.1.9";
        }

        leaf docsQosDynamicAdds {
          type yang:counter32;
          description
           "The number of successful Dynamic Service Addition
            transactions.";
          smiv2:max-access "read-only";
          smiv2:oid "1.3.6.1.2.1.10.127.7.1.6.1.10";
        }

        leaf docsQosDynamicAddFails {
          type yang:counter32;
          description
           "The number of failed Dynamic Service Addition
            transactions.";
          smiv2:max-access "read-only";
          smiv2:oid "1.3.6.1.2.1.10.127.7.1.6.1.11";
        }

        leaf docsQosDynamicChanges {
          type yang:counter32;
          description
           "The number of successful Dynamic Service Change
            transactions.";
          smiv2:max-access "read-only";
          smiv2:oid "1.3.6.1.2.1.10.127.7.1.6.1.12";
        }

        leaf docsQosDynamicChangeFails {
          type yang:counter32;
          description
           "The number of failed Dynamic Service Change
            transactions.";
          smiv2:max-access "read-only";
          smiv2:oid "1.3.6.1.2.1.10.127.7.1.6.1.13";
        }

        leaf docsQosDynamicDeletes {
          type yang:counter32;
          description
           "The number of successful Dynamic Service Delete
            transactions.";
          smiv2:max-access "read-only";
          smiv2:oid "1.3.6.1.2.1.10.127.7.1.6.1.14";
        }

        leaf docsQosDynamicDeleteFails {
          type yang:counter32;
          description
           "The number of failed Dynamic Service Delete
            transactions.";
          smiv2:max-access "read-only";
          smiv2:oid "1.3.6.1.2.1.10.127.7.1.6.1.15";
        }

        leaf docsQosDCCReqs {
          type yang:counter32;
          description
           "The number of Dynamic Channel Change Request messages
            traversing an interface. This count is nonzero only on
            downstream direction rows. This count should
            include number of retries.";
          smiv2:max-access "read-only";
          smiv2:oid "1.3.6.1.2.1.10.127.7.1.6.1.16";
        }

        leaf docsQosDCCRsps {
          type yang:counter32;
          description
           "The number of Dynamic Channel Change Response messages
            traversing an interface. This count is nonzero
            only on upstream direction rows. This count should
            include number of retries.";
          smiv2:max-access "read-only";
          smiv2:oid "1.3.6.1.2.1.10.127.7.1.6.1.17";
        }

        leaf docsQosDCCAcks {
          type yang:counter32;
          description
           "The number of Dynamic Channel Change Acknowledgement
            messages traversing an interface. This count
            is nonzero only on downstream direction rows.
            This count should include number of retries.";
          smiv2:max-access "read-only";
          smiv2:oid "1.3.6.1.2.1.10.127.7.1.6.1.18";
        }

        leaf docsQosDCCs {
          type yang:counter32;
          description
           "The number of successful Dynamic Channel Change
            transactions. This count is nonzero only on downstream
            direction rows.";
          smiv2:max-access "read-only";
          smiv2:oid "1.3.6.1.2.1.10.127.7.1.6.1.19";
        }

        leaf docsQosDCCFails {
          type yang:counter32;
          description
           "The number of failed Dynamic Channel Change
            transactions. This count is nonzero only on
            downstream direction rows.";
          smiv2:max-access "read-only";
          smiv2:oid "1.3.6.1.2.1.10.127.7.1.6.1.20";
        }

        leaf docsQosDCCRspDeparts {
          type yang:counter32;
          description
           "The number of Dynamic Channel Change Response (depart)
            messages traversing an interface. This count is only counted 
            on upstream direction rows.";
          reference
           "SP-RFIv2.0-I04-037030, Figures 11-59, 11-60, 11-61, 11-62";
          smiv2:max-access "read-only";
          smiv2:oid "1.3.6.1.2.1.10.127.7.1.6.1.21";
        }

        leaf docsQosDCCRspArrives {
          type yang:counter32;
          description
           "The number of Dynamic Channel Change Response (arrive)
            messages traversing an interface. This count is only counted on
            upstream direction rows. This count should include number of retries.";
          reference
           "SP-RFIv2.0-I04-037030, Figures 11-59, 11-60, 11-61, 11-62";
          smiv2:max-access "read-only";
          smiv2:oid "1.3.6.1.2.1.10.127.7.1.6.1.22";
        }
      }
    }

    container docsQosServiceFlowLogTable {
      description
       "This table contains a log of the disconnected
        Service Flows in a managed device.";
      smiv2:oid "1.3.6.1.2.1.10.127.7.1.7";

      list docsQosServiceFlowLogEntry {
        key "docsQosServiceFlowLogIndex";
        description
         "The information regarding a single disconnected 
          service flow.";
        smiv2:oid "1.3.6.1.2.1.10.127.7.1.7.1";

        leaf docsQosServiceFlowLogIndex {
          type uint32;
          description
           "Unique index for a logged service flow.";
          smiv2:max-access "not-accessible";
          smiv2:oid "1.3.6.1.2.1.10.127.7.1.7.1.1";
        }

        leaf docsQosServiceFlowLogIfIndex {
          type if-mib:InterfaceIndex;
          description
           "The ifIndex of ifType docsCableMaclayer(127) 
            on the CMTS where the service flow was present.";
          smiv2:max-access "read-only";
          smiv2:oid "1.3.6.1.2.1.10.127.7.1.7.1.2";
        }

        leaf docsQosServiceFlowLogSFID {
          type uint32 {
            range "1..4294967295";
          }
          description
           "The index assigned to the service flow by the CMTS.";
          smiv2:max-access "read-only";
          smiv2:oid "1.3.6.1.2.1.10.127.7.1.7.1.3";
        }

        leaf docsQosServiceFlowLogCmMac {
          type yang:mac-address;
          description
           "The MAC address for the cable modem associated with 
            the service flow.";
          smiv2:max-access "read-only";
          smiv2:oid "1.3.6.1.2.1.10.127.7.1.7.1.4";
        }

        leaf docsQosServiceFlowLogPkts {
          type yang:counter32;
          description
           "The number of packets counted on this service flow 
            after payload header suppression.";
          smiv2:max-access "read-only";
          smiv2:oid "1.3.6.1.2.1.10.127.7.1.7.1.5";
        }

        leaf docsQosServiceFlowLogOctets {
          type yang:counter32;
          description
           "The number of octets counted on this service flow 
            after payload header suppression.";
          smiv2:max-access "read-only";
          smiv2:oid "1.3.6.1.2.1.10.127.7.1.7.1.6";
        }

        leaf docsQosServiceFlowLogTimeDeleted {
          type yang:timestamp;
          description
           "The value of sysUpTime when the service flow 
            was deleted.";
          smiv2:max-access "read-only";
          smiv2:oid "1.3.6.1.2.1.10.127.7.1.7.1.7";
        }

        leaf docsQosServiceFlowLogTimeCreated {
          type yang:timestamp;
          description
           "The value of sysUpTime when the service flow 
            was created.";
          smiv2:max-access "read-only";
          smiv2:oid "1.3.6.1.2.1.10.127.7.1.7.1.8";
        }

        leaf docsQosServiceFlowLogTimeActive {
          type yang:counter32;
          units "seconds";
          description
           "The total time that service flow was active.";
          smiv2:max-access "read-only";
          smiv2:oid "1.3.6.1.2.1.10.127.7.1.7.1.9";
        }

        leaf docsQosServiceFlowLogDirection {
          type DOCS-QOS-MIB:IfDirection;
          description
           "The value of docsQosServiceFlowDirection 
            for the service flow.";
          smiv2:max-access "read-only";
          smiv2:oid "1.3.6.1.2.1.10.127.7.1.7.1.11";
        }

        leaf docsQosServiceFlowLogPrimary {
          type boolean;
          description
           "The value of docsQosServiceFlowPrimary for the 
            service flow.";
          smiv2:max-access "read-only";
          smiv2:oid "1.3.6.1.2.1.10.127.7.1.7.1.12";
        }

        leaf docsQosServiceFlowLogServiceClassName {
          type snmpv2-tc:DisplayString;
          description
           "The value of docsQosParamSetServiceClassName for
            the provisioned QOS Parameter Set of the 
            service flow.";
          smiv2:max-access "read-only";
          smiv2:oid "1.3.6.1.2.1.10.127.7.1.7.1.13";
        }

        leaf docsQosServiceFlowLogPolicedDropPkts {
          type yang:counter32;
          description
           "The final value of docsQosServiceFlowPolicedDropPkts
            for the service flow.";
          smiv2:max-access "read-only";
          smiv2:oid "1.3.6.1.2.1.10.127.7.1.7.1.14";
        }

        leaf docsQosServiceFlowLogPolicedDelayPkts {
          type yang:counter32;
          description
           "The final value of docsQosServiceFlowPolicedDelayPkts
            for the service flow.";
          smiv2:max-access "read-only";
          smiv2:oid "1.3.6.1.2.1.10.127.7.1.7.1.15";
        }

        leaf docsQosServiceFlowLogControl {
          type enumeration {
            enum "active" {
              value "1";
            }
            enum "destroy" {
              value "6";
            }
          }
          description
           "Setting this object to the value destroy(6) removes
            this entry from the table. 
            Reading this object return the value active(1).";
          smiv2:max-access "read-write";
          smiv2:oid "1.3.6.1.2.1.10.127.7.1.7.1.16";
        }
      }
    }

    container docsQosServiceClassTable {
      description
       "This table describes the set of Docsis-QOS 
        Service Classes in a CMTS. ";
      smiv2:oid "1.3.6.1.2.1.10.127.7.1.8";

      list docsQosServiceClassEntry {
        key "docsQosServiceClassName";
        description
         "A provisioned service class on a CMTS. 
          Each entry defines a template for certain 
          DOCSIS QOS Parameter Set values. When a CM 
          creates or modifies an Admitted QOS Parameter Set for a
          Service Flow, it may reference a Service Class
          Name instead of providing explicit QOS Parameter
          Set values. In this case, the CMTS populates
          the QOS Parameter Set with the applicable 
          corresponding values from the named Service Class.
          Subsequent changes to a Service Class row do *not* 
          affect the QOS Parameter Set values of any service flows
          already admitted.
          
          A service class template applies to only
          a single direction, as indicated in the 
          docsQosServiceClassDirection object.";
        smiv2:oid "1.3.6.1.2.1.10.127.7.1.8.1";

        leaf docsQosServiceClassName {
          type snmpv2-tc:DisplayString {
            length "1..15";
          }
          description
           "Service Class Name. DOCSIS specifies that the
            maximum size is 15 printable ASCII characters with 
            a terminating zero. The terminating zero is not
            represented in this DisplayString syntax object.";
          reference
           "SP-RFIv1.1-I07-010829, Appendix C.2.2.3.4";
          smiv2:max-access "not-accessible";
          smiv2:oid "1.3.6.1.2.1.10.127.7.1.8.1.1";
        }

        leaf docsQosServiceClassParamSetIndex {
          type uint32 {
            range "0..4294967295";
          }
          status obsolete;
          description
           "This object is obsolete.";
          smiv2:max-access "read-write";
          smiv2:oid "1.3.6.1.2.1.10.127.7.1.8.1.2";
        }

        leaf docsQosServiceClassStatus {
          type snmpv2-tc:RowStatus;
          description
           "Used to create or delete rows in this table.";
          smiv2:max-access "read-write";
          smiv2:oid "1.3.6.1.2.1.10.127.7.1.8.1.3";
        }

        leaf docsQosServiceClassPriority {
          type int32 {
            range "0..7";
          }
          description
           "Template for docsQosParamSetPriority.";
          smiv2:defval "0";
          smiv2:max-access "read-write";
          smiv2:oid "1.3.6.1.2.1.10.127.7.1.8.1.4";
        }

        leaf docsQosServiceClassMaxTrafficRate {
          type DOCS-QOS-MIB:DOCSQOSBitRate;
          description
           "Template for docsQosParamSetMaxTrafficRate.";
          smiv2:defval "0";
          smiv2:max-access "read-write";
          smiv2:oid "1.3.6.1.2.1.10.127.7.1.8.1.5";
        }

        leaf docsQosServiceClassMaxTrafficBurst {
          type uint32;
          description
           "Template for docsQosParamSetMaxTrafficBurst.";
          smiv2:defval "1522";
          smiv2:max-access "read-write";
          smiv2:oid "1.3.6.1.2.1.10.127.7.1.8.1.6";
        }

        leaf docsQosServiceClassMinReservedRate {
          type DOCS-QOS-MIB:DOCSQOSBitRate;
          description
           "Template for docsQosParamSEtMinReservedRate.";
          smiv2:defval "0";
          smiv2:max-access "read-write";
          smiv2:oid "1.3.6.1.2.1.10.127.7.1.8.1.7";
        }

        leaf docsQosServiceClassMinReservedPkt {
          type int32 {
            range "0..65535";
          }
          description
           "Template for docsQosParamSetMinReservedPkt.";
          smiv2:max-access "read-write";
          smiv2:oid "1.3.6.1.2.1.10.127.7.1.8.1.8";
        }

        leaf docsQosServiceClassMaxConcatBurst {
          type int32 {
            range "0..65535";
          }
          description
           "Template for docsQosParamSetMaxConcatBurst.";
          smiv2:defval "0";
          smiv2:max-access "read-write";
          smiv2:oid "1.3.6.1.2.1.10.127.7.1.8.1.9";
        }

        leaf docsQosServiceClassNomPollInterval {
          type uint32;
          units "microseconds";
          description
           "Template for docsQosParamSetNomPollInterval.";
          smiv2:defval "0";
          smiv2:max-access "read-write";
          smiv2:oid "1.3.6.1.2.1.10.127.7.1.8.1.10";
        }

        leaf docsQosServiceClassTolPollJitter {
          type uint32;
          units "microseconds";
          description
           "Template for docsQosParamSetTolPollJitter.";
          smiv2:defval "0";
          smiv2:max-access "read-write";
          smiv2:oid "1.3.6.1.2.1.10.127.7.1.8.1.11";
        }

        leaf docsQosServiceClassUnsolicitGrantSize {
          type int32 {
            range "0..65535";
          }
          description
           "Template for docsQosParamSetUnsolicitGrantSize.";
          smiv2:defval "0";
          smiv2:max-access "read-write";
          smiv2:oid "1.3.6.1.2.1.10.127.7.1.8.1.12";
        }

        leaf docsQosServiceClassNomGrantInterval {
          type uint32;
          units "microseconds";
          description
           "Template for docsQosParamSetNomGrantInterval.";
          smiv2:defval "0";
          smiv2:max-access "read-write";
          smiv2:oid "1.3.6.1.2.1.10.127.7.1.8.1.13";
        }

        leaf docsQosServiceClassTolGrantJitter {
          type uint32;
          units "microseconds";
          description
           "Template for docsQosParamSetTolGrantJitter.";
          smiv2:defval "0";
          smiv2:max-access "read-write";
          smiv2:oid "1.3.6.1.2.1.10.127.7.1.8.1.14";
        }

        leaf docsQosServiceClassGrantsPerInterval {
          type int32 {
            range "0..127";
          }
          description
           "Template for docsQosParamSetGrantsPerInterval.";
          smiv2:defval "0";
          smiv2:max-access "read-write";
          smiv2:oid "1.3.6.1.2.1.10.127.7.1.8.1.15";
        }

        leaf docsQosServiceClassMaxLatency {
          type uint32;
          units "microseconds";
          description
           "Template for docsQosParamSetClassMaxLatency.";
          reference
           "SP-RFIv1.1-I07-010829, Appendix C.2.2.7.1";
          smiv2:defval "0";
          smiv2:max-access "read-write";
          smiv2:oid "1.3.6.1.2.1.10.127.7.1.8.1.16";
        }

        leaf docsQosServiceClassActiveTimeout {
          type int32 {
            range "0..65535";
          }
          units "seconds";
          description
           "Template for docsQosParamSetActiveTimeout.";
          smiv2:defval "0";
          smiv2:max-access "read-write";
          smiv2:oid "1.3.6.1.2.1.10.127.7.1.8.1.17";
        }

        leaf docsQosServiceClassAdmittedTimeout {
          type int32 {
            range "0..65535";
          }
          units "seconds";
          description
           "Template for docsQosParamSetAdmittedTimeout.";
          smiv2:defval "200";
          smiv2:max-access "read-write";
          smiv2:oid "1.3.6.1.2.1.10.127.7.1.8.1.18";
        }

        leaf docsQosServiceClassSchedulingType {
          type DOCS-QOS-MIB:SchedulingType;
          description
           "Template for docsQosParamSetSchedulingType.";
          smiv2:defval "bestEffort";
          smiv2:max-access "read-write";
          smiv2:oid "1.3.6.1.2.1.10.127.7.1.8.1.19";
        }

        leaf docsQosServiceClassRequestPolicy {
          type binary {
            length "4";
          }
          description
           "Template for docsQosParamSetRequestPolicyOct.";
          smiv2:defval "'00000000'H";
          smiv2:max-access "read-write";
          smiv2:oid "1.3.6.1.2.1.10.127.7.1.8.1.20";
        }

        leaf docsQosServiceClassTosAndMask {
          type binary {
            length "1";
          }
          description
           "Template for docsQosParamSetTosAndMask.";
          smiv2:defval "'ff'H";
          smiv2:max-access "read-write";
          smiv2:oid "1.3.6.1.2.1.10.127.7.1.8.1.21";
        }

        leaf docsQosServiceClassTosOrMask {
          type binary {
            length "1";
          }
          description
           "Template for docsQosParamSetTosOrMask.";
          smiv2:defval "'00'H";
          smiv2:max-access "read-write";
          smiv2:oid "1.3.6.1.2.1.10.127.7.1.8.1.22";
        }

        leaf docsQosServiceClassDirection {
          type DOCS-QOS-MIB:IfDirection;
          description
           "Specifies whether the service class template
            applies to upstream or downstream service flows.";
          smiv2:defval "upstream";
          smiv2:max-access "read-write";
          smiv2:oid "1.3.6.1.2.1.10.127.7.1.8.1.23";
        }
      }
    }

    container docsQosServiceClassPolicyTable {
      description
       "This table describes the set of Docsis-QOS 
        Service Class Policies.  
        
        This table is an adjunct to the
        docsDevFilterPolicy table.  Entries in 
        docsDevFilterPolicy table can  point to 
        specific rows in this table.
        
        This table permits mapping a packet to a service
        class name of an active service flow so long as 
        a classifier does not exist at a higher
        priority.";
      reference
       "SP-RFIv1.1-I07-010829, Appendix E.2.1";
      smiv2:oid "1.3.6.1.2.1.10.127.7.1.9";

      list docsQosServiceClassPolicyEntry {
        key "docsQosServiceClassPolicyIndex";
        description
         "A service class name policy entry.";
        smiv2:oid "1.3.6.1.2.1.10.127.7.1.9.1";

        leaf docsQosServiceClassPolicyIndex {
          type int32 {
            range "1..2147483647";
          }
          description
           "Index value to uniquely identify an entry in
            this table.";
          smiv2:max-access "not-accessible";
          smiv2:oid "1.3.6.1.2.1.10.127.7.1.9.1.1";
        }

        leaf docsQosServiceClassPolicyName {
          type snmpv2-tc:DisplayString;
          description
           "Service Class Name to identify the name of the 
            service class flow to which the packet should be
            directed.";
          reference
           "SP-RFIv1.1-I07-010829, Appendix E.2.1";
          smiv2:max-access "read-write";
          smiv2:oid "1.3.6.1.2.1.10.127.7.1.9.1.2";
        }

        leaf docsQosServiceClassPolicyRulePriority {
          type int32 {
            range "0..255";
          }
          description
           "Service Class Policy rule priority for the
            entry.";
          reference
           "SP-RFIv1.1-I07-010829, Appendix C.2.1.3.5";
          smiv2:max-access "read-write";
          smiv2:oid "1.3.6.1.2.1.10.127.7.1.9.1.3";
        }

        leaf docsQosServiceClassPolicyStatus {
          type snmpv2-tc:RowStatus;
          description
           "Used to create or delete rows in this table.
            This object should not be deleted if it is
            reference by an entry in docsDevFilterPolicy.
            The reference should be deleted first.";
          smiv2:max-access "read-write";
          smiv2:oid "1.3.6.1.2.1.10.127.7.1.9.1.4";
        }
      }
    }

    container docsQosPHSTable {
      description
       "This table describes set of payload header
        suppression entries.";
      smiv2:oid "1.3.6.1.2.1.10.127.7.1.10";

      list docsQosPHSEntry {
        key "ifIndex docsQosServiceFlowId docsQosPktClassId";
        description
         "A payload header suppression entry. 
          The ifIndex is an ifType of docsCableMaclayer(127).
          The index docsQosServiceFlowId selects one
          service flow from the cable MAC layer interface.
          The docsQosPktClassId index matches an
          index of the docsQosPktClassTable.";
        smiv2:oid "1.3.6.1.2.1.10.127.7.1.10.1";

        leaf ifIndex {
          type leafref {
            path "/if-mib:IF-MIB/if-mib:ifTable/if-mib:ifEntry/if-mib:ifIndex";
          }
        }

        leaf docsQosServiceFlowId {
          type leafref {
            path "/DOCS-QOS-MIB:DOCS-QOS-MIB/DOCS-QOS-MIB:docsQosServiceFlowTable/DOCS-QOS-MIB:docsQosServiceFlowEntry/DOCS-QOS-MIB:docsQosServiceFlowId";
          }
        }

        leaf docsQosPktClassId {
          type leafref {
            path "/DOCS-QOS-MIB:DOCS-QOS-MIB/DOCS-QOS-MIB:docsQosPktClassTable/DOCS-QOS-MIB:docsQosPktClassEntry/DOCS-QOS-MIB:docsQosPktClassId";
          }
        }

        leaf docsQosPHSField {
          type binary {
            length "0..255";
          }
          description
           "Payload header suppression field defines the 
            bytes of the header which must be 
            suppressed/restored by the sending/receiving 
            device.
            
            The number of octets in this object should be
            the same as the value of docsQosPHSSize.";
          reference
           "SP-RFIv1.1-I07-010829, Appendix C.2.2.10.1";
          smiv2:max-access "read-only";
          smiv2:oid "1.3.6.1.2.1.10.127.7.1.10.1.2";
        }

        leaf docsQosPHSMask {
          type binary {
            length "0..32";
          }
          description
           "Payload header suppression mask defines the 
            bit mask which used in combination with the
            docsQosPHSField defines which bytes in header
            must be suppressed/restored by the sending or
            receiving device.
            
            Each bit of this bit mask corresponds to a byte
            in the docsQosPHSField, with the least 
            significant  bit corresponding to first byte of
            the docsQosPHSField.
            
            Each bit of the bit mask specifies whether of
            not the corresponding byte should be suppressed
            in the packet. A bit value of '1' indicates that
            the byte should be suppressed by the sending 
            device and restored by the receiving device. 
            A bit value of '0' indicates that 
            the byte should not be suppressed by the sending
            device or restored by the receiving device.
            
            If the bit mask does not contain a bit for each
            byte in the docsQosPHSField then the bit mask is
            extended with bit values of '1' to be the
            necessary length.";
          reference
           "SP-RFIv1.1-I07-010829, Appendix C.2.2.10.3";
          smiv2:max-access "read-only";
          smiv2:oid "1.3.6.1.2.1.10.127.7.1.10.1.3";
        }

        leaf docsQosPHSSize {
          type int32 {
            range "0..255";
          }
          description
           "Payload header suppression size specifies the 
            number of bytes in the header to be suppressed
            and restored.
            
            The value of this object must match the number
            of bytes in the docsQosPHSField.";
          reference
           "SP-RFIv1.1-I07-010829, Appendix C.2.2.10.4";
          smiv2:max-access "read-only";
          smiv2:oid "1.3.6.1.2.1.10.127.7.1.10.1.4";
        }

        leaf docsQosPHSVerify {
          type boolean;
          description
           "Payload header suppression verification value of
            'true' the sender must verify docsQosPHSField 
            is the same as what is contained in the packet
            to be suppressed.";
          reference
           "SP-RFIv1.1-I07-010829, Appendix C.2.2.10.5";
          smiv2:max-access "read-only";
          smiv2:oid "1.3.6.1.2.1.10.127.7.1.10.1.5";
        }

        leaf docsQosPHSClassifierIndex {
          type int32 {
            range "1..65535";
          }
          status obsolete;
          description
           "This object is obsolete.";
          smiv2:max-access "read-only";
          smiv2:oid "1.3.6.1.2.1.10.127.7.1.10.1.6";
        }

        leaf docsQosPHSIndex {
          type int32 {
            range "1..255";
          }
          description
           "Payload header suppression index uniquely 
            references the PHS rule for a given service flow.";
          reference
           "SP-RFIv1.1-I07-010829, Appendix C.2.2.10.2";
          smiv2:max-access "read-only";
          smiv2:oid "1.3.6.1.2.1.10.127.7.1.10.1.7";
        }
      }
    }

    container docsQosCmtsMacToSrvFlowTable {
      description
       "This table provide for referencing the service flows 
        associated with a particular cable modem. This allows 
        for indexing into other docsQos tables that are 
        indexed by docsQosServiceFlowId and ifIndex.";
      smiv2:oid "1.3.6.1.2.1.10.127.7.1.11";

      list docsQosCmtsMacToSrvFlowEntry {
        key "docsQosCmtsCmMac docsQosCmtsServiceFlowId";
        description
         "An entry is created by CMTS for each service flow 
          connected to this CMTS.";
        smiv2:oid "1.3.6.1.2.1.10.127.7.1.11.1";

        leaf docsQosCmtsCmMac {
          type yang:mac-address;
          description
           "The MAC address for the referenced CM.";
          smiv2:max-access "not-accessible";
          smiv2:oid "1.3.6.1.2.1.10.127.7.1.11.1.1";
        }

        leaf docsQosCmtsServiceFlowId {
          type uint32 {
            range "1..4294967295";
          }
          description
           "An index assigned to a service flow by CMTS.";
          smiv2:max-access "not-accessible";
          smiv2:oid "1.3.6.1.2.1.10.127.7.1.11.1.2";
        }

        leaf docsQosCmtsIfIndex {
          type if-mib:InterfaceIndex;
          description
           "The ifIndex of ifType docsCableMacLayter(127) 
            on the CMTS that is connected to the Cable Modem.";
          smiv2:max-access "read-only";
          smiv2:oid "1.3.6.1.2.1.10.127.7.1.11.1.3";
        }
      }
    }
  }

  smiv2:alias "docsQosMIB" {
    smiv2:oid "1.3.6.1.2.1.10.127.7";
  }

  smiv2:alias "docsQosMIBObjects" {
    smiv2:oid "1.3.6.1.2.1.10.127.7.1";
  }

  smiv2:alias "docsQosNotification" {
    smiv2:oid "1.3.6.1.2.1.10.127.7.2";
  }

  smiv2:alias "docsQosConformance" {
    smiv2:oid "1.3.6.1.2.1.10.127.7.3";
  }

  smiv2:alias "docsQosGroups" {
    smiv2:oid "1.3.6.1.2.1.10.127.7.3.1";
  }

  smiv2:alias "docsQosCompliances" {
    smiv2:oid "1.3.6.1.2.1.10.127.7.3.2";
  }

}
