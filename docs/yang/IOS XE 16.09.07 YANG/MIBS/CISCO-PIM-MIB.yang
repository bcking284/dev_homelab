/*
 * Generated by confdc --mib2yang-std
 * Source: mgmt/dmi/model/mib/src/CISCO-PIM-MIB.mib
 */
/*
 * This YANG module has been generated by smidump 0.5.0:
 *
 *      smidump -f yang CISCO-PIM-MIB
 *
 * Do not edit. Edit the source file instead!
 */

module CISCO-PIM-MIB {

  namespace "urn:ietf:params:xml:ns:yang:smiv2:CISCO-PIM-MIB";
  prefix CISCO-PIM-MIB;

  import INET-ADDRESS-MIB {
    prefix "inet-address";
  }

  import PIM-MIB {
    prefix "pim-mib";
  }

  import ietf-inet-types {
    prefix "inet";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA 95134
    USA
    
    Tel: +1 800 553-NETS
    
    EMail: cs-ipmulticast@cisco.com ";

  description
   "This MIB module defines the cisco specific variables
    for Protocol Independent Multicast (PIM) management. 
    These definitions are an extension of those defined in
    the IETF PIM MIB (RFC 2934).";

  revision 2000-11-02 {
    description
     "Initial version of this MIB module.";
  }


  container CISCO-PIM-MIB {
    config false;

    container cpim {
      smiv2:oid "1.3.6.1.4.1.9.9.184.1.1";

      leaf cpimInvalidRegisterMsgsRcvd {
        type yang:counter32;
        description
         "A count of the number of invalid PIM Register messages
          received by this device. A PIM Register message is
          termed invalid if 
          o the encapsulated IP header is malformed,
          o the destination of the PIM Register message is not the
            RP (Rendezvous Point) for the group in question,
          o the source/DR (Designated Router) address is not a valid
            unicast address.";
        smiv2:max-access "read-only";
        smiv2:oid "1.3.6.1.4.1.9.9.184.1.1.1";
      }

      leaf cpimInvalidJoinPruneMsgsRcvd {
        type yang:counter32;
        description
         "A count of the number of invalid PIM Join/Prune
          messages received by this device. A PIM Join/Prune
          message is termed invalid if
          
          o the RP specified in the packet is not the RP for
            the group in question.";
        smiv2:max-access "read-only";
        smiv2:oid "1.3.6.1.4.1.9.9.184.1.1.2";
      }

      leaf cpimLastErrorType {
        type enumeration {
          enum "none" {
            value "1";
          }
          enum "invalidRegister" {
            value "2";
          }
          enum "invalidJoinPrune" {
            value "3";
          }
        }
        description
         "The type of the last invalid message that was received by
          this device.";
        smiv2:max-access "read-only";
        smiv2:oid "1.3.6.1.4.1.9.9.184.1.1.3";
      }

      leaf cpimLastErrorOriginType {
        type inet-address:InetAddressType;
        description
         "Represents the type of address stored in
          cpimLastErrorOrigin. The value of this object is
          irrelevant if the value of cpimLastErrorType is none(1).";
        smiv2:max-access "read-only";
        smiv2:oid "1.3.6.1.4.1.9.9.184.1.1.4";
      }

      leaf cpimLastErrorOrigin {
        type inet-address:InetAddress;
        description
         "This object represents the Network Layer Address of the
          source that originated the last invalid packet. The type
          of address stored depends on the value in
          cpimLastErrorOriginType. 
          
          The value of this object represents the Network Layer
          Address of the Designated Router (DR) whenever the value
          of cpimLastErrorGroup is a zero-length address, 
          for eg. when encapsulated IP header is malformed.
          
          The value of this object is irrelevant if the value of
          cpimLastErrorType is none(1).";
        smiv2:max-access "read-only";
        smiv2:oid "1.3.6.1.4.1.9.9.184.1.1.5";
      }

      leaf cpimLastErrorGroupType {
        type inet-address:InetAddressType;
        description
         "Represents the type of address stored in
          cpimLastErrorGroup. The value of this object is unknown(0)
          if there is a problem in the packet received from the
          DR.
          
          The value of this object is irrelevant if the value of
          cpimLastErrorType is none(1).";
        smiv2:max-access "read-only";
        smiv2:oid "1.3.6.1.4.1.9.9.184.1.1.6";
      }

      leaf cpimLastErrorGroup {
        type inet-address:InetAddress;
        description
         "The IP multicast group address to which the last invalid
          packet was addressed. The type of address stored
          depends on the value in cpimLastErrorGroupType. 
          
          The value of this object is a zero-length InetAddress if
          there is a problem in the packet received from the DR,
          for eg. a malformed encapsulated IP header. 
          
          The value of this object is irrelevant if the value of
          cpimLastErrorType is none(1).";
        smiv2:max-access "read-only";
        smiv2:oid "1.3.6.1.4.1.9.9.184.1.1.7";
      }

      leaf cpimLastErrorRPType {
        type inet-address:InetAddressType;
        description
         "Represents the type of address stored in
          cpimLastErrorRP. The value of this object is irrelevant
          if the value of cpimLastErrorType is none(1).";
        smiv2:max-access "read-only";
        smiv2:oid "1.3.6.1.4.1.9.9.184.1.1.8";
      }

      leaf cpimLastErrorRP {
        type inet-address:InetAddress;
        description
         "The address of the RP, as per the last invalid
          packet. The type of address stored depends on the value in
          cpimLastErrorRPType. 
          
          The value of this object is irrelevant if the value of
          cpimLastErrorType is none(1).";
        smiv2:max-access "read-only";
        smiv2:oid "1.3.6.1.4.1.9.9.184.1.1.9";
      }
    }

    container ciscoPimMIBNotificationObjects {
      smiv2:oid "1.3.6.1.4.1.9.9.184.2.1";

      leaf cpimRPMappingChangeType {
        type enumeration {
          enum "newMapping" {
            value "1";
          }
          enum "deletedMapping" {
            value "2";
          }
          enum "modifiedOldMapping" {
            value "3";
          }
          enum "modifiedNewMapping" {
            value "4";
          }
        }
        description
         "Describes the operation that resulted in generation
          of cpimRPMappingChange notification.
          
          o newMapping, as the name suggests indicates that a new
            mapping has been added into the pimRPSetTable, 
          o deletedMapping indicates that a mapping has been 
            deleted from the pimRPSetTable, and,
          o modifiedXXXMapping indicates that an RP mapping (which
            already existed in the table) has been modified.
            The two modifications types i.e. modifiedOldMapping
            and modifiedNewMapping, are defined to differentiate
            the notification generated before modification from
            that generated after modification.";
        smiv2:max-access "read-only";
        smiv2:oid "1.3.6.1.4.1.9.9.184.2.1.1";
      }
    }
  }

  notification ciscoPimInterfaceUp {
    description
     "A ciscoPimInterfaceUp notification signifies the 
      restoration of a PIM interface. This notification
      should be generated whenever pimInterfaceStatus
      transitions into the 'active' state.
      pimInterfaceStatus identifies the interface which 
      was involved in the generation of this notification.";
    smiv2:oid "1.3.6.1.4.1.9.9.184.2.0.1";

    container object-1 {

      leaf pimInterfaceIfIndex {
        type leafref {
          path "/pim-mib:PIM-MIB/pim-mib:pimInterfaceTable/pim-mib:pimInterfaceEntry/pim-mib:pimInterfaceIfIndex";
        }
      }

      leaf pimInterfaceStatus {
        type leafref {
          path "/pim-mib:PIM-MIB/pim-mib:pimInterfaceTable/pim-mib:pimInterfaceEntry/pim-mib:pimInterfaceStatus";
        }
      }
    }
  }

  notification ciscoPimInterfaceDown {
    description
     "A ciscoPimInterfaceDown notification signifies the loss
      of a PIM interface. This notification should be generated 
      whenever an entry is about to be deleted from the
      PimInterfaceTable.
      pimInterfaceStatus identifies the interface which 
      was involved in the generation of this notification.";
    smiv2:oid "1.3.6.1.4.1.9.9.184.2.0.2";

    container object-1 {

      leaf pimInterfaceIfIndex {
        type leafref {
          path "/pim-mib:PIM-MIB/pim-mib:pimInterfaceTable/pim-mib:pimInterfaceEntry/pim-mib:pimInterfaceIfIndex";
        }
      }

      leaf pimInterfaceStatus {
        type leafref {
          path "/pim-mib:PIM-MIB/pim-mib:pimInterfaceTable/pim-mib:pimInterfaceEntry/pim-mib:pimInterfaceStatus";
        }
      }
    }
  }

  notification ciscoPimRPMappingChange {
    description
     "A ciscoPimRPMappingChange notification signifies a change
      in the RP Mapping on the device in question. A change in RP
      Mapping could be because of addition of new entries to the
      RP Mapping cache, deletion of existing entries, or a
      modification to an existing mapping. The type of change is
      indicated by cpimRPMappingChangeType. pimRPSetHoldTime 
      is used to identify the row in the pimRPSetTable that is
      responsible for the generation of this notification.
      
      In case of modification to existing entries, a
      notification should be generated once before the
      modification (with cpimRPMappingChangeType set to
      modifiedOldMapping) and once after modification (with 
      cpimRPMappingChangeType set to modifiedNewMapping).
      
      NOTE: A high frequency of RP Mapping change could result
      in a large number of ciscoPimRPMappingChange notifications
      being generated. Hence, in environments where the
      possibility of a high frequency of RP Mapping change
      exists, enable this notification with utmost care.";
    smiv2:oid "1.3.6.1.4.1.9.9.184.2.0.3";

    container object-1 {

      leaf pimRPSetComponent {
        type leafref {
          path "/pim-mib:PIM-MIB/pim-mib:pimRPSetTable/pim-mib:pimRPSetEntry/pim-mib:pimRPSetComponent";
        }
      }

      leaf pimRPSetGroupAddress {
        type leafref {
          path "/pim-mib:PIM-MIB/pim-mib:pimRPSetTable/pim-mib:pimRPSetEntry/pim-mib:pimRPSetGroupAddress";
        }
      }

      leaf pimRPSetGroupMask {
        type leafref {
          path "/pim-mib:PIM-MIB/pim-mib:pimRPSetTable/pim-mib:pimRPSetEntry/pim-mib:pimRPSetGroupMask";
        }
      }

      leaf pimRPSetAddress {
        type leafref {
          path "/pim-mib:PIM-MIB/pim-mib:pimRPSetTable/pim-mib:pimRPSetEntry/pim-mib:pimRPSetAddress";
        }
      }

      leaf pimRPSetHoldTime {
        type leafref {
          path "/pim-mib:PIM-MIB/pim-mib:pimRPSetTable/pim-mib:pimRPSetEntry/pim-mib:pimRPSetHoldTime";
        }
      }
    }

    container object-2 {

      leaf cpimRPMappingChangeType {
        type leafref {
          path "/CISCO-PIM-MIB:CISCO-PIM-MIB/CISCO-PIM-MIB:ciscoPimMIBNotificationObjects/CISCO-PIM-MIB:cpimRPMappingChangeType";
        }
      }
    }
  }

  notification ciscoPimInvalidRegister {
    description
     "A ciscoPimInvalidRegister notification signifies that 
      an invalid Register message was received by this device.
      
      This notification is generated whenever the 
      cpimInvalidRegisterMsgsRcvd counter is incremented.
      cpimLastErrorOrigin, cpimLastErrorGroup, and
      cpimLastErrorRP should signify the source address, group
      address and the RP address in the invalid register
      packet.";
    smiv2:oid "1.3.6.1.4.1.9.9.184.2.0.4";

    container object-1 {

      leaf cpimLastErrorOriginType {
        type leafref {
          path "/CISCO-PIM-MIB:CISCO-PIM-MIB/CISCO-PIM-MIB:cpim/CISCO-PIM-MIB:cpimLastErrorOriginType";
        }
      }
    }

    container object-2 {

      leaf cpimLastErrorOrigin {
        type leafref {
          path "/CISCO-PIM-MIB:CISCO-PIM-MIB/CISCO-PIM-MIB:cpim/CISCO-PIM-MIB:cpimLastErrorOrigin";
        }
      }
    }

    container object-3 {

      leaf cpimLastErrorGroupType {
        type leafref {
          path "/CISCO-PIM-MIB:CISCO-PIM-MIB/CISCO-PIM-MIB:cpim/CISCO-PIM-MIB:cpimLastErrorGroupType";
        }
      }
    }

    container object-4 {

      leaf cpimLastErrorGroup {
        type leafref {
          path "/CISCO-PIM-MIB:CISCO-PIM-MIB/CISCO-PIM-MIB:cpim/CISCO-PIM-MIB:cpimLastErrorGroup";
        }
      }
    }

    container object-5 {

      leaf cpimLastErrorRPType {
        type leafref {
          path "/CISCO-PIM-MIB:CISCO-PIM-MIB/CISCO-PIM-MIB:cpim/CISCO-PIM-MIB:cpimLastErrorRPType";
        }
      }
    }

    container object-6 {

      leaf cpimLastErrorRP {
        type leafref {
          path "/CISCO-PIM-MIB:CISCO-PIM-MIB/CISCO-PIM-MIB:cpim/CISCO-PIM-MIB:cpimLastErrorRP";
        }
      }
    }

    container object-7 {

      leaf cpimInvalidRegisterMsgsRcvd {
        type leafref {
          path "/CISCO-PIM-MIB:CISCO-PIM-MIB/CISCO-PIM-MIB:cpim/CISCO-PIM-MIB:cpimInvalidRegisterMsgsRcvd";
        }
      }
    }
  }

  notification ciscoPimInvalidJoinPrune {
    description
     "A ciscoPimInvalidJoinPrune notification signifies the
      receipt of an invalid join/prune message.             
      
      This notification is generated whenever the
      cpimInvalidJoinPruneMsgsRcvd counter is incremented.
      cpimLastErrorOrigin, cpimLastErrorGroup, and
      cpimLastErrorRP should signify the source address, group
      address and the RP address in the invalid join/prune
      packet.";
    smiv2:oid "1.3.6.1.4.1.9.9.184.2.0.5";

    container object-1 {

      leaf cpimLastErrorOriginType {
        type leafref {
          path "/CISCO-PIM-MIB:CISCO-PIM-MIB/CISCO-PIM-MIB:cpim/CISCO-PIM-MIB:cpimLastErrorOriginType";
        }
      }
    }

    container object-2 {

      leaf cpimLastErrorOrigin {
        type leafref {
          path "/CISCO-PIM-MIB:CISCO-PIM-MIB/CISCO-PIM-MIB:cpim/CISCO-PIM-MIB:cpimLastErrorOrigin";
        }
      }
    }

    container object-3 {

      leaf cpimLastErrorGroupType {
        type leafref {
          path "/CISCO-PIM-MIB:CISCO-PIM-MIB/CISCO-PIM-MIB:cpim/CISCO-PIM-MIB:cpimLastErrorGroupType";
        }
      }
    }

    container object-4 {

      leaf cpimLastErrorGroup {
        type leafref {
          path "/CISCO-PIM-MIB:CISCO-PIM-MIB/CISCO-PIM-MIB:cpim/CISCO-PIM-MIB:cpimLastErrorGroup";
        }
      }
    }

    container object-5 {

      leaf cpimLastErrorRPType {
        type leafref {
          path "/CISCO-PIM-MIB:CISCO-PIM-MIB/CISCO-PIM-MIB:cpim/CISCO-PIM-MIB:cpimLastErrorRPType";
        }
      }
    }

    container object-6 {

      leaf cpimLastErrorRP {
        type leafref {
          path "/CISCO-PIM-MIB:CISCO-PIM-MIB/CISCO-PIM-MIB:cpim/CISCO-PIM-MIB:cpimLastErrorRP";
        }
      }
    }

    container object-7 {

      leaf cpimInvalidJoinPruneMsgsRcvd {
        type leafref {
          path "/CISCO-PIM-MIB:CISCO-PIM-MIB/CISCO-PIM-MIB:cpim/CISCO-PIM-MIB:cpimInvalidJoinPruneMsgsRcvd";
        }
      }
    }
  }

  smiv2:alias "ciscoPimMIB" {
    smiv2:oid "1.3.6.1.4.1.9.9.184";
  }

  smiv2:alias "ciscoPimMIBObjects" {
    smiv2:oid "1.3.6.1.4.1.9.9.184.1";
  }

  smiv2:alias "cpim" {
    smiv2:oid "1.3.6.1.4.1.9.9.184.1.1";
  }

  smiv2:alias "ciscoPimMIBNotificationPrefix" {
    smiv2:oid "1.3.6.1.4.1.9.9.184.2";
  }

  smiv2:alias "ciscoPimMIBNotifications" {
    smiv2:oid "1.3.6.1.4.1.9.9.184.2.0";
  }

  smiv2:alias "ciscoPimMIBNotificationObjects" {
    smiv2:oid "1.3.6.1.4.1.9.9.184.2.1";
  }

  smiv2:alias "ciscoPimMIBConformance" {
    smiv2:oid "1.3.6.1.4.1.9.9.184.3";
  }

  smiv2:alias "ciscoPimMIBCompliances" {
    smiv2:oid "1.3.6.1.4.1.9.9.184.3.1";
  }

  smiv2:alias "ciscoPimMIBGroups" {
    smiv2:oid "1.3.6.1.4.1.9.9.184.3.2";
  }

}
