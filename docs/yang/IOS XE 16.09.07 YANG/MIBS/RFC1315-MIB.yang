/*
 * Generated by confdc --mib2yang-std
 * Source: mgmt/dmi/model/mib/src/RFC1315-MIB.mib
 */
/*
 * This YANG module has been generated by smidump 0.5.0:
 *
 *      smidump -f yang RFC1315-MIB
 *
 * Do not edit. Edit the source file instead!
 */

module RFC1315-MIB {

  namespace "urn:ietf:params:xml:ns:yang:smiv2:RFC1315-MIB";
  prefix RFC1315-MIB;

  import ietf-yang-smiv2 {
    prefix "smiv2";
  }

  import ietf-yang-types {
    prefix "yang";
  }

  typedef Index {
    type int32;
  }

  typedef DLCI {
    type int32;
  }


  container RFC1315-MIB {
    config false;

    container frame-relay-globals {
      smiv2:oid "1.3.6.1.2.1.10.32.4";

      leaf frTrapState {
        type enumeration {
          enum "enabled" {
            value "1";
          }
          enum "disabled" {
            value "2";
          }
        }
        description
         "This variable  indicates  whether  the  system
          produces the frDLCIStatusChange trap.";
        smiv2:defval "disabled";
        smiv2:max-access "read-write";
        smiv2:oid "1.3.6.1.2.1.10.32.4.1";
      }
    }

    container frDlcmiTable {
      description
       "The Parameters for the Data Link Connection Management
        Interface for the frame relay service on this
        interface.";
      reference
       "Draft American National Standard T1.617-1991, Annex D";
      smiv2:oid "1.3.6.1.2.1.10.32.1";

      list frDlcmiEntry {
        key "frDlcmiIfIndex";
        description
         "The Parameters for a particular Data Link Con-
          nection Management Interface.";
        smiv2:oid "1.3.6.1.2.1.10.32.1.1";

        leaf frDlcmiIfIndex {
          type RFC1315-MIB:Index;
          description
           "The ifIndex value of the  corresponding  ifEn-
            try.";
          smiv2:max-access "read-only";
          smiv2:oid "1.3.6.1.2.1.10.32.1.1.1";
        }

        leaf frDlcmiState {
          type enumeration {
            enum "noLmiConfigured" {
              value "1";
            }
            enum "lmiRev1" {
              value "2";
            }
            enum "ansiT1-617-D" {
              value "3";
            }
            enum "ansiT1-617-B" {
              value "4";
            }
          }
          description
           "This variable states which Data  Link  Connec-
            tion Management scheme is active (and by impli-
            cation, what DLCI it uses) on the  Frame  Relay
            interface.";
          reference
           "Draft American National Standard T1.617-1991";
          smiv2:max-access "read-write";
          smiv2:oid "1.3.6.1.2.1.10.32.1.1.2";
        }

        leaf frDlcmiAddress {
          type enumeration {
            enum "q921" {
              value "1";
            }
            enum "q922March90" {
              value "2";
            }
            enum "q922November90" {
              value "3";
            }
            enum "q922" {
              value "4";
            }
          }
          description
           "This variable states which address  format  is
            in use on the Frame Relay interface.";
          smiv2:max-access "read-write";
          smiv2:oid "1.3.6.1.2.1.10.32.1.1.3";
        }

        leaf frDlcmiAddressLen {
          type enumeration {
            enum "two-octets" {
              value "2";
            }
            enum "three-octets" {
              value "3";
            }
            enum "four-octets" {
              value "4";
            }
          }
          description
           "This variable states which address  length  in
            octets.  In the case of Q922 format, the length
            indicates the entire length of the address  in-
            cluding the control portion.";
          smiv2:max-access "read-write";
          smiv2:oid "1.3.6.1.2.1.10.32.1.1.4";
        }

        leaf frDlcmiPollingInterval {
          type int32 {
            range "5..30";
          }
          description
           "This is the number of seconds between  succes-
            sive status enquiry messages.";
          reference
           "Draft American National  Standard  T1.617-1991,
            Section D.7 Timer T391.";
          smiv2:defval "10";
          smiv2:max-access "read-write";
          smiv2:oid "1.3.6.1.2.1.10.32.1.1.5";
        }

        leaf frDlcmiFullEnquiryInterval {
          type int32 {
            range "1..255";
          }
          description
           "Number of status enquiry intervals  that  pass
            before  issuance  of a full status enquiry mes-
            sage.";
          reference
           "Draft American National  Standard  T1.617-1991,
            Section D.7 Counter N391.";
          smiv2:defval "6";
          smiv2:max-access "read-write";
          smiv2:oid "1.3.6.1.2.1.10.32.1.1.6";
        }

        leaf frDlcmiErrorThreshold {
          type int32 {
            range "1..10";
          }
          description
           "This  is  the  maximum  number  of  unanswered
            Status Enquiries the equipment shall accept be-
            fore declaring the interface down.";
          reference
           "Draft American National  Standard  T1.617-1991,
            Section D.5.1 Counter N392.";
          smiv2:defval "3";
          smiv2:max-access "read-write";
          smiv2:oid "1.3.6.1.2.1.10.32.1.1.7";
        }

        leaf frDlcmiMonitoredEvents {
          type int32 {
            range "1..10";
          }
          description
           "This is the number of status polling intervals
            over which the error threshold is counted.  For
            example, if within 'MonitoredEvents' number  of
            events  the  station  receives 'ErrorThreshold'
            number of errors, the interface  is  marked  as
            down.";
          reference
           "Draft American National  Standard  T1.617-1991,
            Section D.5.2 Counter N393.";
          smiv2:defval "4";
          smiv2:max-access "read-write";
          smiv2:oid "1.3.6.1.2.1.10.32.1.1.8";
        }

        leaf frDlcmiMaxSupportedVCs {
          type int32;
          description
           "The maximum number of Virtual Circuits allowed
            for  this  interface.   Usually dictated by the
            Frame Relay network.
            
            In response to a SET, if a value less than zero
            or  higher  than the agent's maximal capability
            is configured, the agent  should  respond  bad-
            Value";
          smiv2:max-access "read-write";
          smiv2:oid "1.3.6.1.2.1.10.32.1.1.9";
        }

        leaf frDlcmiMulticast {
          type enumeration {
            enum "nonBroadcast" {
              value "1";
            }
            enum "broadcast" {
              value "2";
            }
          }
          description
           "This indicates whether the Frame Relay  inter-
            face is using a multicast service.";
          smiv2:max-access "read-write";
          smiv2:oid "1.3.6.1.2.1.10.32.1.1.10";
        }
      }
    }

    container frCircuitTable {
      description
       "A table containing information about specific Data
        Link Connection Identifiers and corresponding virtual
        circuits.";
      smiv2:oid "1.3.6.1.2.1.10.32.2";

      list frCircuitEntry {
        key "frCircuitIfIndex frCircuitDlci";
        description
         "The information regarding a single  Data  Link
          Connection Identifier.";
        smiv2:oid "1.3.6.1.2.1.10.32.2.1";

        leaf frCircuitIfIndex {
          type RFC1315-MIB:Index;
          description
           "The ifIndex Value of the ifEntry this  virtual
            circuit is layered onto.";
          smiv2:max-access "read-only";
          smiv2:oid "1.3.6.1.2.1.10.32.2.1.1";
        }

        leaf frCircuitDlci {
          type RFC1315-MIB:DLCI;
          description
           "The Data Link Connection Identifier  for  this
            virtual circuit.";
          reference
           "Draft American National  Standard  T1.618-1991,
            Section 3.3.6";
          smiv2:max-access "read-only";
          smiv2:oid "1.3.6.1.2.1.10.32.2.1.2";
        }

        leaf frCircuitState {
          type enumeration {
            enum "invalid" {
              value "1";
            }
            enum "active" {
              value "2";
            }
            enum "inactive" {
              value "3";
            }
          }
          description
           "Indicates whether the particular virtual  cir-
            cuit  is operational.  In the absence of a Data
            Link Connection Management  Interface,  virtual
            circuit  entries  (rows) may be created by set-
            ting virtual  circuit  state  to  'active',  or
            deleted by changing Circuit state to 'invalid'.
            Whether or not the row actually  disappears  is
            left  to the implementation, so this object may
            actually read as 'invalid' for  some  arbitrary
            length  of  time.   It is also legal to set the
            state of a virtual  circuit  to  'inactive'  to
            temporarily disable a given circuit.";
          smiv2:defval "active";
          smiv2:max-access "read-write";
          smiv2:oid "1.3.6.1.2.1.10.32.2.1.3";
        }

        leaf frCircuitReceivedFECNs {
          type yang:counter32;
          description
           "Number of frames received from the network in-
            dicating  forward  congestion since the virtual
            circuit was created.";
          reference
           "Draft American National  Standard  T1.618-1991,
            Section 3.3.3";
          smiv2:max-access "read-only";
          smiv2:oid "1.3.6.1.2.1.10.32.2.1.4";
        }

        leaf frCircuitReceivedBECNs {
          type yang:counter32;
          description
           "Number of frames received from the network in-
            dicating  backward congestion since the virtual
            circuit was created.";
          reference
           "Draft American National  Standard  T1.618-1991,
            Section 3.3.4";
          smiv2:max-access "read-only";
          smiv2:oid "1.3.6.1.2.1.10.32.2.1.5";
        }

        leaf frCircuitSentFrames {
          type yang:counter32;
          description
           "The number of frames sent  from  this  virtual
            circuit since it was created.";
          smiv2:max-access "read-only";
          smiv2:oid "1.3.6.1.2.1.10.32.2.1.6";
        }

        leaf frCircuitSentOctets {
          type yang:counter32;
          description
           "The number of octets sent  from  this  virtual
            circuit since it was created.";
          smiv2:max-access "read-only";
          smiv2:oid "1.3.6.1.2.1.10.32.2.1.7";
        }

        leaf frCircuitReceivedFrames {
          type yang:counter32;
          description
           "Number of frames received  over  this  virtual
            circuit since it was created.";
          smiv2:max-access "read-only";
          smiv2:oid "1.3.6.1.2.1.10.32.2.1.8";
        }

        leaf frCircuitReceivedOctets {
          type yang:counter32;
          description
           "Number of octets received  over  this  virtual
            circuit since it was created.";
          smiv2:max-access "read-only";
          smiv2:oid "1.3.6.1.2.1.10.32.2.1.9";
        }

        leaf frCircuitCreationTime {
          type yang:timeticks;
          description
           "The value of sysUpTime when the  virtual  cir-
            cuit was created, whether by the Data Link Con-
            nection Management Interface  or  by  a  SetRe-
            quest.";
          smiv2:max-access "read-only";
          smiv2:oid "1.3.6.1.2.1.10.32.2.1.10";
        }

        leaf frCircuitLastTimeChange {
          type yang:timeticks;
          description
           "The value of sysUpTime when last there  was  a
            change in the virtual circuit state";
          smiv2:max-access "read-only";
          smiv2:oid "1.3.6.1.2.1.10.32.2.1.11";
        }

        leaf frCircuitCommittedBurst {
          type int32;
          description
           "This variable indicates the maximum amount  of
            data,  in  bits,  that  the  network  agrees to
            transfer under normal  conditions,  during  the
            measurement interval.";
          reference
           "Draft American National  Standard  T1.617-1991,
            Section 6.5.19";
          smiv2:defval "0";
          smiv2:max-access "read-write";
          smiv2:oid "1.3.6.1.2.1.10.32.2.1.12";
        }

        leaf frCircuitExcessBurst {
          type int32;
          description
           "This variable indicates the maximum amount  of
            uncommitted data bits that the network will at-
            tempt to deliver over the measurement interval.
            
            By default, if not configured when creating the
            entry, the Excess Information Burst Size is set
            to the value of ifSpeed.";
          reference
           "Draft American National  Standard  T1.617-1991,
            Section 6.5.19";
          smiv2:max-access "read-write";
          smiv2:oid "1.3.6.1.2.1.10.32.2.1.13";
        }

        leaf frCircuitThroughput {
          type int32;
          description
           "Throughput is the average number of 'Frame Re-
            lay  Information  Field'  bits  transferred per
            second across a user network interface  in  one
            direction, measured over the measurement inter-
            val.
            
            If the  configured  committed  burst  rate  and
            throughput  are  both non-zero, the measurement
            interval
            T=frCircuitCommittedBurst/frCircuitThroughput.
            
            If the  configured  committed  burst  rate  and
            throughput  are  both zero, the measurement in-
            terval
                   T=frCircuitExcessBurst/ifSpeed.";
          reference
           "Draft American National  Standard  T1.617-1991,
            Section 6.5.19";
          smiv2:defval "0";
          smiv2:max-access "read-write";
          smiv2:oid "1.3.6.1.2.1.10.32.2.1.14";
        }
      }
    }

    container frErrTable {
      description
       "A table containing information about Errors on the
        Frame Relay interface.";
      smiv2:oid "1.3.6.1.2.1.10.32.3";

      list frErrEntry {
        key "frErrIfIndex";
        description
         "The error information for a single frame relay
          interface.";
        smiv2:oid "1.3.6.1.2.1.10.32.3.1";

        leaf frErrIfIndex {
          type RFC1315-MIB:Index;
          description
           "The ifIndex Value of the  corresponding  ifEn-
            try.";
          smiv2:max-access "read-only";
          smiv2:oid "1.3.6.1.2.1.10.32.3.1.1";
        }

        leaf frErrType {
          type enumeration {
            enum "unknownError" {
              value "1";
            }
            enum "receiveShort" {
              value "2";
            }
            enum "receiveLong" {
              value "3";
            }
            enum "illegalDLCI" {
              value "4";
            }
            enum "unknownDLCI" {
              value "5";
            }
            enum "dlcmiProtoErr" {
              value "6";
            }
            enum "dlcmiUnknownIE" {
              value "7";
            }
            enum "dlcmiSequenceErr" {
              value "8";
            }
            enum "dlcmiUnknownRpt" {
              value "9";
            }
            enum "noErrorSinceReset" {
              value "10";
            }
          }
          description
           "The type of error that was last seen  on  this
            interface.";
          smiv2:max-access "read-only";
          smiv2:oid "1.3.6.1.2.1.10.32.3.1.2";
        }

        leaf frErrData {
          type binary;
          description
           "An octet string containing as much of the  er-
            ror  packet as possible.  As a minimum, it must
            contain the Q.922 Address or  as  much  as  was
            delivered.   It is desirable to include all in-
            formation up to the PDU.";
          smiv2:max-access "read-only";
          smiv2:oid "1.3.6.1.2.1.10.32.3.1.3";
        }

        leaf frErrTime {
          type yang:timeticks;
          description
           "The value of sysUpTime at which the error  was
            detected.";
          smiv2:max-access "read-only";
          smiv2:oid "1.3.6.1.2.1.10.32.3.1.4";
        }
      }
    }
  }

  notification frDLCIStatusChange {
    description
     "This trap indicates that the indicated Virtual
      Circuit  has changed state.  It has either been
      created or invalidated, or has toggled  between
      the active and inactive states.";
    smiv2:oid "1.3.6.1.2.1.10.32.0.1";

    container object-1 {

      leaf frCircuitDlci {
        type leafref {
          path "/RFC1315-MIB:RFC1315-MIB/RFC1315-MIB:frCircuitTable/RFC1315-MIB:frCircuitEntry/RFC1315-MIB:frCircuitDlci";
        }
      }

      leaf frCircuitIfIndex {
        type leafref {
          path "/RFC1315-MIB:RFC1315-MIB/RFC1315-MIB:frCircuitTable/RFC1315-MIB:frCircuitEntry/RFC1315-MIB:frCircuitIfIndex";
        }
      }
    }

    container object-2 {

      leaf frCircuitIfIndex {
        type leafref {
          path "/RFC1315-MIB:RFC1315-MIB/RFC1315-MIB:frCircuitTable/RFC1315-MIB:frCircuitEntry/RFC1315-MIB:frCircuitIfIndex";
        }
      }

      leaf frCircuitDlci {
        type leafref {
          path "/RFC1315-MIB:RFC1315-MIB/RFC1315-MIB:frCircuitTable/RFC1315-MIB:frCircuitEntry/RFC1315-MIB:frCircuitDlci";
        }
      }
    }

    container object-3 {

      leaf frCircuitIfIndex {
        type leafref {
          path "/RFC1315-MIB:RFC1315-MIB/RFC1315-MIB:frCircuitTable/RFC1315-MIB:frCircuitEntry/RFC1315-MIB:frCircuitIfIndex";
        }
      }

      leaf frCircuitDlci {
        type leafref {
          path "/RFC1315-MIB:RFC1315-MIB/RFC1315-MIB:frCircuitTable/RFC1315-MIB:frCircuitEntry/RFC1315-MIB:frCircuitDlci";
        }
      }

      leaf frCircuitState {
        type leafref {
          path "/RFC1315-MIB:RFC1315-MIB/RFC1315-MIB:frCircuitTable/RFC1315-MIB:frCircuitEntry/RFC1315-MIB:frCircuitState";
        }
      }
    }
  }

  smiv2:alias "frame-relay" {
    smiv2:oid "1.3.6.1.2.1.10.32";
  }

  smiv2:alias "frame-relay-globals" {
    smiv2:oid "1.3.6.1.2.1.10.32.4";
  }

}
