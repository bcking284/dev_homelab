/*
 * Generated by confdc --mib2yang-std
 * Source: mgmt/dmi/model/mib/src/CISCO-UBE-MIB.mib
 */
/*
 * This YANG module has been generated by smidump 0.5.0:
 *
 *      smidump -f yang CISCO-UBE-MIB
 *
 * Do not edit. Edit the source file instead!
 */

module CISCO-UBE-MIB {

  namespace "urn:ietf:params:xml:ns:yang:smiv2:CISCO-UBE-MIB";
  prefix CISCO-UBE-MIB;

  import SNMP-FRAMEWORK-MIB {
    prefix "snmp-framework";
  }

  import ietf-yang-smiv2 {
    prefix "smiv2";
  }

  organization
   "Cisco Systems, Inc.";

  contact
   "Cisco Systems
    Customer Service
    
    
    Postal: 170 W Tasman Drive
    
    San Jose, CA  95134
    
    USA
    
    
    Tel: +1 800 553-NETS
    
    
    E-mail: cs-cube@cisco.com";

  description
   "This MIB describes objects used for managing Cisco
    Unified Border Element (CUBE).
    
    The Cisco Unified Border Element (CUBE) is a Cisco 
    IOS Session Border Controller (SBC) that interconnects
    independent voice over IP (VoIP) and video over IP 
    networks for data, voice, and video transport";

  revision 2010-11-29 {
    description
     "Initial version of this MIB module.";
  }


  container CISCO-UBE-MIB {
    config false;

    container ciscoUbeMIBObjects {
      smiv2:oid "1.3.6.1.4.1.9.9.764.0";

      leaf cubeEnabled {
        type boolean;
        description
         "This object represents, whether the Cisco
          Unified Border Element (CUBE) is enabled 
          on the device or not.
          
          The value 'true' means that the CUBE feature 
          is enabled on the device.
          
          The value 'false' means that the CUBE feature 
          is disabled.";
        smiv2:max-access "read-write";
        smiv2:oid "1.3.6.1.4.1.9.9.764.0.1";
      }

      leaf cubeVersion {
        type snmp-framework:SnmpAdminString;
        description
         "This object represents the version of Cisco
          Unified Border Element on the device.";
        smiv2:max-access "read-only";
        smiv2:oid "1.3.6.1.4.1.9.9.764.0.2";
      }

      leaf cubeTotalSessionAllowed {
        type uint32 {
          range "0..999999";
        }
        units "session";
        description
         "This object provides the total number of CUBE
          session allowed on the device. The value zero 
          means no sessions are allowed with CUBE.";
        smiv2:max-access "read-write";
        smiv2:oid "1.3.6.1.4.1.9.9.764.0.3";
      }
    }
  }

  smiv2:alias "ciscoUbeMIB" {
    smiv2:oid "1.3.6.1.4.1.9.9.764";
  }

  smiv2:alias "ciscoUbeMIBObjects" {
    smiv2:oid "1.3.6.1.4.1.9.9.764.0";
  }

  smiv2:alias "ciscoUbeMIBConform" {
    smiv2:oid "1.3.6.1.4.1.9.9.764.1";
  }

  smiv2:alias "ciscoUbeMIBCompliances" {
    smiv2:oid "1.3.6.1.4.1.9.9.764.1.1";
  }

  smiv2:alias "ciscoUbeMIBGroups" {
    smiv2:oid "1.3.6.1.4.1.9.9.764.1.2";
  }

}
