/*
 * Generated by confdc --mib2yang-std
 * Source: mgmt/dmi/model/mib/src/CISCO-IETF-PW-MPLS-MIB.mib
 */
/*
 * This YANG module has been generated by smidump 0.5.0:
 *
 *      smidump -f yang CISCO-IETF-PW-MPLS-MIB
 *
 * Do not edit. Edit the source file instead!
 */

module CISCO-IETF-PW-MPLS-MIB {

  namespace "urn:ietf:params:xml:ns:yang:smiv2:CISCO-IETF-PW-MPLS-MIB";
  prefix CISCO-IETF-PW-MPLS-MIB;

  import CISCO-IETF-PW-MIB {
    prefix "cisco-ietf-pw";
  }

  import CISCO-IETF-PW-TC-MIB {
    prefix "cisco-ietf";
  }

  import IF-MIB {
    prefix "if-mib";
  }

  import MPLS-TC-STD-MIB {
    prefix "mpls-tc";
  }

  import SNMPv2-TC {
    prefix "snmpv2-tc";
  }

  import ietf-yang-smiv2 {
    prefix "smiv2";
  }

  organization
   "Cisco Systems, Inc.";

  contact
   " 
    Thomas D. Nadeau 
    Postal: Cisco Systems, Inc. 
            250 Apollo Drive 
            Chelmsford, MA 01824 
    Tel:    +1-978-497-3051 
    Email:  tnadeau@cisco.com 
    
    MPLS MIB Development Team
    Postal: Cisco Systems, Inc.
            250 Apollo Drive
            Chelmsford, MA 01924
    Tel:    +1-978-497-3989
    Email:  ch-mpls-mib-dev@cisco.com";

  description
   "This MIB complements the CISCO-IETF-PW-MIB for PW operation 
    over MPLS. ";

  revision 2003-02-26 {
    description
     "Made Cisco proprietary based on the PW-MPLS-MIB.my file
      extracted from draft-ietf-pwe3-pw-mpls-mib-00.txt";
  }

  revision 2002-06-02 {
    description
     "Draft-ietf-pwe3-pw-mpls-mib-00 version. Changes from  
      previous version: 
      1) Spliting the mapping table into two tables, one for 
         Non TE application and one for TE application. 
      2) Object types alignment with MPLS MIBs. ";
  }

  revision 2002-01-29 {
    description
     "Changes from previous version: 
      1) Add LDP entity association. 
      2) Clarify inbound/outbound directions. 
      3) Simplify indexing of outbound and inbound tables 
         and providing get next variables. ";
  }

  revision 2001-07-11 {
    description
     "draft-zelig-pw-mib-00.txt - initial version";
  }

  revision 2001-07-11 {
    description
     "Changes from previous version: 
      1) Remove Vc instance from table indexing. 
      2) Update descriptions of indexing and protection. 
      3) Remove the need for MPLS-LSR in case of VC only. 
      4) Change pwVcMplsMplsType to BITS in order to enable 
         multiple types of outer tunnel. 
      5) Add ifindex to outer tunnel tables to support vcOnly  
         option. 
      6) change naming of outbound, inbound and mapping tables to  
         reflect addition of VC only port ifindexes. 
      7) Adapt order of items in mapping table to SNMP convention. ";
  }


  container CISCO-IETF-PW-MPLS-MIB {
    config false;

    container cpwVcMplsObjects {
      smiv2:oid "1.3.6.1.4.1.9.10.107.1";

      leaf cpwVcMplsOutboundIndexNext {
        type uint32 {
          range "0..4294967295";
        }
        description
         "This object contains an appropriate value to 
          be used for cpwVcMplsOutboundIndex when creating 
          entries in the cpwVcMplsOutboundTable. The value 
          0 indicates that no unassigned entries are 
          available. To obtain the cpwVcMplsOutboundIndex 
          value for a new entry, the manager issues a 
          management protocol retrieval operation to obtain 
          the current value of this object.  After each 
          retrieval, the agent should modify the value to 
          the next unassigned index, however the agent MUST 
          NOT assume such retrieval will be done for each  
          row created.";
        smiv2:max-access "read-only";
        smiv2:oid "1.3.6.1.4.1.9.10.107.1.2";
      }

      leaf cpwVcMplsInboundIndexNext {
        type uint32 {
          range "0..4294967295";
        }
        description
         "This object contains an appropriate value to 
          be used for cpwVcMplsInboundIndex when creating 
          entries in the cpwVcMplsInboundTable. The value 
          0 indicates that no unassigned entries are 
          available. To obtain the cpwVcMplsInboundIndex 
          value for a new entry, the manager issues a 
          management protocol retrieval operation to obtain 
          the current value of this object.  After each 
          retrieval, the agent should modify the value to 
          the next unassigned index, however the agent MUST 
          NOT assume such retrieval will be done for each  
          row created.";
        smiv2:max-access "read-only";
        smiv2:oid "1.3.6.1.4.1.9.10.107.1.4";
      }
    }

    container cpwVcMplsTable {
      description
       "This table specifies information for VC to be carried over  
        MPLS PSN.";
      smiv2:oid "1.3.6.1.4.1.9.10.107.1.1";

      list cpwVcMplsEntry {
        key "cpwVcIndex";
        description
         "A row in this table represents parameters specific to MPLS  
          PSN for a pseudo wire connection (VC). The row is created  
          automatically by the local agent if the cpwVcPsnType is  
          MPLS. It is indexed by cpwVcIndex, which uniquely  
          identifying a singular connection. ";
        smiv2:oid "1.3.6.1.4.1.9.10.107.1.1.1";

        leaf cpwVcIndex {
          type leafref {
            path "/cisco-ietf-pw:CISCO-IETF-PW-MIB/cisco-ietf-pw:cpwVcTable/cisco-ietf-pw:cpwVcEntry/cisco-ietf-pw:cpwVcIndex";
          }
        }

        leaf cpwVcMplsMplsType {
          type bits {
            bit mplsTe {
              position "0";
            }
            bit mplsNonTe {
              position "1";
            }
            bit vcOnly {
              position "2";
            }
          }
          description
           "Set by the operator to indicate the outer tunnel types, if 
            exists. mplsTe is used if the outer tunnel was set-up by  
            MPLS-TE, and mplsNonTe is used the outer tunnel was set up 
            by LDP or manually. Combination of mplsTe and mplsNonTe  
            may exist in case of outer tunnel protection. 
            vcOnly is used if there is no outer tunnel label. vcOnly  
            cannot be combined with mplsNonTe or mplsTe.";
          smiv2:max-access "read-write";
          smiv2:oid "1.3.6.1.4.1.9.10.107.1.1.1.1";
        }

        leaf cpwVcMplsExpBitsMode {
          type enumeration {
            enum "outerTunnel" {
              value "1";
            }
            enum "specifiedValue" {
              value "2";
            }
            enum "serviceDependant" {
              value "3";
            }
          }
          description
           "Set by the operator to indicate the way the VC shim label 
            EXP bits are to be determined. The value of outerTunnel(1) 
            is used where there is an outer tunnel - cpwVcMplsMplsType  
            is mplsTe or mplsNonTe. Note that in this case there is no 
            need to mark the VC label with the EXP bits since the VC  
            label is not visible to the intermediate nodes. 
            If there is no outer tunnel, specifiedValue(2) indicate  
            that the value is specified by cpwVcMplsExpBits, and  
            serviceDependant(3) indicate that the EXP bits are setup  
            based on a rule specified in the emulated service specific  
            tables, for example when the EXP bits are a function of  
            802.1p marking for Ethernet emulated service.";
          reference
           "martini et al, <draft-martini-l2circuit-encap-mpls.txt>";
          smiv2:defval "outerTunnel";
          smiv2:max-access "read-write";
          smiv2:oid "1.3.6.1.4.1.9.10.107.1.1.1.2";
        }

        leaf cpwVcMplsExpBits {
          type uint32 {
            range "0..7";
          }
          description
           "Set by the operator to indicate the MPLS EXP bits to be  
            used on the VC shim label if cpwVcMplsExpBitsMode is   
            specifiedValue(2), zero otherwise.";
          smiv2:defval "0";
          smiv2:max-access "read-write";
          smiv2:oid "1.3.6.1.4.1.9.10.107.1.1.1.3";
        }

        leaf cpwVcMplsTtl {
          type uint32 {
            range "0..255";
          }
          description
           "Set by the operator to indicate the VC TTL bits to be used 
            on the VC shim label.";
          reference
           "martini et al, <draft-martini-l2circuit-encap-mpls> ";
          smiv2:defval "2";
          smiv2:max-access "read-write";
          smiv2:oid "1.3.6.1.4.1.9.10.107.1.1.1.4";
        }

        leaf cpwVcMplsLocalLdpID {
          type mpls-tc:MplsLdpIdentifier;
          description
           "The local LDP identifier of the LDP entity creating 
            this VC in the local node. As the VC labels are always 
            set from the per platform label space, the last two octets  
            in the LDP ID MUST be always both zeros.";
          reference
           "<draft-ietf-ldp-mib>, 
            <draft-martini-l2circuit-encap-mpls>. ";
          smiv2:max-access "read-write";
          smiv2:oid "1.3.6.1.4.1.9.10.107.1.1.1.5";
        }

        leaf cpwVcMplsLocalLdpEntityID {
          type uint32;
          description
           "The local LDP Entity index of the LDP entity to be used  
            for this VC on the local node. Should be set to all zeros  
            if not used.";
          reference
           "<draft-ietf-ldp-mib> ";
          smiv2:max-access "read-write";
          smiv2:oid "1.3.6.1.4.1.9.10.107.1.1.1.6";
        }

        leaf cpwVcMplsPeerLdpID {
          type mpls-tc:MplsLdpIdentifier;
          description
           "The peer LDP identifier as identified from the LDP  
            session. Should be zero if not relevant or not known yet.";
          reference
           "<draft-ietf-ldp-mib>, 
            <draft-martini-l2circuit-encap-mpls>. ";
          smiv2:max-access "read-only";
          smiv2:oid "1.3.6.1.4.1.9.10.107.1.1.1.7";
        }

        leaf cpwVcMplsStorageType {
          type snmpv2-tc:StorageType;
          description
           "This variable indicates the storage type for this row.";
          smiv2:max-access "read-write";
          smiv2:oid "1.3.6.1.4.1.9.10.107.1.1.1.8";
        }
      }
    }

    container cpwVcMplsOutboundTable {
      description
       "This table associates VCs using MPLS PSN with the outbound 
        MPLS tunnels (i.e. toward the PSN) or the physical  
        interface in case of VC only.";
      smiv2:oid "1.3.6.1.4.1.9.10.107.1.3";

      list cpwVcMplsOutboundEntry {
        key "cpwVcIndex cpwVcMplsOutboundIndex";
        description
         "A row in this table represents a link between PW VC (that 
          require MPLS tunnels) and MPLS tunnel toward the PSN. 
          In the case of VC only, it associate the VC with the  
          interface that shall carry the VC. 
          This table is indexed by the pwVcIndex and an additional 
          index enabling multiple rows for the same VC index. 
          
          At least one entry is created in this table by the operator  
          for each PW VC that requires MPLS PSN. Note that the first 
          entry for each VC can be indexed by cpwVcMplsOutboundIndex  
          equal zero without a need for retrieval of  
          cpwVcMplsOutboundIndexNext. 
          
          This table points to the appropriate MPLS MIB. In the case  
          of MPLS-TE, the 4 variables relevant to the indexing of  
          a TE MPLS tunnel are set as in Srinivasan, et al, <draft- 
          ietf-mpls-te-mib>. 
          In case of Non-TE MPLS (an outer tunnel label assigned by  
          LDP or manually) the table points to the XC entry in the  
          LSR MIB as in Srinivasan, et al, <draft-ietf-mpls-lsr-mib>. 
          In case of VC only (no outer tunnel) the ifIndex of the 
          port to carry the VC is configured.  
          
          Each VC may have multiple rows in this tables if protection  
          is available at the outer tunnel level, each row may be of 
          different type except for VC only, on which only rows with 
          ifIndex of the port are allowed. ";
        smiv2:oid "1.3.6.1.4.1.9.10.107.1.3.1";

        leaf cpwVcIndex {
          type leafref {
            path "/cisco-ietf-pw:CISCO-IETF-PW-MIB/cisco-ietf-pw:cpwVcTable/cisco-ietf-pw:cpwVcEntry/cisco-ietf-pw:cpwVcIndex";
          }
        }

        leaf cpwVcMplsOutboundIndex {
          type uint32 {
            range "0..4294967295";
          }
          description
           "Arbitrary index for enabling multiple rows per VC in 
            this table. Next available free index can be retrieved  
            using cpwVcMplsOutboundIndexNext. ";
          smiv2:max-access "not-accessible";
          smiv2:oid "1.3.6.1.4.1.9.10.107.1.3.1.1";
        }

        leaf cpwVcMplsOutboundLsrXcIndex {
          type uint32;
          description
           "This object will be set by the operator. If the outer 
            label is defined in the MPL-LSR-MIB, i.e. set by LDP 
            or manually, this object points to the XC index  
            of the outer tunnel. Otherwise, it is set to zero.";
          smiv2:max-access "read-write";
          smiv2:oid "1.3.6.1.4.1.9.10.107.1.3.1.2";
        }

        leaf cpwVcMplsOutboundTunnelIndex {
          type mpls-tc:MplsTunnelIndex;
          description
           "Part of set of indexes for outbound tunnel in the case of  
            MPLS-TE outer tunnel, otherwise set to zero.";
          smiv2:max-access "read-write";
          smiv2:oid "1.3.6.1.4.1.9.10.107.1.3.1.3";
        }

        leaf cpwVcMplsOutboundTunnelInstance {
          type mpls-tc:MplsTunnelInstanceIndex;
          description
           "Part of set of indexes for outbound tunnel in the case of  
            MPLS-TE outer tunnel, otherwise set to zero.";
          smiv2:max-access "read-write";
          smiv2:oid "1.3.6.1.4.1.9.10.107.1.3.1.4";
        }

        leaf cpwVcMplsOutboundTunnelLclLSR {
          type mpls-tc:MplsLsrIdentifier;
          description
           "Part of set of indexes for outbound tunnel in the case of  
            MPLS-TE outer tunnel, otherwise set to zero.";
          smiv2:max-access "read-write";
          smiv2:oid "1.3.6.1.4.1.9.10.107.1.3.1.5";
        }

        leaf cpwVcMplsOutboundTunnelPeerLSR {
          type mpls-tc:MplsLsrIdentifier;
          description
           "Part of set of indexes for outbound tunnel in the case of  
            MPLS-TE outer tunnel, otherwise set to zero.";
          smiv2:max-access "read-write";
          smiv2:oid "1.3.6.1.4.1.9.10.107.1.3.1.6";
        }

        leaf cpwVcMplsOutboundIfIndex {
          type if-mib:InterfaceIndexOrZero;
          description
           "In case of VC only (no outer tunnel), this object holds 
            the ifIndex of the outbound port, otherwise set to zero.";
          smiv2:max-access "read-write";
          smiv2:oid "1.3.6.1.4.1.9.10.107.1.3.1.7";
        }

        leaf cpwVcMplsOutboundRowStatus {
          type snmpv2-tc:RowStatus;
          description
           "For creating, modifying, and deleting this row.";
          smiv2:max-access "read-write";
          smiv2:oid "1.3.6.1.4.1.9.10.107.1.3.1.8";
        }

        leaf cpwVcMplsOutboundStorageType {
          type snmpv2-tc:StorageType;
          description
           "This variable indicates the storage type for this object.";
          smiv2:max-access "read-write";
          smiv2:oid "1.3.6.1.4.1.9.10.107.1.3.1.9";
        }
      }
    }

    container cpwVcMplsInboundTable {
      description
       "This table associates VCs using MPLS PSN with the inbound 
        MPLS tunnels (i.e. for packets coming from the PSN),  
        if such association is desired (mainly for security  
        reasons).";
      smiv2:oid "1.3.6.1.4.1.9.10.107.1.5";

      list cpwVcMplsInboundEntry {
        key "cpwVcIndex cpwVcMplsInboundIndex";
        description
         "A row in this table represents a link between PW VCs (that 
          require MPLS tunnels) and MPLS tunnel for packets arriving 
          from the PSN. 
          This table is indexed by the set of indexes used to 
          identify the VC - cpwVcIndex and an additional 
          index enabling multiple rows for the same VC index. 
          
          Note that the first entry for each VC can be indexed by  
          cpwVcMplsOutboundIndex equal zero without a need for  
          retrieval of cpwVcMplsInboundIndexNext. 
          
          An entry is created in this table either automatically by  
          the local agent or created manually by the operator in  
          cases that strict mode is required. 
          
          Note that the control messages contain VC ID and VC type,  
          which together with the remote IP address identify the 
          cpwVcIndex in the local node. 
          This table points to the appropriate MPLS MIB. In the case  
          of MPLS-TE, the 4 variables relevant to the indexing of a 
          TE MPLS tunnel are set as in Srinivasan, et al, <draft- 
          ietf-mpls-te-mib>. 
          
          In case of non-TE MPLS tunnel (an outer tunnel label  
          assigned by LDP or manually) the table points to the XC  
          entry in the MPLS-LSR-MIB as in Srinivasan, et al, <draft- 
          ietf-mpls-lsr-mib>. 
          
          Each VC may have multiple rows in this tables if protection  
          is available at the outer tunnel level, each row may be of 
          different type except for VC only, on which only rows with 
          ifIndex of the port are allowed. ";
        smiv2:oid "1.3.6.1.4.1.9.10.107.1.5.1";

        leaf cpwVcIndex {
          type leafref {
            path "/cisco-ietf-pw:CISCO-IETF-PW-MIB/cisco-ietf-pw:cpwVcTable/cisco-ietf-pw:cpwVcEntry/cisco-ietf-pw:cpwVcIndex";
          }
        }

        leaf cpwVcMplsInboundIndex {
          type uint32 {
            range "0..4294967295";
          }
          description
           "Arbitrary index for enabling multiple rows per VC in 
            this table. Next available free index can be retrieved 
            using cpwVcMplsInboundIndexNext. ";
          smiv2:max-access "not-accessible";
          smiv2:oid "1.3.6.1.4.1.9.10.107.1.5.1.1";
        }

        leaf cpwVcMplsInboundLsrXcIndex {
          type uint32;
          description
           "If the outer label is defined in the MPL-LSR-MIB, i.e. set  
            by LDP or manually, this object points to the XC index  
            of the outer tunnel. Otherwise, it is set to zero.";
          smiv2:max-access "read-write";
          smiv2:oid "1.3.6.1.4.1.9.10.107.1.5.1.2";
        }

        leaf cpwVcMplsInboundTunnelIndex {
          type mpls-tc:MplsTunnelIndex;
          description
           "Part of set of indexes for outbound tunnel in the case of  
            MPLS-TE outer tunnel, otherwise set to zero.";
          smiv2:max-access "read-write";
          smiv2:oid "1.3.6.1.4.1.9.10.107.1.5.1.3";
        }

        leaf cpwVcMplsInboundTunnelInstance {
          type mpls-tc:MplsTunnelInstanceIndex;
          description
           "Part of set of indexes for outbound tunnel in the case of  
            MPLS-TE outer tunnel, otherwise set to zero.";
          smiv2:max-access "read-write";
          smiv2:oid "1.3.6.1.4.1.9.10.107.1.5.1.4";
        }

        leaf cpwVcMplsInboundTunnelLclLSR {
          type mpls-tc:MplsLsrIdentifier;
          description
           "Part of set of indexes for outbound tunnel in the case of  
            MPLS-TE outer tunnel, otherwise set to zero.";
          smiv2:max-access "read-write";
          smiv2:oid "1.3.6.1.4.1.9.10.107.1.5.1.5";
        }

        leaf cpwVcMplsInboundTunnelPeerLSR {
          type mpls-tc:MplsLsrIdentifier;
          description
           "Part of set of indexes for outbound tunnel in the case of  
            MPLS-TE outer tunnel, otherwise set to zero.";
          smiv2:max-access "read-write";
          smiv2:oid "1.3.6.1.4.1.9.10.107.1.5.1.6";
        }

        leaf cpwVcMplsInboundIfIndex {
          type if-mib:InterfaceIndexOrZero;
          description
           "In case of VC only (no outer tunnel), this object holds the 
            ifIndex of the inbound port, otherwise set to zero.";
          smiv2:max-access "read-write";
          smiv2:oid "1.3.6.1.4.1.9.10.107.1.5.1.7";
        }

        leaf cpwVcMplsInboundRowStatus {
          type snmpv2-tc:RowStatus;
          description
           "For creating, modifying, and deleting this row.";
          smiv2:max-access "read-write";
          smiv2:oid "1.3.6.1.4.1.9.10.107.1.5.1.8";
        }

        leaf cpwVcMplsInboundStorageType {
          type snmpv2-tc:StorageType;
          description
           "This variable indicates the storage type for this row.";
          smiv2:max-access "read-write";
          smiv2:oid "1.3.6.1.4.1.9.10.107.1.5.1.9";
        }
      }
    }

    container cpwVcMplsNonTeMappingTable {
      description
       "This table maps an inbound/outbound Tunnel to a VC in non- 
        TE applications.";
      smiv2:oid "1.3.6.1.4.1.9.10.107.1.6";

      list cpwVcMplsNonTeMappingEntry {
        key "cpwVcMplsNonTeMappingTunnelDirection cpwVcMplsNonTeMappingXcTunnelIndex cpwVcMplsNonTeMappingIfIndex cpwVcMplsNonTeMappingVcIndex";
        description
         "A row in this table represents the association 
          between the PW VC and it's non TE MPLS outer Tunnel 
          it's physical interface if there is no outer tunnel  
          (VC only). 
          
          An application can use this table to quickly retrieve the  
          PW carried over specific non-TE MPLS outer tunnel or  
          physical interface. 
          
          The table in indexed by the XC index for MPLS Non-TE  
          tunnel, or ifIndex of the port in VC only case, the  
          direction of the VC in the specific entry and the VCIndex. 
          
          The same table is used in both inbound and outbound 
          directions, but in a different row for each direction. If  
          the inbound association is not known, no rows should exist  
          for it. 
          
          Rows are created by the local agent when all the  
          association data is available for display.";
        smiv2:oid "1.3.6.1.4.1.9.10.107.1.6.1";

        leaf cpwVcMplsNonTeMappingTunnelDirection {
          type enumeration {
            enum "outbound" {
              value "1";
            }
            enum "inbound" {
              value "2";
            }
          }
          description
           "Identifies if the row represent an outbound or inbound  
            mapping.";
          smiv2:max-access "not-accessible";
          smiv2:oid "1.3.6.1.4.1.9.10.107.1.6.1.1";
        }

        leaf cpwVcMplsNonTeMappingXcTunnelIndex {
          type uint32 {
            range "0..4294967295";
          }
          description
           "Index for the conceptual XC row identifying Tunnel to VC  
            mappings when the outer tunnel is created by the MPLS-LSR- 
            MIB, Zero otherwise.";
          smiv2:max-access "not-accessible";
          smiv2:oid "1.3.6.1.4.1.9.10.107.1.6.1.2";
        }

        leaf cpwVcMplsNonTeMappingIfIndex {
          type if-mib:InterfaceIndexOrZero;
          description
           "Identify the port on which the VC is carried for VC only  
            case.";
          smiv2:max-access "not-accessible";
          smiv2:oid "1.3.6.1.4.1.9.10.107.1.6.1.3";
        }

        leaf cpwVcMplsNonTeMappingVcIndex {
          type cisco-ietf:CpwVcIndexType;
          description
           "The value that represent the VC in the cpwVcTable.";
          smiv2:max-access "read-only";
          smiv2:oid "1.3.6.1.4.1.9.10.107.1.6.1.4";
        }
      }
    }

    container cpwVcMplsTeMappingTable {
      description
       "This table maps an inbound/outbound Tunnel to a VC in  
        MPLS-TE applications.";
      smiv2:oid "1.3.6.1.4.1.9.10.107.1.7";

      list cpwVcMplsTeMappingEntry {
        key "cpwVcMplsTeMappingTunnelDirection cpwVcMplsTeMappingTunnelIndex cpwVcMplsTeMappingTunnelInstance cpwVcMplsTeMappingTunnelPeerLsrID cpwVcMplsTeMappingTunnelLocalLsrID cpwVcMplsTeMappingVcIndex";
        description
         "A row in this table represents the association 
          between a PW VC and it's MPLS-TE outer Tunnel. 
          
          An application can use this table to quickly retrieve the  
          PW carried over specific TE MPLS outer tunnel. 
          
          The table in indexed by the 4 indexes of a TE tunnel, 
          the direction of the VC specific entry and the VcIndex. 
          
          The same table is used in both inbound and outbound 
          directions, a different row for each direction. If the  
          inbound association is not known, no rows should exist for  
          it. 
          
          Rows are created by the local agent when all the  
          association data is available for display.";
        smiv2:oid "1.3.6.1.4.1.9.10.107.1.7.1";

        leaf cpwVcMplsTeMappingTunnelDirection {
          type enumeration {
            enum "outbound" {
              value "1";
            }
            enum "inbound" {
              value "2";
            }
          }
          description
           "Identifies if the row represent an outbound or inbound  
            mapping.";
          smiv2:max-access "not-accessible";
          smiv2:oid "1.3.6.1.4.1.9.10.107.1.7.1.1";
        }

        leaf cpwVcMplsTeMappingTunnelIndex {
          type mpls-tc:MplsTunnelIndex;
          description
           "Primary index for the conceptual row identifying the  
            MPLS-TE tunnel.";
          smiv2:max-access "not-accessible";
          smiv2:oid "1.3.6.1.4.1.9.10.107.1.7.1.2";
        }

        leaf cpwVcMplsTeMappingTunnelInstance {
          type mpls-tc:MplsTunnelInstanceIndex;
          description
           "Identifies an instance of the MPLS-TE tunnel.";
          smiv2:max-access "not-accessible";
          smiv2:oid "1.3.6.1.4.1.9.10.107.1.7.1.3";
        }

        leaf cpwVcMplsTeMappingTunnelPeerLsrID {
          type mpls-tc:MplsLsrIdentifier;
          description
           "Identifies an Peer LSR when the outer tunnel is MPLS-TE  
            based.";
          smiv2:max-access "not-accessible";
          smiv2:oid "1.3.6.1.4.1.9.10.107.1.7.1.4";
        }

        leaf cpwVcMplsTeMappingTunnelLocalLsrID {
          type mpls-tc:MplsLsrIdentifier;
          description
           "Identifies the local LSR.";
          smiv2:max-access "not-accessible";
          smiv2:oid "1.3.6.1.4.1.9.10.107.1.7.1.5";
        }

        leaf cpwVcMplsTeMappingVcIndex {
          type cisco-ietf:CpwVcIndexType;
          description
           "The value that represent the VC in the cpwVcTable.";
          smiv2:max-access "read-only";
          smiv2:oid "1.3.6.1.4.1.9.10.107.1.7.1.6";
        }
      }
    }
  }

  smiv2:alias "cpwVcMplsMIB" {
    smiv2:oid "1.3.6.1.4.1.9.10.107";
  }

  smiv2:alias "cpwVcMplsNotifications" {
    smiv2:oid "1.3.6.1.4.1.9.10.107.0";
  }

  smiv2:alias "cpwVcMplsNotifyPrefix" {
    smiv2:oid "1.3.6.1.4.1.9.10.107.0.0";
  }

  smiv2:alias "cpwVcMplsObjects" {
    smiv2:oid "1.3.6.1.4.1.9.10.107.1";
  }

  smiv2:alias "cpwVcMplsConformance" {
    smiv2:oid "1.3.6.1.4.1.9.10.107.2";
  }

  smiv2:alias "cpwVcMplsGroups" {
    smiv2:oid "1.3.6.1.4.1.9.10.107.2.1";
  }

  smiv2:alias "cpwVcMplsCompliances" {
    smiv2:oid "1.3.6.1.4.1.9.10.107.2.2";
  }

}
