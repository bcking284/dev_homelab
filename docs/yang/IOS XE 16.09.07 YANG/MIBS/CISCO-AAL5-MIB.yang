/*
 * Generated by confdc --mib2yang-std
 * Source: mgmt/dmi/model/mib/src/CISCO-AAL5-MIB.mib
 */
/*
 * This YANG module has been generated by smidump 0.5.0:
 *
 *      smidump -f yang CISCO-AAL5-MIB
 *
 * Do not edit. Edit the source file instead!
 */

module CISCO-AAL5-MIB {

  namespace "urn:ietf:params:xml:ns:yang:smiv2:CISCO-AAL5-MIB";
  prefix CISCO-AAL5-MIB;

  import ATM-MIB {
    prefix "atm-mib";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-atm@cisco.com";

  description
   "Cisco Enterprise AAL5 MIB file that provide AAL5
    specific information that are either excluded by 
        RFC 1695 or specific to Cisco product.";

  revision 2003-09-22 {
    description
     "Added following objects in cAal5VccTable: 
      cAal5VccHCInPkts,
      cAal5VccHCOutPkts,
      cAal5VccHCInOctets, 
      cAal5VccHCOutOctets";
  }

  revision 2002-10-17 {
    description
     "Latest version of this MIB module with extended support
      for vc drop stats.";
  }

  revision 1996-11-15 {
    description
     "Initial version of this MIB module.";
  }

  smiv2:alias "cAal5VccTable" {
    description
     "This table contains AAL5 VCC performance 
      parameters beyond that provided by aal5VccEntry
      defined in RFC1695.";
    smiv2:oid "1.3.6.1.4.1.9.9.66.1.1.1";
  }

  smiv2:alias "cAal5VccEntry" {
    description
     "This list contains the additional AAL5 VCC performance 
      parameters beyond that provided by aal5VccEntry defined
      in RFC1695.";
    smiv2:oid "1.3.6.1.4.1.9.9.66.1.1.1.1";
  }

  augment "/atm-mib:ATM-MIB/atm-mib:aal5VccTable/atm-mib:aal5VccEntry" {
    description
     "This list contains the additional AAL5 VCC performance 
      parameters beyond that provided by aal5VccEntry defined
      in RFC1695.";
    smiv2:oid "1.3.6.1.4.1.9.9.66.1.1.1.1";

    leaf cAal5VccInPkts {
      type yang:counter32;
      units "packets";
      description
       "The number of AAL5 CPCS PDUs received on this AAL5 VCC at the
        interface associated with an AAL5 entity.";
      smiv2:max-access "read-only";
      smiv2:oid "1.3.6.1.4.1.9.9.66.1.1.1.1.1";
    }

    leaf cAal5VccOutPkts {
      type yang:counter32;
      units "packets";
      description
       "The number of AAL5 CPCS PDUs transmitted on this AAL5 VCC at
        the interface associated with an AAL5 entity.";
      smiv2:max-access "read-only";
      smiv2:oid "1.3.6.1.4.1.9.9.66.1.1.1.1.2";
    }

    leaf cAal5VccInOctets {
      type yang:counter32;
      units "octets";
      description
       "The number of AAL5 CPCS PDU octets received on this AAL5 VCC
        at the interface associated with an AAL5 entity.";
      smiv2:max-access "read-only";
      smiv2:oid "1.3.6.1.4.1.9.9.66.1.1.1.1.3";
    }

    leaf cAal5VccOutOctets {
      type yang:counter32;
      units "octets";
      description
       "The number of AAL5 CPCS PDU octets transmitted on this AAL5 
        VCC at the interface associated with an AAL5 entity.";
      smiv2:max-access "read-only";
      smiv2:oid "1.3.6.1.4.1.9.9.66.1.1.1.1.4";
    }

    leaf cAal5VccInDroppedPkts {
      type yang:counter32;
      units "packets";
      description
       "The number of AAL5 CPCS PDUs dropped at the 
        receive side of this AAL5 VCC at the interface 
        associated with an AAL5 entity.";
      smiv2:max-access "read-only";
      smiv2:oid "1.3.6.1.4.1.9.9.66.1.1.1.1.5";
    }

    leaf cAal5VccOutDroppedPkts {
      type yang:counter32;
      units "packets";
      description
       "The number of AAL5 CPCS PDUs dropped at the transmit side 
        of this AAL5 VCC at the interface associated with an 
        AAL5 entity.";
      smiv2:max-access "read-only";
      smiv2:oid "1.3.6.1.4.1.9.9.66.1.1.1.1.6";
    }

    leaf cAal5VccInDroppedOctets {
      type yang:counter32;
      units "octets";
      description
       "The number of AAL5 CPCS PDU Octets dropped at the 
        receive side of this AAL5 VCC at the interface 
        associated with an AAL5 entity.";
      smiv2:max-access "read-only";
      smiv2:oid "1.3.6.1.4.1.9.9.66.1.1.1.1.7";
    }

    leaf cAal5VccOutDroppedOctets {
      type yang:counter32;
      units "octets";
      description
       "The number of AAL5 CPCS PDU Octets dropped at the 
        transmit side of this AAL5 VCC at the interface 
        associated with an AAL5 entity.";
      smiv2:max-access "read-only";
      smiv2:oid "1.3.6.1.4.1.9.9.66.1.1.1.1.8";
    }

    leaf cAal5VccHCInPkts {
      type yang:counter64;
      description
       "This is 64bit (High Capacity) version of cAal5VccInPkts 
        counters.";
      smiv2:max-access "read-only";
      smiv2:oid "1.3.6.1.4.1.9.9.66.1.1.1.1.9";
    }

    leaf cAal5VccHCOutPkts {
      type yang:counter64;
      description
       "This is 64bit (High Capacity) version of cAal5VccOutPkts 
        counters.";
      smiv2:max-access "read-only";
      smiv2:oid "1.3.6.1.4.1.9.9.66.1.1.1.1.10";
    }

    leaf cAal5VccHCInOctets {
      type yang:counter64;
      description
       "This is 64bit (High Capacity) version of cAal5VccInOctets 
        counters.";
      smiv2:max-access "read-only";
      smiv2:oid "1.3.6.1.4.1.9.9.66.1.1.1.1.11";
    }

    leaf cAal5VccHCOutOctets {
      type yang:counter64;
      description
       "This is 64bit (High Capacity) version of cAal5VccOutOctets 
        counters.";
      smiv2:max-access "read-only";
      smiv2:oid "1.3.6.1.4.1.9.9.66.1.1.1.1.12";
    }
  }

  smiv2:alias "ciscoAal5MIB" {
    smiv2:oid "1.3.6.1.4.1.9.9.66";
  }

  smiv2:alias "ciscoAal5MIBObjects" {
    smiv2:oid "1.3.6.1.4.1.9.9.66.1";
  }

  smiv2:alias "cAal5Connections" {
    smiv2:oid "1.3.6.1.4.1.9.9.66.1.1";
  }

  smiv2:alias "ciscoAal5MIBConformance" {
    smiv2:oid "1.3.6.1.4.1.9.9.66.3";
  }

  smiv2:alias "ciscoAal5MIBCompliances" {
    smiv2:oid "1.3.6.1.4.1.9.9.66.3.1";
  }

  smiv2:alias "ciscoAal5MIBGroups" {
    smiv2:oid "1.3.6.1.4.1.9.9.66.3.2";
  }

}
