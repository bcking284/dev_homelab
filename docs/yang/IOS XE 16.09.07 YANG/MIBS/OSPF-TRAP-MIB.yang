/*
 * Generated by confdc --mib2yang-std
 * Source: mgmt/dmi/model/mib/src/OSPF-TRAP-MIB.mib
 */
/*
 * This YANG module has been generated by smidump 0.5.0:
 *
 *      smidump -f yang OSPF-TRAP-MIB
 *
 * Do not edit. Edit the source file instead!
 */

module OSPF-TRAP-MIB {

  namespace "urn:ietf:params:xml:ns:yang:smiv2:OSPF-TRAP-MIB";
  prefix OSPF-TRAP-MIB;

  import OSPF-MIB {
    prefix "ospf-mib";
  }

  import ietf-inet-types {
    prefix "inet";
  }

  import ietf-yang-smiv2 {
    prefix "smiv2";
  }

  organization
   "IETF OSPF Working Group";

  contact
   "WG E-Mail: ospf@ietf.org
    
    WG Chairs: acee@cisco.com
               rohit@gmail.com
    
    Editors:   Dan Joyal
               Nortel
               600 Technology Park Drive
               Billerica, MA  01821
               djoyal@nortel.com
    
               Piotr Galecki
               Airvana
               19 Alpha Road
               Chelmsford, MA 01824
               pgalecki@airvana.com
    
               Spencer Giacalone
               CSFB
               Eleven Madison Ave
               New York, NY 10010-3629
    
               spencer.giacalone@gmail.com";

  description
   "The MIB module to describe traps for the OSPF
    Version 2 Protocol.
    
    Copyright (C) The IETF Trust (2006).
    This version of this MIB module is part of
    RFC 4750;  see the RFC itself for full legal
    notices.";

  revision 2006-11-10 {
    description
     "Updated for latest changes to OSPFv2:
      -added graceful restart related traps
      -added new config error types
      -added ospfNssaTranslatorStatusChange trap.
      See Appendix B of RFC 4750 for more details.
      
      This version published as part of RFC 4750";
  }

  revision 1995-01-20 {
    description
     "The initial SMIv2 revision of this MIB module, published
      in RFC 1850.";
  }


  container OSPF-TRAP-MIB {
    config false;

    container ospfTrapControl {
      smiv2:oid "1.3.6.1.2.1.14.16.1";

      leaf ospfSetTrap {
        type binary {
          length "4";
        }
        description
         "A 4-octet string serving as a bit map for
          the trap events defined by the OSPF traps.  This
          object is used to enable and disable specific
          OSPF traps where a 1 in the bit field
          represents enabled.  The right-most bit (least
          significant) represents trap 0.
          
          This object is persistent and when written
          
          the entity SHOULD save the change to non-volatile
          storage.";
        smiv2:max-access "read-write";
        smiv2:oid "1.3.6.1.2.1.14.16.1.1";
      }

      leaf ospfConfigErrorType {
        type enumeration {
          enum "badVersion" {
            value "1";
          }
          enum "areaMismatch" {
            value "2";
          }
          enum "unknownNbmaNbr" {
            value "3";
          }
          enum "unknownVirtualNbr" {
            value "4";
          }
          enum "authTypeMismatch" {
            value "5";
          }
          enum "authFailure" {
            value "6";
          }
          enum "netMaskMismatch" {
            value "7";
          }
          enum "helloIntervalMismatch" {
            value "8";
          }
          enum "deadIntervalMismatch" {
            value "9";
          }
          enum "optionMismatch" {
            value "10";
          }
          enum "mtuMismatch" {
            value "11";
          }
          enum "duplicateRouterId" {
            value "12";
          }
          enum "noError" {
            value "13";
          }
        }
        description
         "Potential types of configuration conflicts.
          Used by the ospfConfigError and
          ospfConfigVirtError traps.  When the last value
          of a trap using this object is needed, but no
          traps of that type have been sent, this value
          pertaining to this object should be returned as
          noError.";
        smiv2:max-access "read-only";
        smiv2:oid "1.3.6.1.2.1.14.16.1.2";
      }

      leaf ospfPacketType {
        type enumeration {
          enum "hello" {
            value "1";
          }
          enum "dbDescript" {
            value "2";
          }
          enum "lsReq" {
            value "3";
          }
          enum "lsUpdate" {
            value "4";
          }
          enum "lsAck" {
            value "5";
          }
          enum "nullPacket" {
            value "6";
          }
        }
        description
         "OSPF packet types.  When the last value of a trap
          using this object is needed, but no traps of
          that type have been sent, this value pertaining
          to this object should be returned as nullPacket.";
        smiv2:max-access "read-only";
        smiv2:oid "1.3.6.1.2.1.14.16.1.3";
      }

      leaf ospfPacketSrc {
        type inet:ipv4-address;
        description
         "The IP address of an inbound packet that cannot
          be identified by a neighbor instance.  When
          the last value of a trap using this object is
          needed, but no traps of that type have been sent,
          this value pertaining to this object should
          be returned as 0.0.0.0.";
        smiv2:max-access "read-only";
        smiv2:oid "1.3.6.1.2.1.14.16.1.4";
      }
    }
  }

  notification ospfVirtIfStateChange {
    description
     "An ospfVirtIfStateChange trap signifies that there
      has been a change in the state of an OSPF virtual
      interface.
      
      This trap should be generated when the interface
      state regresses (e.g., goes from Point-to-Point to Down)
      or progresses to a terminal state
      (i.e., Point-to-Point).";
    smiv2:oid "1.3.6.1.2.1.14.16.2.1";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }

      leaf ospfVirtIfState {
        type leafref {
          path "/ospf-mib:OSPF-MIB/ospf-mib:ospfVirtIfTable/ospf-mib:ospfVirtIfEntry/ospf-mib:ospfVirtIfState";
        }
      }
    }
  }

  notification ospfNbrStateChange {
    description
     "An ospfNbrStateChange trap signifies that
      there has been a change in the state of a
      non-virtual OSPF neighbor.  This trap should be
      generated when the neighbor state regresses
      (e.g., goes from Attempt or Full to 1-Way or
      Down) or progresses to a terminal state (e.g.,
      
      2-Way or Full).  When an neighbor transitions
      from or to Full on non-broadcast multi-access
      and broadcast networks, the trap should be
      generated by the designated router.  A designated
      router transitioning to Down will be noted by
      ospfIfStateChange.";
    smiv2:oid "1.3.6.1.2.1.14.16.2.2";

    container object-1 {

      leaf ospfRouterId {
        type leafref {
          path "/ospf-mib:OSPF-MIB/ospf-mib:ospfGeneralGroup/ospf-mib:ospfRouterId";
        }
      }
    }

    container object-2 {

      leaf ospfNbrAddressLessIndex {
        type leafref {
          path "/ospf-mib:OSPF-MIB/ospf-mib:ospfNbrTable/ospf-mib:ospfNbrEntry/ospf-mib:ospfNbrAddressLessIndex";
        }
      }

      leaf ospfNbrIpAddr {
        type leafref {
          path "/ospf-mib:OSPF-MIB/ospf-mib:ospfNbrTable/ospf-mib:ospfNbrEntry/ospf-mib:ospfNbrIpAddr";
        }
      }
    }

    container object-3 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }
    }

    container object-4 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRtrId {
        type leafref {
          path "/ospf-mib:OSPF-MIB/ospf-mib:ospfNbrTable/ospf-mib:ospfNbrEntry/ospf-mib:ospfNbrRtrId";
        }
      }
    }

    container object-5 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrState {
        type leafref {
          path "/ospf-mib:OSPF-MIB/ospf-mib:ospfNbrTable/ospf-mib:ospfNbrEntry/ospf-mib:ospfNbrState";
        }
      }
    }
  }

  notification ospfVirtNbrStateChange {
    description
     "An ospfVirtNbrStateChange trap signifies that there
      has been a change in the state of an OSPF virtual
      neighbor.  This trap should be generated
      when the neighbor state regresses (e.g., goes
      from Attempt or Full to 1-Way or Down) or
      progresses to a terminal state (e.g., Full).";
    smiv2:oid "1.3.6.1.2.1.14.16.2.3";

    container object-1 {

      leaf ospfRouterId {
        type leafref {
          path "/ospf-mib:OSPF-MIB/ospf-mib:ospfGeneralGroup/ospf-mib:ospfRouterId";
        }
      }
    }

    container object-2 {

      leaf ospfVirtNbrRtrId {
        type leafref {
          path "/ospf-mib:OSPF-MIB/ospf-mib:ospfVirtNbrTable/ospf-mib:ospfVirtNbrEntry/ospf-mib:ospfVirtNbrRtrId";
        }
      }

      leaf ospfVirtNbrArea {
        type leafref {
          path "/ospf-mib:OSPF-MIB/ospf-mib:ospfVirtNbrTable/ospf-mib:ospfVirtNbrEntry/ospf-mib:ospfVirtNbrArea";
        }
      }
    }

    container object-3 {

      leaf ospfVirtNbrArea {
        type leafref {
          path "/ospf-mib:OSPF-MIB/ospf-mib:ospfVirtNbrTable/ospf-mib:ospfVirtNbrEntry/ospf-mib:ospfVirtNbrArea";
        }
      }

      leaf ospfVirtNbrRtrId {
        type leafref {
          path "/ospf-mib:OSPF-MIB/ospf-mib:ospfVirtNbrTable/ospf-mib:ospfVirtNbrEntry/ospf-mib:ospfVirtNbrRtrId";
        }
      }
    }

    container object-4 {

      leaf ospfVirtNbrArea {
        type leafref {
          path "/ospf-mib:OSPF-MIB/ospf-mib:ospfVirtNbrTable/ospf-mib:ospfVirtNbrEntry/ospf-mib:ospfVirtNbrArea";
        }
      }

      leaf ospfVirtNbrRtrId {
        type leafref {
          path "/ospf-mib:OSPF-MIB/ospf-mib:ospfVirtNbrTable/ospf-mib:ospfVirtNbrEntry/ospf-mib:ospfVirtNbrRtrId";
        }
      }

      leaf ospfVirtNbrState {
        type leafref {
          path "/ospf-mib:OSPF-MIB/ospf-mib:ospfVirtNbrTable/ospf-mib:ospfVirtNbrEntry/ospf-mib:ospfVirtNbrState";
        }
      }
    }
  }

  notification ospfIfConfigError {
    description
     "An ospfIfConfigError trap signifies that a
      packet has been received on a non-virtual
      interface from a router whose configuration
      parameters conflict with this router's
      configuration parameters.  Note that the event
      optionMismatch should cause a trap only if it
      prevents an adjacency from forming.";
    smiv2:oid "1.3.6.1.2.1.14.16.2.4";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf ospfPacketSrc {
        type leafref {
          path "/OSPF-TRAP-MIB:OSPF-TRAP-MIB/OSPF-TRAP-MIB:ospfTrapControl/OSPF-TRAP-MIB:ospfPacketSrc";
        }
      }
    }

    container object-5 {

      leaf ospfConfigErrorType {
        type leafref {
          path "/OSPF-TRAP-MIB:OSPF-TRAP-MIB/OSPF-TRAP-MIB:ospfTrapControl/OSPF-TRAP-MIB:ospfConfigErrorType";
        }
      }
    }

    container object-6 {

      leaf ospfPacketType {
        type leafref {
          path "/OSPF-TRAP-MIB:OSPF-TRAP-MIB/OSPF-TRAP-MIB:ospfTrapControl/OSPF-TRAP-MIB:ospfPacketType";
        }
      }
    }
  }

  notification ospfVirtIfConfigError {
    description
     "An ospfVirtIfConfigError trap signifies that a
      packet has been received on a virtual interface
      from a router whose configuration parameters
      conflict with this router's configuration
      parameters.  Note that the event optionMismatch
      should cause a trap only if it prevents an
      adjacency from forming.";
    smiv2:oid "1.3.6.1.2.1.14.16.2.5";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf ospfConfigErrorType {
        type leafref {
          path "/OSPF-TRAP-MIB:OSPF-TRAP-MIB/OSPF-TRAP-MIB:ospfTrapControl/OSPF-TRAP-MIB:ospfConfigErrorType";
        }
      }
    }

    container object-5 {

      leaf ospfPacketType {
        type leafref {
          path "/OSPF-TRAP-MIB:OSPF-TRAP-MIB/OSPF-TRAP-MIB:ospfTrapControl/OSPF-TRAP-MIB:ospfPacketType";
        }
      }
    }
  }

  notification ospfIfAuthFailure {
    description
     "An ospfIfAuthFailure trap signifies that a
      packet has been received on a non-virtual
      interface from a router whose authentication key
      or authentication type conflicts with this
      router's authentication key or authentication
      type.";
    smiv2:oid "1.3.6.1.2.1.14.16.2.6";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf ospfPacketSrc {
        type leafref {
          path "/OSPF-TRAP-MIB:OSPF-TRAP-MIB/OSPF-TRAP-MIB:ospfTrapControl/OSPF-TRAP-MIB:ospfPacketSrc";
        }
      }
    }

    container object-5 {

      leaf ospfConfigErrorType {
        type leafref {
          path "/OSPF-TRAP-MIB:OSPF-TRAP-MIB/OSPF-TRAP-MIB:ospfTrapControl/OSPF-TRAP-MIB:ospfConfigErrorType";
        }
      }
    }

    container object-6 {

      leaf ospfPacketType {
        type leafref {
          path "/OSPF-TRAP-MIB:OSPF-TRAP-MIB/OSPF-TRAP-MIB:ospfTrapControl/OSPF-TRAP-MIB:ospfPacketType";
        }
      }
    }
  }

  notification ospfVirtIfAuthFailure {
    description
     "An ospfVirtIfAuthFailure trap signifies that a
      packet has been received on a virtual interface
      from a router whose authentication key or
      authentication type conflicts with this router's
      authentication key or authentication type.";
    smiv2:oid "1.3.6.1.2.1.14.16.2.7";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf ospfConfigErrorType {
        type leafref {
          path "/OSPF-TRAP-MIB:OSPF-TRAP-MIB/OSPF-TRAP-MIB:ospfTrapControl/OSPF-TRAP-MIB:ospfConfigErrorType";
        }
      }
    }

    container object-5 {

      leaf ospfPacketType {
        type leafref {
          path "/OSPF-TRAP-MIB:OSPF-TRAP-MIB/OSPF-TRAP-MIB:ospfTrapControl/OSPF-TRAP-MIB:ospfPacketType";
        }
      }
    }
  }

  notification ospfIfRxBadPacket {
    description
     "An ospfIfRxBadPacket trap signifies that an
      OSPF packet has been received on a non-virtual
      interface that cannot be parsed.";
    smiv2:oid "1.3.6.1.2.1.14.16.2.8";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf ospfPacketSrc {
        type leafref {
          path "/OSPF-TRAP-MIB:OSPF-TRAP-MIB/OSPF-TRAP-MIB:ospfTrapControl/OSPF-TRAP-MIB:ospfPacketSrc";
        }
      }
    }

    container object-5 {

      leaf ospfPacketType {
        type leafref {
          path "/OSPF-TRAP-MIB:OSPF-TRAP-MIB/OSPF-TRAP-MIB:ospfTrapControl/OSPF-TRAP-MIB:ospfPacketType";
        }
      }
    }
  }

  notification ospfVirtIfRxBadPacket {
    description
     "An ospfVirtIfRxBadPacket trap signifies that an OSPF
      packet has been received on a virtual interface
      that cannot be parsed.";
    smiv2:oid "1.3.6.1.2.1.14.16.2.9";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf ospfPacketType {
        type leafref {
          path "/OSPF-TRAP-MIB:OSPF-TRAP-MIB/OSPF-TRAP-MIB:ospfTrapControl/OSPF-TRAP-MIB:ospfPacketType";
        }
      }
    }
  }

  notification ospfTxRetransmit {
    description
     "An ospfTxRetransmit trap signifies than an
      OSPF packet has been retransmitted on a
      non-virtual interface.  All packets that may be
      retransmitted are associated with an LSDB entry.
      The LS type, LS ID, and Router ID are used to
      identify the LSDB entry.";
    smiv2:oid "1.3.6.1.2.1.14.16.2.10";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRtrId {
        type leafref {
          path "/ospf-mib:OSPF-MIB/ospf-mib:ospfNbrTable/ospf-mib:ospfNbrEntry/ospf-mib:ospfNbrRtrId";
        }
      }
    }

    container object-5 {

      leaf ospfPacketType {
        type leafref {
          path "/OSPF-TRAP-MIB:OSPF-TRAP-MIB/OSPF-TRAP-MIB:ospfTrapControl/OSPF-TRAP-MIB:ospfPacketType";
        }
      }
    }

    container object-6 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbType {
        type leafref {
          path "/ospf-mib:OSPF-MIB/ospf-mib:ospfLsdbTable/ospf-mib:ospfLsdbEntry/ospf-mib:ospfLsdbType";
        }
      }
    }

    container object-7 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-8 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification ospfVirtIfTxRetransmit {
    description
     "An ospfVirtIfTxRetransmit trap signifies than an
      OSPF packet has been retransmitted on a virtual
      interface.  All packets that may be retransmitted
      are associated with an LSDB entry.  The LS
      type, LS ID, and Router ID are used to identify
      the LSDB entry.";
    smiv2:oid "1.3.6.1.2.1.14.16.2.11";

    container object-1 {

      leaf ospfRouterId {
        type leafref {
          path "/ospf-mib:OSPF-MIB/ospf-mib:ospfGeneralGroup/ospf-mib:ospfRouterId";
        }
      }
    }

    container object-2 {

      leaf ospfVirtIfNeighbor {
        type leafref {
          path "/ospf-mib:OSPF-MIB/ospf-mib:ospfVirtIfTable/ospf-mib:ospfVirtIfEntry/ospf-mib:ospfVirtIfNeighbor";
        }
      }

      leaf ospfVirtIfAreaId {
        type leafref {
          path "/ospf-mib:OSPF-MIB/ospf-mib:ospfVirtIfTable/ospf-mib:ospfVirtIfEntry/ospf-mib:ospfVirtIfAreaId";
        }
      }
    }

    container object-3 {

      leaf ospfVirtIfAreaId {
        type leafref {
          path "/ospf-mib:OSPF-MIB/ospf-mib:ospfVirtIfTable/ospf-mib:ospfVirtIfEntry/ospf-mib:ospfVirtIfAreaId";
        }
      }

      leaf ospfVirtIfNeighbor {
        type leafref {
          path "/ospf-mib:OSPF-MIB/ospf-mib:ospfVirtIfTable/ospf-mib:ospfVirtIfEntry/ospf-mib:ospfVirtIfNeighbor";
        }
      }
    }

    container object-4 {

      leaf ospfPacketType {
        type leafref {
          path "/OSPF-TRAP-MIB:OSPF-TRAP-MIB/OSPF-TRAP-MIB:ospfTrapControl/OSPF-TRAP-MIB:ospfPacketType";
        }
      }
    }

    container object-5 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbType {
        type leafref {
          path "/ospf-mib:OSPF-MIB/ospf-mib:ospfLsdbTable/ospf-mib:ospfLsdbEntry/ospf-mib:ospfLsdbType";
        }
      }
    }

    container object-6 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-7 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification ospfOriginateLsa {
    description
     "An ospfOriginateLsa trap signifies that a new
      LSA has been originated by this router.  This
      trap should not be invoked for simple refreshes
      of LSAs (which happens every 30 minutes), but
      instead will only be invoked when an LSA is
      (re)originated due to a topology change.
      Additionally, this trap does not include LSAs that
      are being flushed because they have reached
      MaxAge.";
    smiv2:oid "1.3.6.1.2.1.14.16.2.12";

    container object-1 {

      leaf ospfRouterId {
        type leafref {
          path "/ospf-mib:OSPF-MIB/ospf-mib:ospfGeneralGroup/ospf-mib:ospfRouterId";
        }
      }
    }

    container object-2 {

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbAreaId {
        type leafref {
          path "/ospf-mib:OSPF-MIB/ospf-mib:ospfLsdbTable/ospf-mib:ospfLsdbEntry/ospf-mib:ospfLsdbAreaId";
        }
      }
    }

    container object-3 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbType {
        type leafref {
          path "/ospf-mib:OSPF-MIB/ospf-mib:ospfLsdbTable/ospf-mib:ospfLsdbEntry/ospf-mib:ospfLsdbType";
        }
      }
    }

    container object-4 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-5 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification ospfMaxAgeLsa {
    description
     "An ospfMaxAgeLsa trap signifies that one of
      the LSAs in the router's link state database has
      aged to MaxAge.";
    smiv2:oid "1.3.6.1.2.1.14.16.2.13";

    container object-1 {

      leaf ospfRouterId {
        type leafref {
          path "/ospf-mib:OSPF-MIB/ospf-mib:ospfGeneralGroup/ospf-mib:ospfRouterId";
        }
      }
    }

    container object-2 {

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbAreaId {
        type leafref {
          path "/ospf-mib:OSPF-MIB/ospf-mib:ospfLsdbTable/ospf-mib:ospfLsdbEntry/ospf-mib:ospfLsdbAreaId";
        }
      }
    }

    container object-3 {

      leaf ospfLsdbAreaId {
        type leafref {
          path "/ospf-mib:OSPF-MIB/ospf-mib:ospfLsdbTable/ospf-mib:ospfLsdbEntry/ospf-mib:ospfLsdbAreaId";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }

      leaf ospfLsdbType {
        type leafref {
          path "/ospf-mib:OSPF-MIB/ospf-mib:ospfLsdbTable/ospf-mib:ospfLsdbEntry/ospf-mib:ospfLsdbType";
        }
      }
    }

    container object-4 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbRouterId {
        type leafref {
          path "/ospf-mib:OSPF-MIB/ospf-mib:ospfLsdbTable/ospf-mib:ospfLsdbEntry/ospf-mib:ospfLsdbRouterId";
        }
      }

      leaf ospfLsdbLsid {
        type leafref {
          path "/ospf-mib:OSPF-MIB/ospf-mib:ospfLsdbTable/ospf-mib:ospfLsdbEntry/ospf-mib:ospfLsdbLsid";
        }
      }
    }

    container object-5 {

      leaf ospfLsdbAreaId {
        type leafref {
          path "/ospf-mib:OSPF-MIB/ospf-mib:ospfLsdbTable/ospf-mib:ospfLsdbEntry/ospf-mib:ospfLsdbAreaId";
        }
      }

      leaf ospfLsdbType {
        type leafref {
          path "/ospf-mib:OSPF-MIB/ospf-mib:ospfLsdbTable/ospf-mib:ospfLsdbEntry/ospf-mib:ospfLsdbType";
        }
      }

      leaf ospfLsdbLsid {
        type leafref {
          path "/ospf-mib:OSPF-MIB/ospf-mib:ospfLsdbTable/ospf-mib:ospfLsdbEntry/ospf-mib:ospfLsdbLsid";
        }
      }

      leaf ospfLsdbRouterId {
        type leafref {
          path "/ospf-mib:OSPF-MIB/ospf-mib:ospfLsdbTable/ospf-mib:ospfLsdbEntry/ospf-mib:ospfLsdbRouterId";
        }
      }
    }
  }

  notification ospfLsdbOverflow {
    description
     "An ospfLsdbOverflow trap signifies that the
      number of LSAs in the router's link state
      database has exceeded ospfExtLsdbLimit.";
    smiv2:oid "1.3.6.1.2.1.14.16.2.14";

    container object-1 {

      leaf ospfRouterId {
        type leafref {
          path "/ospf-mib:OSPF-MIB/ospf-mib:ospfGeneralGroup/ospf-mib:ospfRouterId";
        }
      }
    }

    container object-2 {

      leaf ospfExtLsdbLimit {
        type leafref {
          path "/ospf-mib:OSPF-MIB/ospf-mib:ospfGeneralGroup/ospf-mib:ospfExtLsdbLimit";
        }
      }
    }
  }

  notification ospfLsdbApproachingOverflow {
    description
     "An ospfLsdbApproachingOverflow trap signifies
      that the number of LSAs in the router's
      link state database has exceeded ninety percent of
      ospfExtLsdbLimit.";
    smiv2:oid "1.3.6.1.2.1.14.16.2.15";

    container object-1 {

      leaf ospfRouterId {
        type leafref {
          path "/ospf-mib:OSPF-MIB/ospf-mib:ospfGeneralGroup/ospf-mib:ospfRouterId";
        }
      }
    }

    container object-2 {

      leaf ospfExtLsdbLimit {
        type leafref {
          path "/ospf-mib:OSPF-MIB/ospf-mib:ospfGeneralGroup/ospf-mib:ospfExtLsdbLimit";
        }
      }
    }
  }

  notification ospfIfStateChange {
    description
     "An ospfIfStateChange trap signifies that there
      has been a change in the state of a non-virtual
      OSPF interface.  This trap should be generated
      when the interface state regresses (e.g., goes
      from Dr to Down) or progresses to a terminal
      state (i.e., Point-to-Point, DR Other, Dr, or
      Backup).";
    smiv2:oid "1.3.6.1.2.1.14.16.2.16";

    container object-1 {

      leaf ospfRouterId {
        type leafref {
          path "/ospf-mib:OSPF-MIB/ospf-mib:ospfGeneralGroup/ospf-mib:ospfRouterId";
        }
      }
    }

    container object-2 {

      leaf ospfAddressLessIf {
        type leafref {
          path "/ospf-mib:OSPF-MIB/ospf-mib:ospfIfTable/ospf-mib:ospfIfEntry/ospf-mib:ospfAddressLessIf";
        }
      }

      leaf ospfIfIpAddress {
        type leafref {
          path "/ospf-mib:OSPF-MIB/ospf-mib:ospfIfTable/ospf-mib:ospfIfEntry/ospf-mib:ospfIfIpAddress";
        }
      }
    }

    container object-3 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }
    }

    container object-4 {

      leaf ospfIfIpAddress {
        type leafref {
          path "/ospf-mib:OSPF-MIB/ospf-mib:ospfIfTable/ospf-mib:ospfIfEntry/ospf-mib:ospfIfIpAddress";
        }
      }

      leaf ospfAddressLessIf {
        type leafref {
          path "/ospf-mib:OSPF-MIB/ospf-mib:ospfIfTable/ospf-mib:ospfIfEntry/ospf-mib:ospfAddressLessIf";
        }
      }

      leaf ospfIfState {
        type leafref {
          path "/ospf-mib:OSPF-MIB/ospf-mib:ospfIfTable/ospf-mib:ospfIfEntry/ospf-mib:ospfIfState";
        }
      }
    }
  }

  notification ospfNssaTranslatorStatusChange {
    description
     "An ospfNssaTranslatorStatusChange trap indicates that
      there has been a change in the router's ability to
      translate OSPF type-7 LSAs into OSPF type-5 LSAs.
      This trap should be generated when the translator
      status transitions from or to any defined status on
      a per-area basis.";
    smiv2:oid "1.3.6.1.2.1.14.16.2.17";

    container object-1 {

      leaf ospfRouterId {
        type leafref {
          path "/ospf-mib:OSPF-MIB/ospf-mib:ospfGeneralGroup/ospf-mib:ospfRouterId";
        }
      }
    }

    container object-2 {

      leaf ospfAreaId {
        type leafref {
          path "/ospf-mib:OSPF-MIB/ospf-mib:ospfAreaTable/ospf-mib:ospfAreaEntry/ospf-mib:ospfAreaId";
        }
      }
    }

    container object-3 {

      leaf ospfAreaId {
        type leafref {
          path "/ospf-mib:OSPF-MIB/ospf-mib:ospfAreaTable/ospf-mib:ospfAreaEntry/ospf-mib:ospfAreaId";
        }
      }

      leaf ospfAreaNssaTranslatorState {
        type leafref {
          path "/ospf-mib:OSPF-MIB/ospf-mib:ospfAreaTable/ospf-mib:ospfAreaEntry/ospf-mib:ospfAreaNssaTranslatorState";
        }
      }
    }
  }

  notification ospfRestartStatusChange {
    description
     "An ospfRestartStatusChange trap signifies that
      there has been a change in the graceful restart
      state for the router.  This trap should be
      generated when the router restart status
      changes.";
    smiv2:oid "1.3.6.1.2.1.14.16.2.18";

    container object-1 {

      leaf ospfRouterId {
        type leafref {
          path "/ospf-mib:OSPF-MIB/ospf-mib:ospfGeneralGroup/ospf-mib:ospfRouterId";
        }
      }
    }

    container object-2 {

      leaf ospfRestartStatus {
        type leafref {
          path "/ospf-mib:OSPF-MIB/ospf-mib:ospfGeneralGroup/ospf-mib:ospfRestartStatus";
        }
      }
    }

    container object-3 {

      leaf ospfRestartInterval {
        type leafref {
          path "/ospf-mib:OSPF-MIB/ospf-mib:ospfGeneralGroup/ospf-mib:ospfRestartInterval";
        }
      }
    }

    container object-4 {

      leaf ospfRestartExitReason {
        type leafref {
          path "/ospf-mib:OSPF-MIB/ospf-mib:ospfGeneralGroup/ospf-mib:ospfRestartExitReason";
        }
      }
    }
  }

  notification ospfNbrRestartHelperStatusChange {
    description
     "An ospfNbrRestartHelperStatusChange trap signifies that
      there has been a change in the graceful restart
      helper state for the neighbor.  This trap should be
      generated when the neighbor restart helper status
      transitions for a neighbor.";
    smiv2:oid "1.3.6.1.2.1.14.16.2.19";

    container object-1 {

      leaf ospfRouterId {
        type leafref {
          path "/ospf-mib:OSPF-MIB/ospf-mib:ospfGeneralGroup/ospf-mib:ospfRouterId";
        }
      }
    }

    container object-2 {

      leaf ospfNbrAddressLessIndex {
        type leafref {
          path "/ospf-mib:OSPF-MIB/ospf-mib:ospfNbrTable/ospf-mib:ospfNbrEntry/ospf-mib:ospfNbrAddressLessIndex";
        }
      }

      leaf ospfNbrIpAddr {
        type leafref {
          path "/ospf-mib:OSPF-MIB/ospf-mib:ospfNbrTable/ospf-mib:ospfNbrEntry/ospf-mib:ospfNbrIpAddr";
        }
      }
    }

    container object-3 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }
    }

    container object-4 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRtrId {
        type leafref {
          path "/ospf-mib:OSPF-MIB/ospf-mib:ospfNbrTable/ospf-mib:ospfNbrEntry/ospf-mib:ospfNbrRtrId";
        }
      }
    }

    container object-5 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRestartHelperStatus {
        type leafref {
          path "/ospf-mib:OSPF-MIB/ospf-mib:ospfNbrTable/ospf-mib:ospfNbrEntry/ospf-mib:ospfNbrRestartHelperStatus";
        }
      }
    }

    container object-6 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRestartHelperAge {
        type leafref {
          path "/ospf-mib:OSPF-MIB/ospf-mib:ospfNbrTable/ospf-mib:ospfNbrEntry/ospf-mib:ospfNbrRestartHelperAge";
        }
      }
    }

    container object-7 {

      leaf ospfNbrIpAddr {
        type leafref {
          path "/ospf-mib:OSPF-MIB/ospf-mib:ospfNbrTable/ospf-mib:ospfNbrEntry/ospf-mib:ospfNbrIpAddr";
        }
      }

      leaf ospfNbrAddressLessIndex {
        type leafref {
          path "/ospf-mib:OSPF-MIB/ospf-mib:ospfNbrTable/ospf-mib:ospfNbrEntry/ospf-mib:ospfNbrAddressLessIndex";
        }
      }

      leaf ospfNbrRestartHelperExitReason {
        type leafref {
          path "/ospf-mib:OSPF-MIB/ospf-mib:ospfNbrTable/ospf-mib:ospfNbrEntry/ospf-mib:ospfNbrRestartHelperExitReason";
        }
      }
    }
  }

  notification ospfVirtNbrRestartHelperStatusChange {
    description
     "An ospfVirtNbrRestartHelperStatusChange trap signifies
      that there has been a change in the graceful restart
      helper state for the virtual neighbor.  This trap should
      be generated when the virtual neighbor restart helper
      status transitions for a virtual neighbor.";
    smiv2:oid "1.3.6.1.2.1.14.16.2.20";

    container object-1 {

      leaf ospfRouterId {
        type leafref {
          path "/ospf-mib:OSPF-MIB/ospf-mib:ospfGeneralGroup/ospf-mib:ospfRouterId";
        }
      }
    }

    container object-2 {

      leaf ospfVirtNbrRtrId {
        type leafref {
          path "/ospf-mib:OSPF-MIB/ospf-mib:ospfVirtNbrTable/ospf-mib:ospfVirtNbrEntry/ospf-mib:ospfVirtNbrRtrId";
        }
      }

      leaf ospfVirtNbrArea {
        type leafref {
          path "/ospf-mib:OSPF-MIB/ospf-mib:ospfVirtNbrTable/ospf-mib:ospfVirtNbrEntry/ospf-mib:ospfVirtNbrArea";
        }
      }
    }

    container object-3 {

      leaf ospfVirtNbrArea {
        type leafref {
          path "/ospf-mib:OSPF-MIB/ospf-mib:ospfVirtNbrTable/ospf-mib:ospfVirtNbrEntry/ospf-mib:ospfVirtNbrArea";
        }
      }

      leaf ospfVirtNbrRtrId {
        type leafref {
          path "/ospf-mib:OSPF-MIB/ospf-mib:ospfVirtNbrTable/ospf-mib:ospfVirtNbrEntry/ospf-mib:ospfVirtNbrRtrId";
        }
      }
    }

    container object-4 {

      leaf ospfVirtNbrArea {
        type leafref {
          path "/ospf-mib:OSPF-MIB/ospf-mib:ospfVirtNbrTable/ospf-mib:ospfVirtNbrEntry/ospf-mib:ospfVirtNbrArea";
        }
      }

      leaf ospfVirtNbrRtrId {
        type leafref {
          path "/ospf-mib:OSPF-MIB/ospf-mib:ospfVirtNbrTable/ospf-mib:ospfVirtNbrEntry/ospf-mib:ospfVirtNbrRtrId";
        }
      }

      leaf ospfVirtNbrRestartHelperStatus {
        type leafref {
          path "/ospf-mib:OSPF-MIB/ospf-mib:ospfVirtNbrTable/ospf-mib:ospfVirtNbrEntry/ospf-mib:ospfVirtNbrRestartHelperStatus";
        }
      }
    }

    container object-5 {

      leaf ospfVirtNbrArea {
        type leafref {
          path "/ospf-mib:OSPF-MIB/ospf-mib:ospfVirtNbrTable/ospf-mib:ospfVirtNbrEntry/ospf-mib:ospfVirtNbrArea";
        }
      }

      leaf ospfVirtNbrRtrId {
        type leafref {
          path "/ospf-mib:OSPF-MIB/ospf-mib:ospfVirtNbrTable/ospf-mib:ospfVirtNbrEntry/ospf-mib:ospfVirtNbrRtrId";
        }
      }

      leaf ospfVirtNbrRestartHelperAge {
        type leafref {
          path "/ospf-mib:OSPF-MIB/ospf-mib:ospfVirtNbrTable/ospf-mib:ospfVirtNbrEntry/ospf-mib:ospfVirtNbrRestartHelperAge";
        }
      }
    }

    container object-6 {

      leaf ospfVirtNbrArea {
        type leafref {
          path "/ospf-mib:OSPF-MIB/ospf-mib:ospfVirtNbrTable/ospf-mib:ospfVirtNbrEntry/ospf-mib:ospfVirtNbrArea";
        }
      }

      leaf ospfVirtNbrRtrId {
        type leafref {
          path "/ospf-mib:OSPF-MIB/ospf-mib:ospfVirtNbrTable/ospf-mib:ospfVirtNbrEntry/ospf-mib:ospfVirtNbrRtrId";
        }
      }

      leaf ospfVirtNbrRestartHelperExitReason {
        type leafref {
          path "/ospf-mib:OSPF-MIB/ospf-mib:ospfVirtNbrTable/ospf-mib:ospfVirtNbrEntry/ospf-mib:ospfVirtNbrRestartHelperExitReason";
        }
      }
    }
  }

  smiv2:alias "ospfTrap" {
    smiv2:oid "1.3.6.1.2.1.14.16";
  }

  smiv2:alias "ospfTrapControl" {
    smiv2:oid "1.3.6.1.2.1.14.16.1";
  }

  smiv2:alias "ospfTraps" {
    smiv2:oid "1.3.6.1.2.1.14.16.2";
  }

  smiv2:alias "ospfTrapConformance" {
    smiv2:oid "1.3.6.1.2.1.14.16.3";
  }

  smiv2:alias "ospfTrapGroups" {
    smiv2:oid "1.3.6.1.2.1.14.16.3.1";
  }

  smiv2:alias "ospfTrapCompliances" {
    smiv2:oid "1.3.6.1.2.1.14.16.3.2";
  }

}
