/*
 * Generated by confdc --mib2yang-std
 * Source: mgmt/dmi/model/mib/src/PIM-MIB.mib
 */
/*
 * This YANG module has been generated by smidump 0.5.0:
 *
 *      smidump -f yang PIM-MIB
 *
 * Do not edit. Edit the source file instead!
 */

module PIM-MIB {

  namespace "urn:ietf:params:xml:ns:yang:smiv2:PIM-MIB";
  prefix PIM-MIB;

  import IF-MIB {
    prefix "if-mib";
  }

  import IPMROUTE-STD-MIB {
    prefix "ipmroute-std";
  }

  import SNMPv2-TC {
    prefix "snmpv2-tc";
  }

  import ietf-inet-types {
    prefix "inet";
  }

  import ietf-yang-smiv2 {
    prefix "smiv2";
  }

  import ietf-yang-types {
    prefix "yang";
  }

  organization
   "IETF IDMR Working Group.";

  contact
   " Dave Thaler
    Microsoft Corporation
    One Microsoft Way
    Redmond, WA  98052-6399
    US
    
    Phone: +1 425 703 8835
    EMail: dthaler@microsoft.com";

  description
   "The MIB module for management of PIM routers.";

  revision 2000-09-28 {
    description
     "Initial version, published as RFC 2934.";
  }


  container PIM-MIB {
    config false;

    container pim {
      smiv2:oid "1.3.6.1.3.61.1.1";

      leaf pimJoinPruneInterval {
        type int32;
        units "seconds";
        description
         "The default interval at which periodic PIM-SM Join/Prune
          messages are to be sent.";
        smiv2:max-access "read-write";
        smiv2:oid "1.3.6.1.3.61.1.1.1";
      }
    }

    container pimInterfaceTable {
      description
       "The (conceptual) table listing the router's PIM interfaces.
        IGMP and PIM are enabled on all interfaces listed in this
        table.";
      smiv2:oid "1.3.6.1.3.61.1.1.2";

      list pimInterfaceEntry {
        key "pimInterfaceIfIndex";
        description
         "An entry (conceptual row) in the pimInterfaceTable.";
        smiv2:oid "1.3.6.1.3.61.1.1.2.1";

        leaf pimInterfaceIfIndex {
          type if-mib:InterfaceIndex;
          description
           "The ifIndex value of this PIM interface.";
          smiv2:max-access "not-accessible";
          smiv2:oid "1.3.6.1.3.61.1.1.2.1.1";
        }

        leaf pimInterfaceAddress {
          type inet:ipv4-address;
          description
           "The IP address of the PIM interface.";
          smiv2:max-access "read-only";
          smiv2:oid "1.3.6.1.3.61.1.1.2.1.2";
        }

        leaf pimInterfaceNetMask {
          type inet:ipv4-address;
          description
           "The network mask for the IP address of the PIM interface.";
          smiv2:max-access "read-only";
          smiv2:oid "1.3.6.1.3.61.1.1.2.1.3";
        }

        leaf pimInterfaceMode {
          type enumeration {
            enum "dense" {
              value "1";
            }
            enum "sparse" {
              value "2";
            }
            enum "sparseDense" {
              value "3";
            }
          }
          description
           "The configured mode of this PIM interface.  A value of
            sparseDense is only valid for PIMv1.";
          smiv2:defval "dense";
          smiv2:max-access "read-write";
          smiv2:oid "1.3.6.1.3.61.1.1.2.1.4";
        }

        leaf pimInterfaceDR {
          type inet:ipv4-address;
          description
           "The Designated Router on this PIM interface.  For point-to-
            point interfaces, this object has the value 0.0.0.0.";
          smiv2:max-access "read-only";
          smiv2:oid "1.3.6.1.3.61.1.1.2.1.5";
        }

        leaf pimInterfaceHelloInterval {
          type int32;
          units "seconds";
          description
           "The frequency at which PIM Hello messages are transmitted
            on this interface.";
          smiv2:defval "30";
          smiv2:max-access "read-write";
          smiv2:oid "1.3.6.1.3.61.1.1.2.1.6";
        }

        leaf pimInterfaceStatus {
          type snmpv2-tc:RowStatus;
          description
           "The status of this entry.  Creating the entry enables PIM
            on the interface; destroying the entry disables PIM on the
            interface.";
          smiv2:max-access "read-write";
          smiv2:oid "1.3.6.1.3.61.1.1.2.1.7";
        }

        leaf pimInterfaceJoinPruneInterval {
          type int32;
          units "seconds";
          description
           "The frequency at which PIM Join/Prune messages are
            transmitted on this PIM interface.  The default value of
            this object is the pimJoinPruneInterval.";
          smiv2:max-access "read-write";
          smiv2:oid "1.3.6.1.3.61.1.1.2.1.8";
        }

        leaf pimInterfaceCBSRPreference {
          type int32 {
            range "-1..255";
          }
          description
           "The preference value for the local interface as a candidate
            bootstrap router.  The value of -1 is used to indicate that
            the local interface is not a candidate BSR interface.";
          smiv2:defval "0";
          smiv2:max-access "read-write";
          smiv2:oid "1.3.6.1.3.61.1.1.2.1.9";
        }
      }
    }

    container pimNeighborTable {
      description
       "The (conceptual) table listing the router's PIM neighbors.";
      smiv2:oid "1.3.6.1.3.61.1.1.3";

      list pimNeighborEntry {
        key "pimNeighborAddress";
        description
         "An entry (conceptual row) in the pimNeighborTable.";
        smiv2:oid "1.3.6.1.3.61.1.1.3.1";

        leaf pimNeighborAddress {
          type inet:ipv4-address;
          description
           "The IP address of the PIM neighbor for which this entry
            contains information.";
          smiv2:max-access "not-accessible";
          smiv2:oid "1.3.6.1.3.61.1.1.3.1.1";
        }

        leaf pimNeighborIfIndex {
          type if-mib:InterfaceIndex;
          description
           "The value of ifIndex for the interface used to reach this
            PIM neighbor.";
          smiv2:max-access "read-only";
          smiv2:oid "1.3.6.1.3.61.1.1.3.1.2";
        }

        leaf pimNeighborUpTime {
          type yang:timeticks;
          description
           "The time since this PIM neighbor (last) became a neighbor
            of the local router.";
          smiv2:max-access "read-only";
          smiv2:oid "1.3.6.1.3.61.1.1.3.1.3";
        }

        leaf pimNeighborExpiryTime {
          type yang:timeticks;
          description
           "The minimum time remaining before this PIM neighbor will be
            aged out.";
          smiv2:max-access "read-only";
          smiv2:oid "1.3.6.1.3.61.1.1.3.1.4";
        }

        leaf pimNeighborMode {
          type enumeration {
            enum "dense" {
              value "1";
            }
            enum "sparse" {
              value "2";
            }
          }
          status deprecated;
          description
           "The active PIM mode of this neighbor.  This object is
            deprecated for PIMv2 routers since all neighbors on the
            interface must be either dense or sparse as determined by
            the protocol running on the interface.";
          smiv2:max-access "read-only";
          smiv2:oid "1.3.6.1.3.61.1.1.3.1.5";
        }
      }
    }

    container pimIpMRouteTable {
      description
       "The (conceptual) table listing PIM-specific information on
        a subset of the rows of the ipMRouteTable defined in the IP
        Multicast MIB.";
      smiv2:oid "1.3.6.1.3.61.1.1.4";

      list pimIpMRouteEntry {
        key "ipMRouteGroup ipMRouteSource ipMRouteSourceMask";
        description
         "An entry (conceptual row) in the pimIpMRouteTable.  There
          is one entry per entry in the ipMRouteTable whose incoming
          interface is running PIM.";
        smiv2:oid "1.3.6.1.3.61.1.1.4.1";

        leaf ipMRouteGroup {
          type leafref {
            path "/ipmroute-std:IPMROUTE-STD-MIB/ipmroute-std:ipMRouteTable/ipmroute-std:ipMRouteEntry/ipmroute-std:ipMRouteGroup";
          }
        }

        leaf ipMRouteSource {
          type leafref {
            path "/ipmroute-std:IPMROUTE-STD-MIB/ipmroute-std:ipMRouteTable/ipmroute-std:ipMRouteEntry/ipmroute-std:ipMRouteSource";
          }
        }

        leaf ipMRouteSourceMask {
          type leafref {
            path "/ipmroute-std:IPMROUTE-STD-MIB/ipmroute-std:ipMRouteTable/ipmroute-std:ipMRouteEntry/ipmroute-std:ipMRouteSourceMask";
          }
        }

        leaf pimIpMRouteUpstreamAssertTimer {
          type yang:timeticks;
          description
           "The time remaining before the router changes its upstream
            neighbor back to its RPF neighbor.  This timer is called the
            Assert timer in the PIM Sparse and Dense mode specification.
            
            
            
            
            
            A value of 0 indicates that no Assert has changed the
            upstream neighbor away from the RPF neighbor.";
          smiv2:max-access "read-only";
          smiv2:oid "1.3.6.1.3.61.1.1.4.1.1";
        }

        leaf pimIpMRouteAssertMetric {
          type int32;
          description
           "The metric advertised by the assert winner on the upstream
            interface, or 0 if no such assert is in received.";
          smiv2:max-access "read-only";
          smiv2:oid "1.3.6.1.3.61.1.1.4.1.2";
        }

        leaf pimIpMRouteAssertMetricPref {
          type int32;
          description
           "The preference advertised by the assert winner on the
            upstream interface, or 0 if no such assert is in effect.";
          smiv2:max-access "read-only";
          smiv2:oid "1.3.6.1.3.61.1.1.4.1.3";
        }

        leaf pimIpMRouteAssertRPTBit {
          type boolean;
          description
           "The value of the RPT-bit advertised by the assert winner on
            the upstream interface, or false if no such assert is in
            effect.";
          smiv2:max-access "read-only";
          smiv2:oid "1.3.6.1.3.61.1.1.4.1.4";
        }

        leaf pimIpMRouteFlags {
          type binary {
            length "1";
          }
          description
           "This object describes PIM-specific flags related to a
            multicast state entry.  See the PIM Sparse Mode
            specification for the meaning of the RPT and SPT bits.";
          smiv2:max-access "read-only";
          smiv2:oid "1.3.6.1.3.61.1.1.4.1.5";
        }
      }
    }

    container pimRPTable {
      status deprecated;
      description
       "The (conceptual) table listing PIM version 1 information
        for the Rendezvous Points (RPs) for IP multicast groups.
        This table is deprecated since its function is replaced by
        the pimRPSetTable for PIM version 2.";
      smiv2:oid "1.3.6.1.3.61.1.1.5";

      list pimRPEntry {
        key "pimRPGroupAddress pimRPAddress";
        status deprecated;
        description
         "An entry (conceptual row) in the pimRPTable.  There is one
          entry per RP address for each IP multicast group.";
        smiv2:oid "1.3.6.1.3.61.1.1.5.1";

        leaf pimRPGroupAddress {
          type inet:ipv4-address;
          status deprecated;
          description
           "The IP multicast group address for which this entry
            contains information about an RP.";
          smiv2:max-access "not-accessible";
          smiv2:oid "1.3.6.1.3.61.1.1.5.1.1";
        }

        leaf pimRPAddress {
          type inet:ipv4-address;
          status deprecated;
          description
           "The unicast address of the RP.";
          smiv2:max-access "not-accessible";
          smiv2:oid "1.3.6.1.3.61.1.1.5.1.2";
        }

        leaf pimRPState {
          type enumeration {
            enum "up" {
              value "1";
            }
            enum "down" {
              value "2";
            }
          }
          status deprecated;
          description
           "The state of the RP.";
          smiv2:max-access "read-only";
          smiv2:oid "1.3.6.1.3.61.1.1.5.1.3";
        }

        leaf pimRPStateTimer {
          type yang:timeticks;
          status deprecated;
          description
           "The minimum time remaining before the next state change.
            When pimRPState is up, this is the minimum time which must
            expire until it can be declared down.  When pimRPState is
            down, this is the time until it will be declared up (in
            order to retry).";
          smiv2:max-access "read-only";
          smiv2:oid "1.3.6.1.3.61.1.1.5.1.4";
        }

        leaf pimRPLastChange {
          type yang:timeticks;
          status deprecated;
          description
           "The value of sysUpTime at the time when the corresponding
            instance of pimRPState last changed its value.";
          smiv2:max-access "read-only";
          smiv2:oid "1.3.6.1.3.61.1.1.5.1.5";
        }

        leaf pimRPRowStatus {
          type snmpv2-tc:RowStatus;
          status deprecated;
          description
           "The status of this row, by which new entries may be
            created, or old entries deleted from this table.";
          smiv2:max-access "read-write";
          smiv2:oid "1.3.6.1.3.61.1.1.5.1.6";
        }
      }
    }

    container pimRPSetTable {
      description
       "The (conceptual) table listing PIM information for
        candidate Rendezvous Points (RPs) for IP multicast groups.
        When the local router is the BSR, this information is
        obtained from received Candidate-RP-Advertisements.  When
        the local router is not the BSR, this information is
        obtained from received RP-Set messages.";
      smiv2:oid "1.3.6.1.3.61.1.1.6";

      list pimRPSetEntry {
        key "pimRPSetComponent pimRPSetGroupAddress pimRPSetGroupMask pimRPSetAddress";
        description
         "An entry (conceptual row) in the pimRPSetTable.";
        smiv2:oid "1.3.6.1.3.61.1.1.6.1";

        leaf pimRPSetGroupAddress {
          type inet:ipv4-address;
          description
           "The IP multicast group address which, when combined with
            pimRPSetGroupMask, gives the group prefix for which this
            entry contains information about the Candidate-RP.";
          smiv2:max-access "not-accessible";
          smiv2:oid "1.3.6.1.3.61.1.1.6.1.1";
        }

        leaf pimRPSetGroupMask {
          type inet:ipv4-address;
          description
           "The multicast group address mask which, when combined with
            pimRPSetGroupAddress, gives the group prefix for which this
            entry contains information about the Candidate-RP.";
          smiv2:max-access "not-accessible";
          smiv2:oid "1.3.6.1.3.61.1.1.6.1.2";
        }

        leaf pimRPSetAddress {
          type inet:ipv4-address;
          description
           "The IP address of the Candidate-RP.";
          smiv2:max-access "not-accessible";
          smiv2:oid "1.3.6.1.3.61.1.1.6.1.3";
        }

        leaf pimRPSetHoldTime {
          type int32 {
            range "0..255";
          }
          units "seconds";
          description
           "The holdtime of a Candidate-RP.  If the local router is not
            the BSR, this value is 0.";
          smiv2:max-access "read-only";
          smiv2:oid "1.3.6.1.3.61.1.1.6.1.4";
        }

        leaf pimRPSetExpiryTime {
          type yang:timeticks;
          description
           "The minimum time remaining before the Candidate-RP will be
            declared down.  If the local router is not the BSR, this
            value is 0.";
          smiv2:max-access "read-only";
          smiv2:oid "1.3.6.1.3.61.1.1.6.1.5";
        }

        leaf pimRPSetComponent {
          type int32 {
            range "1..255";
          }
          description
           " A number uniquely identifying the component.  Each
            protocol instance connected to a separate domain should have
            a different index value.";
          smiv2:max-access "not-accessible";
          smiv2:oid "1.3.6.1.3.61.1.1.6.1.6";
        }
      }
    }

    container pimIpMRouteNextHopTable {
      description
       "The (conceptual) table listing PIM-specific information on
        a subset of the rows of the ipMRouteNextHopTable defined in
        the IP Multicast MIB.";
      smiv2:oid "1.3.6.1.3.61.1.1.7";

      list pimIpMRouteNextHopEntry {
        key "ipMRouteNextHopGroup ipMRouteNextHopSource ipMRouteNextHopSourceMask ipMRouteNextHopIfIndex ipMRouteNextHopAddress";
        description
         "An entry (conceptual row) in the pimIpMRouteNextHopTable.
          There is one entry per entry in the ipMRouteNextHopTable
          whose interface is running PIM and whose
          ipMRouteNextHopState is pruned(1).";
        smiv2:oid "1.3.6.1.3.61.1.1.7.1";

        leaf ipMRouteNextHopGroup {
          type leafref {
            path "/ipmroute-std:IPMROUTE-STD-MIB/ipmroute-std:ipMRouteNextHopTable/ipmroute-std:ipMRouteNextHopEntry/ipmroute-std:ipMRouteNextHopGroup";
          }
        }

        leaf ipMRouteNextHopSource {
          type leafref {
            path "/ipmroute-std:IPMROUTE-STD-MIB/ipmroute-std:ipMRouteNextHopTable/ipmroute-std:ipMRouteNextHopEntry/ipmroute-std:ipMRouteNextHopSource";
          }
        }

        leaf ipMRouteNextHopSourceMask {
          type leafref {
            path "/ipmroute-std:IPMROUTE-STD-MIB/ipmroute-std:ipMRouteNextHopTable/ipmroute-std:ipMRouteNextHopEntry/ipmroute-std:ipMRouteNextHopSourceMask";
          }
        }

        leaf ipMRouteNextHopIfIndex {
          type leafref {
            path "/ipmroute-std:IPMROUTE-STD-MIB/ipmroute-std:ipMRouteNextHopTable/ipmroute-std:ipMRouteNextHopEntry/ipmroute-std:ipMRouteNextHopIfIndex";
          }
        }

        leaf ipMRouteNextHopAddress {
          type leafref {
            path "/ipmroute-std:IPMROUTE-STD-MIB/ipmroute-std:ipMRouteNextHopTable/ipmroute-std:ipMRouteNextHopEntry/ipmroute-std:ipMRouteNextHopAddress";
          }
        }

        leaf pimIpMRouteNextHopPruneReason {
          type enumeration {
            enum "other" {
              value "1";
            }
            enum "prune" {
              value "2";
            }
            enum "assert" {
              value "3";
            }
          }
          description
           "This object indicates why the downstream interface was
            pruned, whether in response to a PIM prune message or due to
            PIM Assert processing.";
          smiv2:max-access "read-only";
          smiv2:oid "1.3.6.1.3.61.1.1.7.1.2";
        }
      }
    }

    container pimCandidateRPTable {
      description
       "The (conceptual) table listing the IP multicast groups for
        which the local router is to advertise itself as a
        Candidate-RP when the value of pimComponentCRPHoldTime is
        non-zero.  If this table is empty, then the local router
        
        
        
        
        
        will advertise itself as a Candidate-RP for all groups
        (providing the value of pimComponentCRPHoldTime is non-
        zero).";
      smiv2:oid "1.3.6.1.3.61.1.1.11";

      list pimCandidateRPEntry {
        key "pimCandidateRPGroupAddress pimCandidateRPGroupMask";
        description
         "An entry (conceptual row) in the pimCandidateRPTable.";
        smiv2:oid "1.3.6.1.3.61.1.1.11.1";

        leaf pimCandidateRPGroupAddress {
          type inet:ipv4-address;
          description
           "The IP multicast group address which, when combined with
            pimCandidateRPGroupMask, identifies a group prefix for which
            the local router will advertise itself as a Candidate-RP.";
          smiv2:max-access "not-accessible";
          smiv2:oid "1.3.6.1.3.61.1.1.11.1.1";
        }

        leaf pimCandidateRPGroupMask {
          type inet:ipv4-address;
          description
           "The multicast group address mask which, when combined with
            pimCandidateRPGroupMask, identifies a group prefix for which
            the local router will advertise itself as a Candidate-RP.";
          smiv2:max-access "not-accessible";
          smiv2:oid "1.3.6.1.3.61.1.1.11.1.2";
        }

        leaf pimCandidateRPAddress {
          type inet:ipv4-address;
          description
           "The (unicast) address of the interface which will be
            
            
            
            
            
            advertised as a Candidate-RP.";
          smiv2:max-access "read-write";
          smiv2:oid "1.3.6.1.3.61.1.1.11.1.3";
        }

        leaf pimCandidateRPRowStatus {
          type snmpv2-tc:RowStatus;
          description
           "The status of this row, by which new entries may be
            created, or old entries deleted from this table.";
          smiv2:max-access "read-write";
          smiv2:oid "1.3.6.1.3.61.1.1.11.1.4";
        }
      }
    }

    container pimComponentTable {
      description
       "The (conceptual) table containing objects specific to a PIM
        domain.  One row exists for each domain to which the router
        is connected.  A PIM-SM domain is defined as an area of the
        network over which Bootstrap messages are forwarded.
        Typically, a PIM-SM router will be a member of exactly one
        domain.  This table also supports, however, routers which
        may form a border between two PIM-SM domains and do not
        forward Bootstrap messages between them.";
      smiv2:oid "1.3.6.1.3.61.1.1.12";

      list pimComponentEntry {
        key "pimComponentIndex";
        description
         "An entry (conceptual row) in the pimComponentTable.";
        smiv2:oid "1.3.6.1.3.61.1.1.12.1";

        leaf pimComponentIndex {
          type int32 {
            range "1..255";
          }
          description
           "A number uniquely identifying the component.  Each protocol
            instance connected to a separate domain should have a
            different index value.  Routers that only support membership
            in a single PIM-SM domain should use a pimComponentIndex
            value of 1.";
          smiv2:max-access "not-accessible";
          smiv2:oid "1.3.6.1.3.61.1.1.12.1.1";
        }

        leaf pimComponentBSRAddress {
          type inet:ipv4-address;
          description
           "The IP address of the bootstrap router (BSR) for the local
            PIM region.";
          smiv2:max-access "read-only";
          smiv2:oid "1.3.6.1.3.61.1.1.12.1.2";
        }

        leaf pimComponentBSRExpiryTime {
          type yang:timeticks;
          description
           "The minimum time remaining before the bootstrap router in
            the local domain will be declared down.  For candidate BSRs,
            this is the time until the component sends an RP-Set
            message.  For other routers, this is the time until it may
            accept an RP-Set message from a lower candidate BSR.";
          smiv2:max-access "read-only";
          smiv2:oid "1.3.6.1.3.61.1.1.12.1.3";
        }

        leaf pimComponentCRPHoldTime {
          type int32 {
            range "0..255";
          }
          units "seconds";
          description
           "The holdtime of the component when it is a candidate RP in
            the local domain.  The value of 0 is used to indicate that
            the local system is not a Candidate-RP.";
          smiv2:defval "0";
          smiv2:max-access "read-write";
          smiv2:oid "1.3.6.1.3.61.1.1.12.1.4";
        }

        leaf pimComponentStatus {
          type snmpv2-tc:RowStatus;
          description
           "The status of this entry.  Creating the entry creates
            another protocol instance; destroying the entry disables a
            protocol instance.";
          smiv2:max-access "read-write";
          smiv2:oid "1.3.6.1.3.61.1.1.12.1.5";
        }
      }
    }
  }

  notification pimNeighborLoss {
    description
     "A pimNeighborLoss trap signifies the loss of an adjacency
      with a neighbor.  This trap should be generated when the
      neighbor timer expires, and the router has no other
      neighbors on the same interface with a lower IP address than
      itself.";
    smiv2:oid "1.3.6.1.3.61.1.0.1";

    container object-1 {

      leaf pimNeighborAddress {
        type leafref {
          path "/PIM-MIB:PIM-MIB/PIM-MIB:pimNeighborTable/PIM-MIB:pimNeighborEntry/PIM-MIB:pimNeighborAddress";
        }
      }

      leaf pimNeighborIfIndex {
        type leafref {
          path "/PIM-MIB:PIM-MIB/PIM-MIB:pimNeighborTable/PIM-MIB:pimNeighborEntry/PIM-MIB:pimNeighborIfIndex";
        }
      }
    }
  }

  smiv2:alias "pimMIB" {
    smiv2:oid "1.3.6.1.3.61";
  }

  smiv2:alias "pimMIBObjects" {
    smiv2:oid "1.3.6.1.3.61.1";
  }

  smiv2:alias "pimTraps" {
    smiv2:oid "1.3.6.1.3.61.1.0";
  }

  smiv2:alias "pim" {
    smiv2:oid "1.3.6.1.3.61.1.1";
  }

  smiv2:alias "pimMIBConformance" {
    smiv2:oid "1.3.6.1.3.61.2";
  }

  smiv2:alias "pimMIBCompliances" {
    smiv2:oid "1.3.6.1.3.61.2.1";
  }

  smiv2:alias "pimMIBGroups" {
    smiv2:oid "1.3.6.1.3.61.2.2";
  }

}
