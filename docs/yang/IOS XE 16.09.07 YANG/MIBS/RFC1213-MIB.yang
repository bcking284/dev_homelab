/*
 * Generated by confdc --mib2yang-std
 * Source: mgmt/dmi/model/mib/src/patched/RFC1213-MIB.mib
 */
/*
 * This YANG module has been generated by smidump 0.5.0:
 *
 *      smidump -f yang RFC1213-MIB
 *
 * Do not edit. Edit the source file instead!
 */

module RFC1213-MIB {

  namespace "urn:ietf:params:xml:ns:yang:smiv2:RFC1213-MIB";
  prefix RFC1213-MIB;

  import IANAifType-MIB {
    prefix "ianaiftype-mib";
  }

  import ietf-inet-types {
    prefix "inet";
  }

  import ietf-yang-smiv2 {
    prefix "smiv2";
  }

  import ietf-yang-types {
    prefix "yang";
  }

  typedef DisplayString {
    type binary;
  }

  typedef PhysAddress {
    type binary;
  }


  container RFC1213-MIB {
    config false;

    container system {
      smiv2:oid "1.3.6.1.2.1.1";

      leaf sysDescr {
        type RFC1213-MIB:DisplayString {
          length "0..255";
        }
        description
         "A textual description of the entity.  This value
          should include the full name and version
          identification of the system's hardware type,
          software operating-system, and networking
          software.  It is mandatory that this only contain
          printable ASCII characters.";
        smiv2:max-access "read-only";
        smiv2:oid "1.3.6.1.2.1.1.1";
      }

      leaf sysObjectID {
        type yang:object-identifier-128;
        description
         "The vendor's authoritative identification of the
          network management subsystem contained in the
          entity.  This value is allocated within the SMI
          enterprises subtree (1.3.6.1.4.1) and provides an
          easy and unambiguous means for determining `what
          kind of box' is being managed.  For example, if
          vendor `Flintstones, Inc.' was assigned the
          subtree 1.3.6.1.4.1.4242, it could assign the
          identifier 1.3.6.1.4.1.4242.1.1 to its `Fred
          Router'.";
        smiv2:max-access "read-only";
        smiv2:oid "1.3.6.1.2.1.1.2";
      }

      leaf sysUpTime {
        type yang:timeticks;
        description
         "The time (in hundredths of a second) since the
          network management portion of the system was last
          re-initialized.";
        smiv2:max-access "read-only";
        smiv2:oid "1.3.6.1.2.1.1.3";
      }

      leaf sysContact {
        type RFC1213-MIB:DisplayString {
          length "0..255";
        }
        description
         "The textual identification of the contact person
          for this managed node, together with information
          on how to contact this person.";
        smiv2:max-access "read-write";
        smiv2:oid "1.3.6.1.2.1.1.4";
      }

      leaf sysName {
        type RFC1213-MIB:DisplayString {
          length "0..255";
        }
        description
         "An administratively-assigned name for this
          managed node.  By convention, this is the node's
          fully-qualified domain name.";
        smiv2:max-access "read-write";
        smiv2:oid "1.3.6.1.2.1.1.5";
      }

      leaf sysLocation {
        type RFC1213-MIB:DisplayString {
          length "0..255";
        }
        description
         "The physical location of this node (e.g.,
          `telephone closet, 3rd floor').";
        smiv2:max-access "read-write";
        smiv2:oid "1.3.6.1.2.1.1.6";
      }

      leaf sysServices {
        type int32 {
          range "0..127";
        }
        description
         "A value which indicates the set of services that
          this entity primarily offers.
          
          The value is a sum.  This sum initially takes the
          value zero, Then, for each layer, L, in the range
          1 through 7, that this node performs transactions
          for, 2 raised to (L - 1) is added to the sum.  For
          example, a node which performs primarily routing
          functions would have a value of 4 (2^(3-1)).  In
          contrast, a node which is a host offering
          application services would have a value of 72
          (2^(4-1) + 2^(7-1)).  Note that in the context of
          the Internet suite of protocols, values should be
          calculated accordingly:
          
               layer  functionality
                   1  physical (e.g., repeaters)
                   2  datalink/subnetwork (e.g., bridges)
                   3  internet (e.g., IP gateways)
                   4  end-to-end  (e.g., IP hosts)
                   7  applications (e.g., mail relays)
          
          For systems including OSI protocols, layers 5 and
          6 may also be counted.";
        smiv2:max-access "read-only";
        smiv2:oid "1.3.6.1.2.1.1.7";
      }
    }

    container interfaces {
      smiv2:oid "1.3.6.1.2.1.2";

      leaf ifNumber {
        type int32;
        description
         "The number of network interfaces (regardless of
          their current state) present on this system.";
        smiv2:max-access "read-only";
        smiv2:oid "1.3.6.1.2.1.2.1";
      }
    }

    container ip {
      smiv2:oid "1.3.6.1.2.1.4";

      leaf ipForwarding {
        type enumeration {
          enum "forwarding" {
            value "1";
          }
          enum "not-forwarding" {
            value "2";
          }
        }
        description
         "The indication of whether this entity is acting
          as an IP gateway in respect to the forwarding of
          datagrams received by, but not addressed to, this
          entity.  IP gateways forward datagrams.  IP hosts
          do not (except those source-routed via the host).
          
          Note that for some managed nodes, this object may
          take on only a subset of the values possible.
          Accordingly, it is appropriate for an agent to
          return a `badValue' response if a management
          station attempts to change this object to an
          inappropriate value.";
        smiv2:max-access "read-write";
        smiv2:oid "1.3.6.1.2.1.4.1";
      }

      leaf ipDefaultTTL {
        type int32;
        description
         "The default value inserted into the Time-To-Live
          field of the IP header of datagrams originated at
          this entity, whenever a TTL value is not supplied
          by the transport layer protocol.";
        smiv2:max-access "read-write";
        smiv2:oid "1.3.6.1.2.1.4.2";
      }

      leaf ipInReceives {
        type yang:counter32;
        description
         "The total number of input datagrams received from
          interfaces, including those received in error.";
        smiv2:max-access "read-only";
        smiv2:oid "1.3.6.1.2.1.4.3";
      }

      leaf ipInHdrErrors {
        type yang:counter32;
        description
         "The number of input datagrams discarded due to
          errors in their IP headers, including bad
          checksums, version number mismatch, other format
          errors, time-to-live exceeded, errors discovered
          in processing their IP options, etc.";
        smiv2:max-access "read-only";
        smiv2:oid "1.3.6.1.2.1.4.4";
      }

      leaf ipInAddrErrors {
        type yang:counter32;
        description
         "The number of input datagrams discarded because
          the IP address in their IP header's destination
          field was not a valid address to be received at
          this entity.  This count includes invalid
          addresses (e.g., 0.0.0.0) and addresses of
          unsupported Classes (e.g., Class E).  For entities
          which are not IP Gateways and therefore do not
          forward datagrams, this counter includes datagrams
          discarded because the destination address was not
          a local address.";
        smiv2:max-access "read-only";
        smiv2:oid "1.3.6.1.2.1.4.5";
      }

      leaf ipForwDatagrams {
        type yang:counter32;
        description
         "The number of input datagrams for which this
          entity was not their final IP destination, as a
          result of which an attempt was made to find a
          route to forward them to that final destination.
          In entities which do not act as IP Gateways, this
          counter will include only those packets which were
          Source-Routed via this entity, and the Source-
          Route option processing was successful.";
        smiv2:max-access "read-only";
        smiv2:oid "1.3.6.1.2.1.4.6";
      }

      leaf ipInUnknownProtos {
        type yang:counter32;
        description
         "The number of locally-addressed datagrams
          received successfully but discarded because of an
          unknown or unsupported protocol.";
        smiv2:max-access "read-only";
        smiv2:oid "1.3.6.1.2.1.4.7";
      }

      leaf ipInDiscards {
        type yang:counter32;
        description
         "The number of input IP datagrams for which no
          problems were encountered to prevent their
          continued processing, but which were discarded
          (e.g., for lack of buffer space).  Note that this
          counter does not include any datagrams discarded
          while awaiting re-assembly.";
        smiv2:max-access "read-only";
        smiv2:oid "1.3.6.1.2.1.4.8";
      }

      leaf ipInDelivers {
        type yang:counter32;
        description
         "The total number of input datagrams successfully
          delivered to IP user-protocols (including ICMP).";
        smiv2:max-access "read-only";
        smiv2:oid "1.3.6.1.2.1.4.9";
      }

      leaf ipOutRequests {
        type yang:counter32;
        description
         "The total number of IP datagrams which local IP
          user-protocols (including ICMP) supplied to IP in
          requests for transmission.  Note that this counter
          does not include any datagrams counted in
          ipForwDatagrams.";
        smiv2:max-access "read-only";
        smiv2:oid "1.3.6.1.2.1.4.10";
      }

      leaf ipOutDiscards {
        type yang:counter32;
        description
         "The number of output IP datagrams for which no
          problem was encountered to prevent their
          transmission to their destination, but which were
          discarded (e.g., for lack of buffer space).  Note
          that this counter would include datagrams counted
          in ipForwDatagrams if any such packets met this
          (discretionary) discard criterion.";
        smiv2:max-access "read-only";
        smiv2:oid "1.3.6.1.2.1.4.11";
      }

      leaf ipOutNoRoutes {
        type yang:counter32;
        description
         "The number of IP datagrams discarded because no
          route could be found to transmit them to their
          destination.  Note that this counter includes any
          packets counted in ipForwDatagrams which meet this
          `no-route' criterion.  Note that this includes any
          datagrams which a host cannot route because all of
          its default gateways are down.";
        smiv2:max-access "read-only";
        smiv2:oid "1.3.6.1.2.1.4.12";
      }

      leaf ipReasmTimeout {
        type int32;
        description
         "The maximum number of seconds which received
          fragments are held while they are awaiting
          reassembly at this entity.";
        smiv2:max-access "read-only";
        smiv2:oid "1.3.6.1.2.1.4.13";
      }

      leaf ipReasmReqds {
        type yang:counter32;
        description
         "The number of IP fragments received which needed
          to be reassembled at this entity.";
        smiv2:max-access "read-only";
        smiv2:oid "1.3.6.1.2.1.4.14";
      }

      leaf ipReasmOKs {
        type yang:counter32;
        description
         "The number of IP datagrams successfully re-
          assembled.";
        smiv2:max-access "read-only";
        smiv2:oid "1.3.6.1.2.1.4.15";
      }

      leaf ipReasmFails {
        type yang:counter32;
        description
         "The number of failures detected by the IP re-
          assembly algorithm (for whatever reason: timed
          out, errors, etc).  Note that this is not
          necessarily a count of discarded IP fragments
          since some algorithms (notably the algorithm in
          RFC 815) can lose track of the number of fragments
          by combining them as they are received.";
        smiv2:max-access "read-only";
        smiv2:oid "1.3.6.1.2.1.4.16";
      }

      leaf ipFragOKs {
        type yang:counter32;
        description
         "The number of IP datagrams that have been
          successfully fragmented at this entity.";
        smiv2:max-access "read-only";
        smiv2:oid "1.3.6.1.2.1.4.17";
      }

      leaf ipFragFails {
        type yang:counter32;
        description
         "The number of IP datagrams that have been
          discarded because they needed to be fragmented at
          this entity but could not be, e.g., because their
          Don't Fragment flag was set.";
        smiv2:max-access "read-only";
        smiv2:oid "1.3.6.1.2.1.4.18";
      }

      leaf ipFragCreates {
        type yang:counter32;
        description
         "The number of IP datagram fragments that have
          been generated as a result of fragmentation at
          this entity.";
        smiv2:max-access "read-only";
        smiv2:oid "1.3.6.1.2.1.4.19";
      }

      leaf ipRoutingDiscards {
        type yang:counter32;
        description
         "The number of routing entries which were chosen
          to be discarded even though they are valid.  One
          possible reason for discarding such an entry could
          be to free-up buffer space for other routing
          entries.";
        smiv2:max-access "read-only";
        smiv2:oid "1.3.6.1.2.1.4.23";
      }
    }

    container icmp {
      smiv2:oid "1.3.6.1.2.1.5";

      leaf icmpInMsgs {
        type yang:counter32;
        description
         "The total number of ICMP messages which the
          entity received.  Note that this counter includes
          all those counted by icmpInErrors.";
        smiv2:max-access "read-only";
        smiv2:oid "1.3.6.1.2.1.5.1";
      }

      leaf icmpInErrors {
        type yang:counter32;
        description
         "The number of ICMP messages which the entity
          received but determined as having ICMP-specific
          errors (bad ICMP checksums, bad length, etc.).";
        smiv2:max-access "read-only";
        smiv2:oid "1.3.6.1.2.1.5.2";
      }

      leaf icmpInDestUnreachs {
        type yang:counter32;
        description
         "The number of ICMP Destination Unreachable
          messages received.";
        smiv2:max-access "read-only";
        smiv2:oid "1.3.6.1.2.1.5.3";
      }

      leaf icmpInTimeExcds {
        type yang:counter32;
        description
         "The number of ICMP Time Exceeded messages
          received.";
        smiv2:max-access "read-only";
        smiv2:oid "1.3.6.1.2.1.5.4";
      }

      leaf icmpInParmProbs {
        type yang:counter32;
        description
         "The number of ICMP Parameter Problem messages
          received.";
        smiv2:max-access "read-only";
        smiv2:oid "1.3.6.1.2.1.5.5";
      }

      leaf icmpInSrcQuenchs {
        type yang:counter32;
        description
         "The number of ICMP Source Quench messages
          received.";
        smiv2:max-access "read-only";
        smiv2:oid "1.3.6.1.2.1.5.6";
      }

      leaf icmpInRedirects {
        type yang:counter32;
        description
         "The number of ICMP Redirect messages received.";
        smiv2:max-access "read-only";
        smiv2:oid "1.3.6.1.2.1.5.7";
      }

      leaf icmpInEchos {
        type yang:counter32;
        description
         "The number of ICMP Echo (request) messages
          received.";
        smiv2:max-access "read-only";
        smiv2:oid "1.3.6.1.2.1.5.8";
      }

      leaf icmpInEchoReps {
        type yang:counter32;
        description
         "The number of ICMP Echo Reply messages received.";
        smiv2:max-access "read-only";
        smiv2:oid "1.3.6.1.2.1.5.9";
      }

      leaf icmpInTimestamps {
        type yang:counter32;
        description
         "The number of ICMP Timestamp (request) messages
          received.";
        smiv2:max-access "read-only";
        smiv2:oid "1.3.6.1.2.1.5.10";
      }

      leaf icmpInTimestampReps {
        type yang:counter32;
        description
         "The number of ICMP Timestamp Reply messages
          received.";
        smiv2:max-access "read-only";
        smiv2:oid "1.3.6.1.2.1.5.11";
      }

      leaf icmpInAddrMasks {
        type yang:counter32;
        description
         "The number of ICMP Address Mask Request messages
          received.";
        smiv2:max-access "read-only";
        smiv2:oid "1.3.6.1.2.1.5.12";
      }

      leaf icmpInAddrMaskReps {
        type yang:counter32;
        description
         "The number of ICMP Address Mask Reply messages
          received.";
        smiv2:max-access "read-only";
        smiv2:oid "1.3.6.1.2.1.5.13";
      }

      leaf icmpOutMsgs {
        type yang:counter32;
        description
         "The total number of ICMP messages which this
          entity attempted to send.  Note that this counter
          includes all those counted by icmpOutErrors.";
        smiv2:max-access "read-only";
        smiv2:oid "1.3.6.1.2.1.5.14";
      }

      leaf icmpOutErrors {
        type yang:counter32;
        description
         "The number of ICMP messages which this entity did
          not send due to problems discovered within ICMP
          such as a lack of buffers.  This value should not
          include errors discovered outside the ICMP layer
          such as the inability of IP to route the resultant
          datagram.  In some implementations there may be no
          types of error which contribute to this counter's
          value.";
        smiv2:max-access "read-only";
        smiv2:oid "1.3.6.1.2.1.5.15";
      }

      leaf icmpOutDestUnreachs {
        type yang:counter32;
        description
         "The number of ICMP Destination Unreachable
          messages sent.";
        smiv2:max-access "read-only";
        smiv2:oid "1.3.6.1.2.1.5.16";
      }

      leaf icmpOutTimeExcds {
        type yang:counter32;
        description
         "The number of ICMP Time Exceeded messages sent.";
        smiv2:max-access "read-only";
        smiv2:oid "1.3.6.1.2.1.5.17";
      }

      leaf icmpOutParmProbs {
        type yang:counter32;
        description
         "The number of ICMP Parameter Problem messages
          sent.";
        smiv2:max-access "read-only";
        smiv2:oid "1.3.6.1.2.1.5.18";
      }

      leaf icmpOutSrcQuenchs {
        type yang:counter32;
        description
         "The number of ICMP Source Quench messages sent.";
        smiv2:max-access "read-only";
        smiv2:oid "1.3.6.1.2.1.5.19";
      }

      leaf icmpOutRedirects {
        type yang:counter32;
        description
         "The number of ICMP Redirect messages sent.  For a
          host, this object will always be zero, since hosts
          do not send redirects.";
        smiv2:max-access "read-only";
        smiv2:oid "1.3.6.1.2.1.5.20";
      }

      leaf icmpOutEchos {
        type yang:counter32;
        description
         "The number of ICMP Echo (request) messages sent.";
        smiv2:max-access "read-only";
        smiv2:oid "1.3.6.1.2.1.5.21";
      }

      leaf icmpOutEchoReps {
        type yang:counter32;
        description
         "The number of ICMP Echo Reply messages sent.";
        smiv2:max-access "read-only";
        smiv2:oid "1.3.6.1.2.1.5.22";
      }

      leaf icmpOutTimestamps {
        type yang:counter32;
        description
         "The number of ICMP Timestamp (request) messages
          sent.";
        smiv2:max-access "read-only";
        smiv2:oid "1.3.6.1.2.1.5.23";
      }

      leaf icmpOutTimestampReps {
        type yang:counter32;
        description
         "The number of ICMP Timestamp Reply messages
          sent.";
        smiv2:max-access "read-only";
        smiv2:oid "1.3.6.1.2.1.5.24";
      }

      leaf icmpOutAddrMasks {
        type yang:counter32;
        description
         "The number of ICMP Address Mask Request messages
          sent.";
        smiv2:max-access "read-only";
        smiv2:oid "1.3.6.1.2.1.5.25";
      }

      leaf icmpOutAddrMaskReps {
        type yang:counter32;
        description
         "The number of ICMP Address Mask Reply messages
          sent.";
        smiv2:max-access "read-only";
        smiv2:oid "1.3.6.1.2.1.5.26";
      }
    }

    container tcp {
      smiv2:oid "1.3.6.1.2.1.6";

      leaf tcpRtoAlgorithm {
        type enumeration {
          enum "other" {
            value "1";
          }
          enum "constant" {
            value "2";
          }
          enum "rsre" {
            value "3";
          }
          enum "vanj" {
            value "4";
          }
          enum "rfc2988" {
            value "5";
          }
        }
        description
         "The algorithm used to determine the timeout value
          used for retransmitting unacknowledged octets.";
        smiv2:max-access "read-only";
        smiv2:oid "1.3.6.1.2.1.6.1";
      }

      leaf tcpRtoMin {
        type int32;
        description
         "The minimum value permitted by a TCP
          implementation for the retransmission timeout,
          measured in milliseconds.  More refined semantics
          for objects of this type depend upon the algorithm
          used to determine the retransmission timeout.  In
          particular, when the timeout algorithm is rsre(3),
          an object of this type has the semantics of the
          LBOUND quantity described in RFC 793.";
        smiv2:max-access "read-only";
        smiv2:oid "1.3.6.1.2.1.6.2";
      }

      leaf tcpRtoMax {
        type int32;
        description
         "The maximum value permitted by a TCP
          implementation for the retransmission timeout,
          measured in milliseconds.  More refined semantics
          for objects of this type depend upon the algorithm
          used to determine the retransmission timeout.  In
          particular, when the timeout algorithm is rsre(3),
          an object of this type has the semantics of the
          UBOUND quantity described in RFC 793.";
        smiv2:max-access "read-only";
        smiv2:oid "1.3.6.1.2.1.6.3";
      }

      leaf tcpMaxConn {
        type int32;
        description
         "The limit on the total number of TCP connections
          the entity can support.  In entities where the
          maximum number of connections is dynamic, this
          object should contain the value -1.";
        smiv2:max-access "read-only";
        smiv2:oid "1.3.6.1.2.1.6.4";
      }

      leaf tcpActiveOpens {
        type yang:counter32;
        description
         "The number of times TCP connections have made a
          direct transition to the SYN-SENT state from the
          CLOSED state.";
        smiv2:max-access "read-only";
        smiv2:oid "1.3.6.1.2.1.6.5";
      }

      leaf tcpPassiveOpens {
        type yang:counter32;
        description
         "The number of times TCP connections have made a
          direct transition to the SYN-RCVD state from the
          LISTEN state.";
        smiv2:max-access "read-only";
        smiv2:oid "1.3.6.1.2.1.6.6";
      }

      leaf tcpAttemptFails {
        type yang:counter32;
        description
         "The number of times TCP connections have made a
          direct transition to the CLOSED state from either
          the SYN-SENT state or the SYN-RCVD state, plus the
          number of times TCP connections have made a direct
          transition to the LISTEN state from the SYN-RCVD
          state.";
        smiv2:max-access "read-only";
        smiv2:oid "1.3.6.1.2.1.6.7";
      }

      leaf tcpEstabResets {
        type yang:counter32;
        description
         "The number of times TCP connections have made a
          direct transition to the CLOSED state from either
          the ESTABLISHED state or the CLOSE-WAIT state.";
        smiv2:max-access "read-only";
        smiv2:oid "1.3.6.1.2.1.6.8";
      }

      leaf tcpCurrEstab {
        type yang:gauge32;
        description
         "The number of TCP connections for which the
          current state is either ESTABLISHED or CLOSE-
          WAIT.";
        smiv2:max-access "read-only";
        smiv2:oid "1.3.6.1.2.1.6.9";
      }

      leaf tcpInSegs {
        type yang:counter32;
        description
         "The total number of segments received, including
          those received in error.  This count includes
          segments received on currently established
          connections.";
        smiv2:max-access "read-only";
        smiv2:oid "1.3.6.1.2.1.6.10";
      }

      leaf tcpOutSegs {
        type yang:counter32;
        description
         "The total number of segments sent, including
          those on current connections but excluding those
          containing only retransmitted octets.";
        smiv2:max-access "read-only";
        smiv2:oid "1.3.6.1.2.1.6.11";
      }

      leaf tcpRetransSegs {
        type yang:counter32;
        description
         "The total number of segments retransmitted - that
          is, the number of TCP segments transmitted
          containing one or more previously transmitted
          octets.";
        smiv2:max-access "read-only";
        smiv2:oid "1.3.6.1.2.1.6.12";
      }

      leaf tcpInErrs {
        type yang:counter32;
        description
         "The total number of segments received in error
          (e.g., bad TCP checksums).";
        smiv2:max-access "read-only";
        smiv2:oid "1.3.6.1.2.1.6.14";
      }

      leaf tcpOutRsts {
        type yang:counter32;
        description
         "The number of TCP segments sent containing the
          RST flag.";
        smiv2:max-access "read-only";
        smiv2:oid "1.3.6.1.2.1.6.15";
      }
    }

    container udp {
      smiv2:oid "1.3.6.1.2.1.7";

      leaf udpInDatagrams {
        type yang:counter32;
        description
         "The total number of UDP datagrams delivered to
          UDP users.";
        smiv2:max-access "read-only";
        smiv2:oid "1.3.6.1.2.1.7.1";
      }

      leaf udpNoPorts {
        type yang:counter32;
        description
         "The total number of received UDP datagrams for
          which there was no application at the destination
          port.";
        smiv2:max-access "read-only";
        smiv2:oid "1.3.6.1.2.1.7.2";
      }

      leaf udpInErrors {
        type yang:counter32;
        description
         "The number of received UDP datagrams that could
          not be delivered for reasons other than the lack
          of an application at the destination port.";
        smiv2:max-access "read-only";
        smiv2:oid "1.3.6.1.2.1.7.3";
      }

      leaf udpOutDatagrams {
        type yang:counter32;
        description
         "The total number of UDP datagrams sent from this
          entity.";
        smiv2:max-access "read-only";
        smiv2:oid "1.3.6.1.2.1.7.4";
      }
    }

    container egp {
      smiv2:oid "1.3.6.1.2.1.8";

      leaf egpInMsgs {
        type yang:counter32;
        description
         "The number of EGP messages received without
          error.";
        smiv2:max-access "read-only";
        smiv2:oid "1.3.6.1.2.1.8.1";
      }

      leaf egpInErrors {
        type yang:counter32;
        description
         "The number of EGP messages received that proved
          to be in error.";
        smiv2:max-access "read-only";
        smiv2:oid "1.3.6.1.2.1.8.2";
      }

      leaf egpOutMsgs {
        type yang:counter32;
        description
         "The total number of locally generated EGP
          messages.";
        smiv2:max-access "read-only";
        smiv2:oid "1.3.6.1.2.1.8.3";
      }

      leaf egpOutErrors {
        type yang:counter32;
        description
         "The number of locally generated EGP messages not
          sent due to resource limitations within an EGP
          entity.";
        smiv2:max-access "read-only";
        smiv2:oid "1.3.6.1.2.1.8.4";
      }

      leaf egpAs {
        type int32;
        description
         "The autonomous system number of this EGP entity.";
        smiv2:max-access "read-only";
        smiv2:oid "1.3.6.1.2.1.8.6";
      }
    }

    container snmp {
      smiv2:oid "1.3.6.1.2.1.11";

      leaf snmpInPkts {
        type yang:counter32;
        description
         "The total number of Messages delivered to the
          SNMP entity from the transport service.";
        smiv2:max-access "read-only";
        smiv2:oid "1.3.6.1.2.1.11.1";
      }

      leaf snmpOutPkts {
        type yang:counter32;
        description
         "The total number of SNMP Messages which were
          passed from the SNMP protocol entity to the
          transport service.";
        smiv2:max-access "read-only";
        smiv2:oid "1.3.6.1.2.1.11.2";
      }

      leaf snmpInBadVersions {
        type yang:counter32;
        description
         "The total number of SNMP Messages which were
          delivered to the SNMP protocol entity and were for
          an unsupported SNMP version.";
        smiv2:max-access "read-only";
        smiv2:oid "1.3.6.1.2.1.11.3";
      }

      leaf snmpInBadCommunityNames {
        type yang:counter32;
        description
         "The total number of SNMP Messages delivered to
          the SNMP protocol entity which used a SNMP
          community name not known to said entity.";
        smiv2:max-access "read-only";
        smiv2:oid "1.3.6.1.2.1.11.4";
      }

      leaf snmpInBadCommunityUses {
        type yang:counter32;
        description
         "The total number of SNMP Messages delivered to
          the SNMP protocol entity which represented an SNMP
          operation which was not allowed by the SNMP
          community named in the Message.";
        smiv2:max-access "read-only";
        smiv2:oid "1.3.6.1.2.1.11.5";
      }

      leaf snmpInASNParseErrs {
        type yang:counter32;
        description
         "The total number of ASN.1 or BER errors
          encountered by the SNMP protocol entity when
          decoding received SNMP Messages.";
        smiv2:max-access "read-only";
        smiv2:oid "1.3.6.1.2.1.11.6";
      }

      leaf snmpInTooBigs {
        type yang:counter32;
        description
         "The total number of SNMP PDUs which were
          delivered to the SNMP protocol entity and for
          which the value of the error-status field is
          `tooBig'.";
        smiv2:max-access "read-only";
        smiv2:oid "1.3.6.1.2.1.11.8";
      }

      leaf snmpInNoSuchNames {
        type yang:counter32;
        description
         "The total number of SNMP PDUs which were
          delivered to the SNMP protocol entity and for
          which the value of the error-status field is
          `noSuchName'.";
        smiv2:max-access "read-only";
        smiv2:oid "1.3.6.1.2.1.11.9";
      }

      leaf snmpInBadValues {
        type yang:counter32;
        description
         "The total number of SNMP PDUs which were
          delivered to the SNMP protocol entity and for
          which the value of the error-status field is
          `badValue'.";
        smiv2:max-access "read-only";
        smiv2:oid "1.3.6.1.2.1.11.10";
      }

      leaf snmpInReadOnlys {
        type yang:counter32;
        description
         "The total number valid SNMP PDUs which were
          delivered to the SNMP protocol entity and for
          which the value of the error-status field is
          `readOnly'.  It should be noted that it is a
          protocol error to generate an SNMP PDU which
          contains the value `readOnly' in the error-status
          field, as such this object is provided as a means
          of detecting incorrect implementations of the
          SNMP.";
        smiv2:max-access "read-only";
        smiv2:oid "1.3.6.1.2.1.11.11";
      }

      leaf snmpInGenErrs {
        type yang:counter32;
        description
         "The total number of SNMP PDUs which were
          delivered to the SNMP protocol entity and for
          which the value of the error-status field is
          `genErr'.";
        smiv2:max-access "read-only";
        smiv2:oid "1.3.6.1.2.1.11.12";
      }

      leaf snmpInTotalReqVars {
        type yang:counter32;
        description
         "The total number of MIB objects which have been
          retrieved successfully by the SNMP protocol entity
          as the result of receiving valid SNMP Get-Request
          and Get-Next PDUs.";
        smiv2:max-access "read-only";
        smiv2:oid "1.3.6.1.2.1.11.13";
      }

      leaf snmpInTotalSetVars {
        type yang:counter32;
        description
         "The total number of MIB objects which have been
          altered successfully by the SNMP protocol entity
          as the result of receiving valid SNMP Set-Request
          PDUs.";
        smiv2:max-access "read-only";
        smiv2:oid "1.3.6.1.2.1.11.14";
      }

      leaf snmpInGetRequests {
        type yang:counter32;
        description
         "The total number of SNMP Get-Request PDUs which
          have been accepted and processed by the SNMP
          protocol entity.";
        smiv2:max-access "read-only";
        smiv2:oid "1.3.6.1.2.1.11.15";
      }

      leaf snmpInGetNexts {
        type yang:counter32;
        description
         "The total number of SNMP Get-Next PDUs which have
          been accepted and processed by the SNMP protocol
          entity.";
        smiv2:max-access "read-only";
        smiv2:oid "1.3.6.1.2.1.11.16";
      }

      leaf snmpInSetRequests {
        type yang:counter32;
        description
         "The total number of SNMP Set-Request PDUs which
          have been accepted and processed by the SNMP
          protocol entity.";
        smiv2:max-access "read-only";
        smiv2:oid "1.3.6.1.2.1.11.17";
      }

      leaf snmpInGetResponses {
        type yang:counter32;
        description
         "The total number of SNMP Get-Response PDUs which
          have been accepted and processed by the SNMP
          protocol entity.";
        smiv2:max-access "read-only";
        smiv2:oid "1.3.6.1.2.1.11.18";
      }

      leaf snmpInTraps {
        type yang:counter32;
        description
         "The total number of SNMP Trap PDUs which have
          been accepted and processed by the SNMP protocol
          entity.";
        smiv2:max-access "read-only";
        smiv2:oid "1.3.6.1.2.1.11.19";
      }

      leaf snmpOutTooBigs {
        type yang:counter32;
        description
         "The total number of SNMP PDUs which were
          generated by the SNMP protocol entity and for
          which the value of the error-status field is
          `tooBig.'";
        smiv2:max-access "read-only";
        smiv2:oid "1.3.6.1.2.1.11.20";
      }

      leaf snmpOutNoSuchNames {
        type yang:counter32;
        description
         "The total number of SNMP PDUs which were
          generated by the SNMP protocol entity and for
          which the value of the error-status is
          `noSuchName'.";
        smiv2:max-access "read-only";
        smiv2:oid "1.3.6.1.2.1.11.21";
      }

      leaf snmpOutBadValues {
        type yang:counter32;
        description
         "The total number of SNMP PDUs which were
          generated by the SNMP protocol entity and for
          which the value of the error-status field is
          `badValue'.";
        smiv2:max-access "read-only";
        smiv2:oid "1.3.6.1.2.1.11.22";
      }

      leaf snmpOutGenErrs {
        type yang:counter32;
        description
         "The total number of SNMP PDUs which were
          generated by the SNMP protocol entity and for
          which the value of the error-status field is
          `genErr'.";
        smiv2:max-access "read-only";
        smiv2:oid "1.3.6.1.2.1.11.24";
      }

      leaf snmpOutGetRequests {
        type yang:counter32;
        description
         "The total number of SNMP Get-Request PDUs which
          have been generated by the SNMP protocol entity.";
        smiv2:max-access "read-only";
        smiv2:oid "1.3.6.1.2.1.11.25";
      }

      leaf snmpOutGetNexts {
        type yang:counter32;
        description
         "The total number of SNMP Get-Next PDUs which have
          been generated by the SNMP protocol entity.";
        smiv2:max-access "read-only";
        smiv2:oid "1.3.6.1.2.1.11.26";
      }

      leaf snmpOutSetRequests {
        type yang:counter32;
        description
         "The total number of SNMP Set-Request PDUs which
          have been generated by the SNMP protocol entity.";
        smiv2:max-access "read-only";
        smiv2:oid "1.3.6.1.2.1.11.27";
      }

      leaf snmpOutGetResponses {
        type yang:counter32;
        description
         "The total number of SNMP Get-Response PDUs which
          have been generated by the SNMP protocol entity.";
        smiv2:max-access "read-only";
        smiv2:oid "1.3.6.1.2.1.11.28";
      }

      leaf snmpOutTraps {
        type yang:counter32;
        description
         "The total number of SNMP Trap PDUs which have
          been generated by the SNMP protocol entity.";
        smiv2:max-access "read-only";
        smiv2:oid "1.3.6.1.2.1.11.29";
      }

      leaf snmpEnableAuthenTraps {
        type enumeration {
          enum "enabled" {
            value "1";
          }
          enum "disabled" {
            value "2";
          }
        }
        description
         "Indicates whether the SNMP agent process is
          permitted to generate authentication-failure
          traps.  The value of this object overrides any
          configuration information; as such, it provides a
          means whereby all authentication-failure traps may
          be disabled.
          
          Note that it is strongly recommended that this
          object be stored in non-volatile memory so that it
          remains constant between re-initializations of the
          network management system.";
        smiv2:max-access "read-write";
        smiv2:oid "1.3.6.1.2.1.11.30";
      }
    }

    container ifTable {
      description
       "A list of interface entries.  The number of
        entries is given by the value of ifNumber.";
      smiv2:oid "1.3.6.1.2.1.2.2";

      list ifEntry {
        key "ifIndex";
        description
         "An interface entry containing objects at the
          subnetwork layer and below for a particular
          interface.";
        smiv2:oid "1.3.6.1.2.1.2.2.1";

        leaf ifIndex {
          type int32;
          description
           "A unique value for each interface.  Its value
            ranges between 1 and the value of ifNumber.  The
            value for each interface must remain constant at
            least from one re-initialization of the entity's
            network management system to the next re-
            initialization.";
          smiv2:max-access "read-only";
          smiv2:oid "1.3.6.1.2.1.2.2.1.1";
        }

        leaf ifDescr {
          type RFC1213-MIB:DisplayString {
            length "0..255";
          }
          description
           "A textual string containing information about the
            interface.  This string should include the name of
            the manufacturer, the product name and the version
            of the hardware interface.";
          smiv2:max-access "read-only";
          smiv2:oid "1.3.6.1.2.1.2.2.1.2";
        }

        leaf ifType {
          type ianaiftype-mib:IANAifType;
          description
           "The type of interface.  Additional values for ifType
            are assigned by the Internet Assigned Numbers
            Authority (IANA), through updating the syntax of the
            IANAifType textual convention.";
          smiv2:max-access "read-only";
          smiv2:oid "1.3.6.1.2.1.2.2.1.3";
        }

        leaf ifMtu {
          type int32;
          description
           "The size of the largest datagram which can be
            sent/received on the interface, specified in
            octets.  For interfaces that are used for
            transmitting network datagrams, this is the size
            of the largest network datagram that can be sent
            on the interface.";
          smiv2:max-access "read-only";
          smiv2:oid "1.3.6.1.2.1.2.2.1.4";
        }

        leaf ifSpeed {
          type yang:gauge32;
          description
           "An estimate of the interface's current bandwidth
            in bits per second.  For interfaces which do not
            vary in bandwidth or for those where no accurate
            estimation can be made, this object should contain
            the nominal bandwidth.";
          smiv2:max-access "read-only";
          smiv2:oid "1.3.6.1.2.1.2.2.1.5";
        }

        leaf ifPhysAddress {
          type RFC1213-MIB:PhysAddress;
          description
           "The interface's address at the protocol layer
            immediately `below' the network layer in the
            protocol stack.  For interfaces which do not have
            such an address (e.g., a serial line), this object
            should contain an octet string of zero length.";
          smiv2:max-access "read-only";
          smiv2:oid "1.3.6.1.2.1.2.2.1.6";
        }

        leaf ifAdminStatus {
          type enumeration {
            enum "up" {
              value "1";
            }
            enum "down" {
              value "2";
            }
            enum "testing" {
              value "3";
            }
          }
          description
           "The desired state of the interface.  The
            testing(3) state indicates that no operational
            packets can be passed.";
          smiv2:max-access "read-write";
          smiv2:oid "1.3.6.1.2.1.2.2.1.7";
        }

        leaf ifOperStatus {
          type enumeration {
            enum "up" {
              value "1";
            }
            enum "down" {
              value "2";
            }
            enum "testing" {
              value "3";
            }
            enum "unknown" {
              value "4";
            }
            enum "dormant" {
              value "5";
            }
          }
          description
           "The current operational state of the interface.
            The testing(3) state indicates that no operational
            packets can be passed.";
          smiv2:max-access "read-only";
          smiv2:oid "1.3.6.1.2.1.2.2.1.8";
        }

        leaf ifLastChange {
          type yang:timeticks;
          description
           "The value of sysUpTime at the time the interface
            entered its current operational state.  If the
            current state was entered prior to the last re-
            initialization of the local network management
            subsystem, then this object contains a zero
            value.";
          smiv2:max-access "read-only";
          smiv2:oid "1.3.6.1.2.1.2.2.1.9";
        }

        leaf ifInOctets {
          type yang:counter32;
          description
           "The total number of octets received on the
            interface, including framing characters.";
          smiv2:max-access "read-only";
          smiv2:oid "1.3.6.1.2.1.2.2.1.10";
        }

        leaf ifInUcastPkts {
          type yang:counter32;
          description
           "The number of subnetwork-unicast packets
            delivered to a higher-layer protocol.";
          smiv2:max-access "read-only";
          smiv2:oid "1.3.6.1.2.1.2.2.1.11";
        }

        leaf ifInNUcastPkts {
          type yang:counter32;
          description
           "The number of non-unicast (i.e., subnetwork-
            broadcast or subnetwork-multicast) packets
            delivered to a higher-layer protocol.";
          smiv2:max-access "read-only";
          smiv2:oid "1.3.6.1.2.1.2.2.1.12";
        }

        leaf ifInDiscards {
          type yang:counter32;
          description
           "The number of inbound packets which were chosen
            to be discarded even though no errors had been
            detected to prevent their being deliverable to a
            higher-layer protocol.  One possible reason for
            discarding such a packet could be to free up
            buffer space.";
          smiv2:max-access "read-only";
          smiv2:oid "1.3.6.1.2.1.2.2.1.13";
        }

        leaf ifInErrors {
          type yang:counter32;
          description
           "The number of inbound packets that contained
            errors preventing them from being deliverable to a
            higher-layer protocol.";
          smiv2:max-access "read-only";
          smiv2:oid "1.3.6.1.2.1.2.2.1.14";
        }

        leaf ifInUnknownProtos {
          type yang:counter32;
          description
           "The number of packets received via the interface
            which were discarded because of an unknown or
            unsupported protocol.";
          smiv2:max-access "read-only";
          smiv2:oid "1.3.6.1.2.1.2.2.1.15";
        }

        leaf ifOutOctets {
          type yang:counter32;
          description
           "The total number of octets transmitted out of the
            interface, including framing characters.";
          smiv2:max-access "read-only";
          smiv2:oid "1.3.6.1.2.1.2.2.1.16";
        }

        leaf ifOutUcastPkts {
          type yang:counter32;
          description
           "The total number of packets that higher-level
            protocols requested be transmitted to a
            subnetwork-unicast address, including those that
            were discarded or not sent.";
          smiv2:max-access "read-only";
          smiv2:oid "1.3.6.1.2.1.2.2.1.17";
        }

        leaf ifOutNUcastPkts {
          type yang:counter32;
          description
           "The total number of packets that higher-level
            protocols requested be transmitted to a non-
            unicast (i.e., a subnetwork-broadcast or
            subnetwork-multicast) address, including those
            that were discarded or not sent.";
          smiv2:max-access "read-only";
          smiv2:oid "1.3.6.1.2.1.2.2.1.18";
        }

        leaf ifOutDiscards {
          type yang:counter32;
          description
           "The number of outbound packets which were chosen
            to be discarded even though no errors had been
            detected to prevent their being transmitted.  One
            possible reason for discarding such a packet could
            be to free up buffer space.";
          smiv2:max-access "read-only";
          smiv2:oid "1.3.6.1.2.1.2.2.1.19";
        }

        leaf ifOutErrors {
          type yang:counter32;
          description
           "The number of outbound packets that could not be
            transmitted because of errors.";
          smiv2:max-access "read-only";
          smiv2:oid "1.3.6.1.2.1.2.2.1.20";
        }

        leaf ifOutQLen {
          type yang:gauge32;
          description
           "The length of the output packet queue (in
            packets).";
          smiv2:max-access "read-only";
          smiv2:oid "1.3.6.1.2.1.2.2.1.21";
        }

        leaf ifSpecific {
          type yang:object-identifier-128;
          description
           "A reference to MIB definitions specific to the
            particular media being used to realize the
            interface.  For example, if the interface is
            realized by an ethernet, then the value of this
            object refers to a document defining objects
            specific to ethernet.  If this information is not
            present, its value should be set to the OBJECT
            IDENTIFIER { 0 0 }, which is a syntactically valid
            object identifier, and any conformant
            implementation of ASN.1 and BER must be able to
            generate and recognize this value.";
          smiv2:max-access "read-only";
          smiv2:oid "1.3.6.1.2.1.2.2.1.22";
        }
      }
    }

    container atTable {
      status obsolete;
      description
       "The Address Translation tables contain the
        NetworkAddress to `physical' address equivalences.
        Some interfaces do not use translation tables for
        determining address equivalences (e.g., DDN-X.25
        has an algorithmic method); if all interfaces are
        of this type, then the Address Translation table
        is empty, i.e., has zero entries.";
      smiv2:oid "1.3.6.1.2.1.3.1";

      list atEntry {
        key "atIfIndex atIfIndex_2 atNetAddress";
        status obsolete;
        description
         "Each entry contains one NetworkAddress to
          `physical' address equivalence.";
        smiv2:oid "1.3.6.1.2.1.3.1.1";

        leaf atIfIndex {
          type int32;
          status obsolete;
          description
           "The interface on which this entry's equivalence
            is effective.  The interface identified by a
            particular value of this index is the same
            interface as identified by the same value of
            ifIndex.";
          smiv2:max-access "read-write";
          smiv2:oid "1.3.6.1.2.1.3.1.1.1";
        }

        leaf atIfIndex_2 {
          type int32;
          status obsolete;
          description
           "The interface on which this entry's equivalence
            is effective.  The interface identified by a
            particular value of this index is the same
            interface as identified by the same value of
            ifIndex.";
          smiv2:max-access "read-write";
          smiv2:oid "1.3.6.1.2.1.3.1.1.1";
        }

        leaf atPhysAddress {
          type RFC1213-MIB:PhysAddress;
          status obsolete;
          description
           "The media-dependent `physical' address.
            
            Setting this object to a null string (one of zero
            length) has the effect of invaliding the
            corresponding entry in the atTable object.  That
            is, it effectively disassociates the interface
            identified with said entry from the mapping
            identified with said entry.  It is an
            implementation-specific matter as to whether the
            agent removes an invalidated entry from the table.
            Accordingly, management stations must be prepared
            to receive tabular information from agents that
            corresponds to entries not currently in use.
            Proper interpretation of such entries requires
            examination of the relevant atPhysAddress object.";
          smiv2:max-access "read-write";
          smiv2:oid "1.3.6.1.2.1.3.1.1.2";
        }

        leaf atNetAddress {
          type inet:ipv4-address;
          status obsolete;
          description
           "The NetworkAddress (e.g., the IP address)
            corresponding to the media-dependent `physical'
            address.";
          smiv2:max-access "read-write";
          smiv2:oid "1.3.6.1.2.1.3.1.1.3";
        }
      }
    }

    container ipAddrTable {
      description
       "The table of addressing information relevant to
        this entity's IP addresses.";
      smiv2:oid "1.3.6.1.2.1.4.20";

      list ipAddrEntry {
        key "ipAdEntAddr";
        description
         "The addressing information for one of this
          entity's IP addresses.";
        smiv2:oid "1.3.6.1.2.1.4.20.1";

        leaf ipAdEntAddr {
          type inet:ipv4-address;
          description
           "The IP address to which this entry's addressing
            information pertains.";
          smiv2:max-access "read-only";
          smiv2:oid "1.3.6.1.2.1.4.20.1.1";
        }

        leaf ipAdEntIfIndex {
          type int32;
          description
           "The index value which uniquely identifies the
            interface to which this entry is applicable.  The
            interface identified by a particular value of this
            index is the same interface as identified by the
            same value of ifIndex.";
          smiv2:max-access "read-only";
          smiv2:oid "1.3.6.1.2.1.4.20.1.2";
        }

        leaf ipAdEntNetMask {
          type inet:ipv4-address;
          description
           "The subnet mask associated with the IP address of
            this entry.  The value of the mask is an IP
            address with all the network bits set to 1 and all
            the hosts bits set to 0.";
          smiv2:max-access "read-only";
          smiv2:oid "1.3.6.1.2.1.4.20.1.3";
        }

        leaf ipAdEntBcastAddr {
          type int32;
          description
           "The value of the least-significant bit in the IP
            broadcast address used for sending datagrams on
            the (logical) interface associated with the IP
            address of this entry.  For example, when the
            Internet standard all-ones broadcast address is
            used, the value will be 1.  This value applies to
            both the subnet and network broadcasts addresses
            used by the entity on this (logical) interface.";
          smiv2:max-access "read-only";
          smiv2:oid "1.3.6.1.2.1.4.20.1.4";
        }

        leaf ipAdEntReasmMaxSize {
          type int32 {
            range "0..65535";
          }
          description
           "The size of the largest IP datagram which this
            entity can re-assemble from incoming IP fragmented
            datagrams received on this interface.";
          smiv2:max-access "read-only";
          smiv2:oid "1.3.6.1.2.1.4.20.1.5";
        }
      }
    }

    container ipRouteTable {
      description
       "This entity's IP Routing table.";
      smiv2:oid "1.3.6.1.2.1.4.21";

      list ipRouteEntry {
        key "ipRouteDest";
        description
         "A route to a particular destination.";
        smiv2:oid "1.3.6.1.2.1.4.21.1";

        leaf ipRouteDest {
          type inet:ipv4-address;
          description
           "The destination IP address of this route.  An
            entry with a value of 0.0.0.0 is considered a
            default route.  Multiple routes to a single
            destination can appear in the table, but access to
            such multiple entries is dependent on the table-
            access mechanisms defined by the network
            management protocol in use.";
          smiv2:max-access "read-write";
          smiv2:oid "1.3.6.1.2.1.4.21.1.1";
        }

        leaf ipRouteIfIndex {
          type int32;
          description
           "The index value which uniquely identifies the
            local interface through which the next hop of this
            route should be reached.  The interface identified
            by a particular value of this index is the same
            interface as identified by the same value of
            ifIndex.";
          smiv2:max-access "read-write";
          smiv2:oid "1.3.6.1.2.1.4.21.1.2";
        }

        leaf ipRouteMetric1 {
          type int32;
          description
           "The primary routing metric for this route.  The
            semantics of this metric are determined by the
            routing-protocol specified in the route's
            ipRouteProto value.  If this metric is not used,
            its value should be set to -1.";
          smiv2:max-access "read-write";
          smiv2:oid "1.3.6.1.2.1.4.21.1.3";
        }

        leaf ipRouteMetric2 {
          type int32;
          description
           "An alternate routing metric for this route.  The
            semantics of this metric are determined by the
            routing-protocol specified in the route's
            ipRouteProto value.  If this metric is not used,
            its value should be set to -1.";
          smiv2:max-access "read-write";
          smiv2:oid "1.3.6.1.2.1.4.21.1.4";
        }

        leaf ipRouteMetric3 {
          type int32;
          description
           "An alternate routing metric for this route.  The
            semantics of this metric are determined by the
            routing-protocol specified in the route's
            ipRouteProto value.  If this metric is not used,
            its value should be set to -1.";
          smiv2:max-access "read-write";
          smiv2:oid "1.3.6.1.2.1.4.21.1.5";
        }

        leaf ipRouteMetric4 {
          type int32;
          description
           "An alternate routing metric for this route.  The
            semantics of this metric are determined by the
            routing-protocol specified in the route's
            ipRouteProto value.  If this metric is not used,
            its value should be set to -1.";
          smiv2:max-access "read-write";
          smiv2:oid "1.3.6.1.2.1.4.21.1.6";
        }

        leaf ipRouteNextHop {
          type inet:ipv4-address;
          description
           "The IP address of the next hop of this route.
            (In the case of a route bound to an interface
            which is realized via a broadcast media, the value
            of this field is the agent's IP address on that
            interface.)";
          smiv2:max-access "read-write";
          smiv2:oid "1.3.6.1.2.1.4.21.1.7";
        }

        leaf ipRouteType {
          type enumeration {
            enum "other" {
              value "1";
            }
            enum "invalid" {
              value "2";
            }
            enum "direct" {
              value "3";
            }
            enum "indirect" {
              value "4";
            }
          }
          description
           "The type of route.  Note that the values
            direct(3) and indirect(4) refer to the notion of
            direct and indirect routing in the IP
            architecture.
            
            Setting this object to the value invalid(2) has
            the effect of invalidating the corresponding entry
            in the ipRouteTable object.  That is, it
            effectively disassociates the destination
            identified with said entry from the route
            identified with said entry.  It is an
            implementation-specific matter as to whether the
            agent removes an invalidated entry from the table.
            Accordingly, management stations must be prepared
            to receive tabular information from agents that
            corresponds to entries not currently in use.
            Proper interpretation of such entries requires
            examination of the relevant ipRouteType object.";
          smiv2:max-access "read-write";
          smiv2:oid "1.3.6.1.2.1.4.21.1.8";
        }

        leaf ipRouteProto {
          type enumeration {
            enum "other" {
              value "1";
            }
            enum "local" {
              value "2";
            }
            enum "netmgmt" {
              value "3";
            }
            enum "icmp" {
              value "4";
            }
            enum "egp" {
              value "5";
            }
            enum "ggp" {
              value "6";
            }
            enum "hello" {
              value "7";
            }
            enum "rip" {
              value "8";
            }
            enum "is-is" {
              value "9";
            }
            enum "es-is" {
              value "10";
            }
            enum "ciscoIgrp" {
              value "11";
            }
            enum "bbnSpfIgp" {
              value "12";
            }
            enum "ospf" {
              value "13";
            }
            enum "bgp" {
              value "14";
            }
          }
          description
           "The routing mechanism via which this route was
            learned.  Inclusion of values for gateway routing
            protocols is not intended to imply that hosts
            should support those protocols.";
          smiv2:max-access "read-only";
          smiv2:oid "1.3.6.1.2.1.4.21.1.9";
        }

        leaf ipRouteAge {
          type int32;
          description
           "The number of seconds since this route was last
            updated or otherwise determined to be correct.
            Note that no semantics of `too old' can be implied
            except through knowledge of the routing protocol
            by which the route was learned.";
          smiv2:max-access "read-write";
          smiv2:oid "1.3.6.1.2.1.4.21.1.10";
        }

        leaf ipRouteMask {
          type inet:ipv4-address;
          description
           "Indicate the mask to be logical-ANDed with the
            destination address before being compared to the
            value in the ipRouteDest field.  For those systems
            that do not support arbitrary subnet masks, an
            agent constructs the value of the ipRouteMask by
            determining whether the value of the correspondent
            ipRouteDest field belong to a class-A, B, or C
            network, and then using one of:
            
                 mask           network
                 255.0.0.0      class-A
                 255.255.0.0    class-B
                 255.255.255.0  class-C
            
            If the value of the ipRouteDest is 0.0.0.0 (a
            default route), then the mask value is also
            0.0.0.0.  It should be noted that all IP routing
            subsystems implicitly use this mechanism.";
          smiv2:max-access "read-write";
          smiv2:oid "1.3.6.1.2.1.4.21.1.11";
        }

        leaf ipRouteMetric5 {
          type int32;
          description
           "An alternate routing metric for this route.  The
            semantics of this metric are determined by the
            routing-protocol specified in the route's
            ipRouteProto value.  If this metric is not used,
            its value should be set to -1.";
          smiv2:max-access "read-write";
          smiv2:oid "1.3.6.1.2.1.4.21.1.12";
        }

        leaf ipRouteInfo {
          type yang:object-identifier-128;
          description
           "A reference to MIB definitions specific to the
            particular routing protocol which is responsible
            for this route, as determined by the value
            specified in the route's ipRouteProto value.  If
            this information is not present, its value should
            be set to the OBJECT IDENTIFIER { 0 0 }, which is
            a syntactically valid object identifier, and any
            conformant implementation of ASN.1 and BER must be
            able to generate and recognize this value.";
          smiv2:max-access "read-only";
          smiv2:oid "1.3.6.1.2.1.4.21.1.13";
        }
      }
    }

    container ipNetToMediaTable {
      description
       "The IP Address Translation table used for mapping
        from IP addresses to physical addresses.";
      smiv2:oid "1.3.6.1.2.1.4.22";

      list ipNetToMediaEntry {
        key "ipNetToMediaIfIndex ipNetToMediaNetAddress";
        description
         "Each entry contains one IpAddress to `physical'
          address equivalence.";
        smiv2:oid "1.3.6.1.2.1.4.22.1";

        leaf ipNetToMediaIfIndex {
          type int32;
          description
           "The interface on which this entry's equivalence
            is effective.  The interface identified by a
            particular value of this index is the same
            interface as identified by the same value of
            ifIndex.";
          smiv2:max-access "read-write";
          smiv2:oid "1.3.6.1.2.1.4.22.1.1";
        }

        leaf ipNetToMediaPhysAddress {
          type RFC1213-MIB:PhysAddress;
          description
           "The media-dependent `physical' address.";
          smiv2:max-access "read-write";
          smiv2:oid "1.3.6.1.2.1.4.22.1.2";
        }

        leaf ipNetToMediaNetAddress {
          type inet:ipv4-address;
          description
           "The IpAddress corresponding to the media-
            dependent `physical' address.";
          smiv2:max-access "read-write";
          smiv2:oid "1.3.6.1.2.1.4.22.1.3";
        }

        leaf ipNetToMediaType {
          type enumeration {
            enum "other" {
              value "1";
            }
            enum "invalid" {
              value "2";
            }
            enum "dynamic" {
              value "3";
            }
            enum "static" {
              value "4";
            }
          }
          description
           "The type of mapping.
            
            Setting this object to the value invalid(2) has
            the effect of invalidating the corresponding entry
            in the ipNetToMediaTable.  That is, it effectively
            disassociates the interface identified with said
            entry from the mapping identified with said entry.
            It is an implementation-specific matter as to
            whether the agent removes an invalidated entry
            from the table.  Accordingly, management stations
            must be prepared to receive tabular information
            from agents that corresponds to entries not
            currently in use.  Proper interpretation of such
            entries requires examination of the relevant
            ipNetToMediaType object.";
          smiv2:max-access "read-write";
          smiv2:oid "1.3.6.1.2.1.4.22.1.4";
        }
      }
    }

    container tcpConnTable {
      description
       "A table containing TCP connection-specific
        information.";
      smiv2:oid "1.3.6.1.2.1.6.13";

      list tcpConnEntry {
        key "tcpConnLocalAddress tcpConnLocalPort tcpConnRemAddress tcpConnRemPort";
        description
         "Information about a particular current TCP
          connection.  An object of this type is transient,
          in that it ceases to exist when (or soon after)
          the connection makes the transition to the CLOSED
          state.";
        smiv2:oid "1.3.6.1.2.1.6.13.1";

        leaf tcpConnState {
          type enumeration {
            enum "closed" {
              value "1";
            }
            enum "listen" {
              value "2";
            }
            enum "synSent" {
              value "3";
            }
            enum "synReceived" {
              value "4";
            }
            enum "established" {
              value "5";
            }
            enum "finWait1" {
              value "6";
            }
            enum "finWait2" {
              value "7";
            }
            enum "closeWait" {
              value "8";
            }
            enum "lastAck" {
              value "9";
            }
            enum "closing" {
              value "10";
            }
            enum "timeWait" {
              value "11";
            }
            enum "deleteTCB" {
              value "12";
            }
          }
          description
           "The state of this TCP connection.
            
            The only value which may be set by a management
            station is deleteTCB(12).  Accordingly, it is
            appropriate for an agent to return a `badValue'
            response if a management station attempts to set
            this object to any other value.
            
            If a management station sets this object to the
            value deleteTCB(12), then this has the effect of
            deleting the TCB (as defined in RFC 793) of the
            corresponding connection on the managed node,
            resulting in immediate termination of the
            connection.
            
            As an implementation-specific option, a RST
            segment may be sent from the managed node to the
            other TCP endpoint (note however that RST segments
            are not sent reliably).";
          smiv2:max-access "read-write";
          smiv2:oid "1.3.6.1.2.1.6.13.1.1";
        }

        leaf tcpConnLocalAddress {
          type inet:ipv4-address;
          description
           "The local IP address for this TCP connection.  In
            the case of a connection in the listen state which
            is willing to accept connections for any IP
            interface associated with the node, the value
            0.0.0.0 is used.";
          smiv2:max-access "read-only";
          smiv2:oid "1.3.6.1.2.1.6.13.1.2";
        }

        leaf tcpConnLocalPort {
          type int32 {
            range "0..65535";
          }
          description
           "The local port number for this TCP connection.";
          smiv2:max-access "read-only";
          smiv2:oid "1.3.6.1.2.1.6.13.1.3";
        }

        leaf tcpConnRemAddress {
          type inet:ipv4-address;
          description
           "The remote IP address for this TCP connection.";
          smiv2:max-access "read-only";
          smiv2:oid "1.3.6.1.2.1.6.13.1.4";
        }

        leaf tcpConnRemPort {
          type int32 {
            range "0..65535";
          }
          description
           "The remote port number for this TCP connection.";
          smiv2:max-access "read-only";
          smiv2:oid "1.3.6.1.2.1.6.13.1.5";
        }
      }
    }

    container udpTable {
      description
       "A table containing UDP listener information.";
      smiv2:oid "1.3.6.1.2.1.7.5";

      list udpEntry {
        key "udpLocalAddress udpLocalPort";
        description
         "Information about a particular current UDP
          listener.";
        smiv2:oid "1.3.6.1.2.1.7.5.1";

        leaf udpLocalAddress {
          type inet:ipv4-address;
          description
           "The local IP address for this UDP listener.  In
            the case of a UDP listener which is willing to
            accept datagrams for any IP interface associated
            with the node, the value 0.0.0.0 is used.";
          smiv2:max-access "read-only";
          smiv2:oid "1.3.6.1.2.1.7.5.1.1";
        }

        leaf udpLocalPort {
          type int32 {
            range "0..65535";
          }
          description
           "The local port number for this UDP listener.";
          smiv2:max-access "read-only";
          smiv2:oid "1.3.6.1.2.1.7.5.1.2";
        }
      }
    }

    container egpNeighTable {
      description
       "The EGP neighbor table.";
      smiv2:oid "1.3.6.1.2.1.8.5";

      list egpNeighEntry {
        key "egpNeighAddr";
        description
         "Information about this entity's relationship with
          a particular EGP neighbor.";
        smiv2:oid "1.3.6.1.2.1.8.5.1";

        leaf egpNeighState {
          type enumeration {
            enum "idle" {
              value "1";
            }
            enum "acquisition" {
              value "2";
            }
            enum "down" {
              value "3";
            }
            enum "up" {
              value "4";
            }
            enum "cease" {
              value "5";
            }
          }
          description
           "The EGP state of the local system with respect to
            this entry's EGP neighbor.  Each EGP state is
            represented by a value that is one greater than
            the numerical value associated with said state in
            RFC 904.";
          smiv2:max-access "read-only";
          smiv2:oid "1.3.6.1.2.1.8.5.1.1";
        }

        leaf egpNeighAddr {
          type inet:ipv4-address;
          description
           "The IP address of this entry's EGP neighbor.";
          smiv2:max-access "read-only";
          smiv2:oid "1.3.6.1.2.1.8.5.1.2";
        }

        leaf egpNeighAs {
          type int32;
          description
           "The autonomous system of this EGP peer.  Zero
            should be specified if the autonomous system
            number of the neighbor is not yet known.";
          smiv2:max-access "read-only";
          smiv2:oid "1.3.6.1.2.1.8.5.1.3";
        }

        leaf egpNeighInMsgs {
          type yang:counter32;
          description
           "The number of EGP messages received without error
            from this EGP peer.";
          smiv2:max-access "read-only";
          smiv2:oid "1.3.6.1.2.1.8.5.1.4";
        }

        leaf egpNeighInErrs {
          type yang:counter32;
          description
           "The number of EGP messages received from this EGP
            peer that proved to be in error (e.g., bad EGP
            checksum).";
          smiv2:max-access "read-only";
          smiv2:oid "1.3.6.1.2.1.8.5.1.5";
        }

        leaf egpNeighOutMsgs {
          type yang:counter32;
          description
           "The number of locally generated EGP messages to
            this EGP peer.";
          smiv2:max-access "read-only";
          smiv2:oid "1.3.6.1.2.1.8.5.1.6";
        }

        leaf egpNeighOutErrs {
          type yang:counter32;
          description
           "The number of locally generated EGP messages not
            sent to this EGP peer due to resource limitations
            within an EGP entity.";
          smiv2:max-access "read-only";
          smiv2:oid "1.3.6.1.2.1.8.5.1.7";
        }

        leaf egpNeighInErrMsgs {
          type yang:counter32;
          description
           "The number of EGP-defined error messages received
            from this EGP peer.";
          smiv2:max-access "read-only";
          smiv2:oid "1.3.6.1.2.1.8.5.1.8";
        }

        leaf egpNeighOutErrMsgs {
          type yang:counter32;
          description
           "The number of EGP-defined error messages sent to
            this EGP peer.";
          smiv2:max-access "read-only";
          smiv2:oid "1.3.6.1.2.1.8.5.1.9";
        }

        leaf egpNeighStateUps {
          type yang:counter32;
          description
           "The number of EGP state transitions to the UP
            state with this EGP peer.";
          smiv2:max-access "read-only";
          smiv2:oid "1.3.6.1.2.1.8.5.1.10";
        }

        leaf egpNeighStateDowns {
          type yang:counter32;
          description
           "The number of EGP state transitions from the UP
            state to any other state with this EGP peer.";
          smiv2:max-access "read-only";
          smiv2:oid "1.3.6.1.2.1.8.5.1.11";
        }

        leaf egpNeighIntervalHello {
          type int32;
          description
           "The interval between EGP Hello command
            retransmissions (in hundredths of a second).  This
            represents the t1 timer as defined in RFC 904.";
          smiv2:max-access "read-only";
          smiv2:oid "1.3.6.1.2.1.8.5.1.12";
        }

        leaf egpNeighIntervalPoll {
          type int32;
          description
           "The interval between EGP poll command
            retransmissions (in hundredths of a second).  This
            represents the t3 timer as defined in RFC 904.";
          smiv2:max-access "read-only";
          smiv2:oid "1.3.6.1.2.1.8.5.1.13";
        }

        leaf egpNeighMode {
          type enumeration {
            enum "active" {
              value "1";
            }
            enum "passive" {
              value "2";
            }
          }
          description
           "The polling mode of this EGP entity, either
            passive or active.";
          smiv2:max-access "read-only";
          smiv2:oid "1.3.6.1.2.1.8.5.1.14";
        }

        leaf egpNeighEventTrigger {
          type enumeration {
            enum "start" {
              value "1";
            }
            enum "stop" {
              value "2";
            }
          }
          description
           "A control variable used to trigger operator-
            initiated Start and Stop events.  When read, this
            variable always returns the most recent value that
            egpNeighEventTrigger was set to.  If it has not
            been set since the last initialization of the
            network management subsystem on the node, it
            returns a value of `stop'.
            
            When set, this variable causes a Start or Stop
            event on the specified neighbor, as specified on
            pages 8-10 of RFC 904.  Briefly, a Start event
            causes an Idle peer to begin neighbor acquisition
            and a non-Idle peer to reinitiate neighbor
            acquisition.  A stop event causes a non-Idle peer
            to return to the Idle state until a Start event
            occurs, either via egpNeighEventTrigger or
            otherwise.";
          smiv2:max-access "read-write";
          smiv2:oid "1.3.6.1.2.1.8.5.1.15";
        }
      }
    }
  }

  smiv2:alias "mib-2" {
    smiv2:oid "1.3.6.1.2.1";
  }

  smiv2:alias "system" {
    smiv2:oid "1.3.6.1.2.1.1";
  }

  smiv2:alias "interfaces" {
    smiv2:oid "1.3.6.1.2.1.2";
  }

  smiv2:alias "at" {
    smiv2:oid "1.3.6.1.2.1.3";
  }

  smiv2:alias "ip" {
    smiv2:oid "1.3.6.1.2.1.4";
  }

  smiv2:alias "icmp" {
    smiv2:oid "1.3.6.1.2.1.5";
  }

  smiv2:alias "tcp" {
    smiv2:oid "1.3.6.1.2.1.6";
  }

  smiv2:alias "udp" {
    smiv2:oid "1.3.6.1.2.1.7";
  }

  smiv2:alias "egp" {
    smiv2:oid "1.3.6.1.2.1.8";
  }

  smiv2:alias "transmission" {
    smiv2:oid "1.3.6.1.2.1.10";
  }

  smiv2:alias "snmp" {
    smiv2:oid "1.3.6.1.2.1.11";
  }

}
