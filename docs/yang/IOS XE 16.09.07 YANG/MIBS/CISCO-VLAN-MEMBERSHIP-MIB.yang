/*
 * Generated by confdc --mib2yang-std
 * Source: mgmt/dmi/model/mib/src/CISCO-VLAN-MEMBERSHIP-MIB.mib
 */
/*
 * This YANG module has been generated by smidump 0.5.0:
 *
 *      smidump -f yang CISCO-VLAN-MEMBERSHIP-MIB
 *
 * Do not edit. Edit the source file instead!
 */

module CISCO-VLAN-MEMBERSHIP-MIB {

  namespace "urn:ietf:params:xml:ns:yang:smiv2:CISCO-VLAN-MEMBERSHIP-MIB";
  prefix CISCO-VLAN-MEMBERSHIP-MIB;

  import CISCO-TC {
    prefix "cisco-tc";
  }

  import CISCO-VTP-MIB {
    prefix "cisco-vtp";
  }

  import IF-MIB {
    prefix "if-mib";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems Inc.";

  contact
   "Cisco Systems
    Customer Service
    
    Postal: 170 W Tasman Drive
    San Jose, CA  95134
    USA
    
    Tel: +1 800 553-NETS
    
    E-mail: cs-vlans@cisco.com";

  description
   "The MIB module for the management of the VLAN
    Membership within the frame  work of Cisco
    VLAN Architecture, v 2.0 by Keith McCloghrie. The MIB
    provides information on VLAN Membership Policy Servers
    used by a device and VLAN membership assignments of
    non-trunk bridge ports of the device.";

  revision 2007-12-14 {
    description
     "Add vmVlanCreationGroup.";
  }

  revision 2004-07-16 {
    description
     "Add vmMembershipSummaryExtTable.";
  }

  revision 2004-04-07 {
    description
     "Change the SYNTAX of vmMembershipSummaryMember2kPorts
      from PortList to CiscoPortList.";
  }

  revision 2003-10-10 {
    description
     "Add vmVoiceVlanCdpVerifyEnable to support the feature
      of voice VLANs' detection through CDP packets.";
  }

  revision 2003-06-05 {
    description
     "Deprecate vmMembershipSummaryMemberPorts and define
      vmMembershipSummaryMember2kPorts to support up to 2k 
      bridge ports.";
  }

  revision 2002-03-28 {
    description
     "Add vmVoiceVlanTable to support VVID feature";
  }

  revision 2001-05-01 {
    description
     "Import VlanIndex from CISCO-VTP-MIB";
  }

  revision 2001-01-30 {
    description
     "Corrected description of vmVmpsReconfirmResult";
  }

  revision 2000-01-06 {
    description
     "Added 4k VLAN support";
  }

  revision 1999-01-18 {
    description
     "Add vmNotificationsEnabled.
      Add support for multi-vlan ports.
                  Other minor edits.";
  }

  revision 1996-12-06 {
    description
     "Initial version of this MIB module.";
  }


  container CISCO-VLAN-MEMBERSHIP-MIB {
    config false;

    container vmVmps {
      smiv2:oid "1.3.6.1.4.1.9.9.68.1.1";

      leaf vmVmpsVQPVersion {
        type int32;
        description
         "The VLAN Query Protocol (VQP) version supported on
          the device. VQP is the protocol used to query
          VLAN Membership Policy Server (VMPS) for VLAN
          membership assignments of dynamic VLAN ports.
          A VMPS provides VLAN membership policy
          assignments based on the content of the packets
          received on a port.";
        smiv2:max-access "read-only";
        smiv2:oid "1.3.6.1.4.1.9.9.68.1.1.1";
      }

      leaf vmVmpsRetries {
        type int32 {
          range "1..10";
        }
        description
         "The number of retries for VQP requests to a VMPS before
          using the next available VMPS.";
        smiv2:max-access "read-write";
        smiv2:oid "1.3.6.1.4.1.9.9.68.1.1.2";
      }

      leaf vmVmpsReconfirmInterval {
        type int32 {
          range "0..120";
        }
        units "Minutes";
        description
         "The switch will reconfirm membership of addresses on
          each port with VMPS periodically. This object specifies
          the interval to perform reconfirmation. If the value is
          set to 0, the switch does not reconfirm membership with
          VMPS.";
        smiv2:defval "60";
        smiv2:max-access "read-write";
        smiv2:oid "1.3.6.1.4.1.9.9.68.1.1.3";
      }

      leaf vmVmpsReconfirm {
        type enumeration {
          enum "ready" {
            value "1";
          }
          enum "execute" {
            value "2";
          }
        }
        description
         "Setting this object to execute(2) causes the switch
          to reconfirm membership of every dynamic port.
          Reading this object always return ready(1).";
        smiv2:max-access "read-write";
        smiv2:oid "1.3.6.1.4.1.9.9.68.1.1.4";
      }

      leaf vmVmpsReconfirmResult {
        type enumeration {
          enum "other" {
            value "1";
          }
          enum "inProgress" {
            value "2";
          }
          enum "success" {
            value "3";
          }
          enum "noResponse" {
            value "4";
          }
          enum "noVmps" {
            value "5";
          }
          enum "noDynamicPort" {
            value "6";
          }
          enum "noHostConnected" {
            value "7";
          }
        }
        description
         "This object returns the result of the last request
          that sets vmVmpsReconfirm to execute(2). The
          semantics of the possible results are as follows:
          
               other(1)           - none of following
               inProgress(2)      - reconfirm in progress
               success(3)         - reconfirm completed successfully
               noResponse(4)      - reconfirm failed because no
                                    VMPS responded
               noVmps(5)          - No VMPS configured
               noDynamicPort(6)   - No dynamic ports configured
               noHostConnected(7) - No hosts on dynamic ports";
        smiv2:max-access "read-only";
        smiv2:oid "1.3.6.1.4.1.9.9.68.1.1.5";
      }

      leaf vmVmpsCurrent {
        type inet:ipv4-address;
        description
         "This is the IpAddress of the current VMPS used.";
        smiv2:max-access "read-only";
        smiv2:oid "1.3.6.1.4.1.9.9.68.1.1.6";
      }
    }

    container vmMembership {
      smiv2:oid "1.3.6.1.4.1.9.9.68.1.2";

      leaf vmVlanCreationMode {
        type enumeration {
          enum "automatic" {
            value "1";
          }
          enum "manual" {
            value "2";
          }
        }
        description
         "This object is used to determine whether or not
          a non-existing VLAN will be created automatically
          by the system after assigned to a port.
          
          automatic(1):  a non-existing VLAN will be created
                         automatically by the system after
                         assigned to a port.
          
          manual(2):     a non-existing VLAN will not be created
                         automatically by the system and need to be
                         manually created by the users after assigned
                         to a port.";
        smiv2:max-access "read-write";
        smiv2:oid "1.3.6.1.4.1.9.9.68.1.2.4";
      }
    }

    container vmStatistics {
      smiv2:oid "1.3.6.1.4.1.9.9.68.1.3";

      leaf vmVQPQueries {
        type yang:counter32;
        description
         "The total number of VQP requests sent by this device
          to all VMPS since last system re-initialization.";
        smiv2:max-access "read-only";
        smiv2:oid "1.3.6.1.4.1.9.9.68.1.3.1";
      }

      leaf vmVQPResponses {
        type yang:counter32;
        description
         "The number of VQP responses received by this device
          from all VMPS since last system re-initialization.";
        smiv2:max-access "read-only";
        smiv2:oid "1.3.6.1.4.1.9.9.68.1.3.2";
      }

      leaf vmVmpsChanges {
        type yang:counter32;
        description
         "The number of times, since last system
          re-initialization, the current VMPS was changed. The
          current VMPS is changed whenever the VMPS fails to 
          response after vmVmpsRetries of a VQP request.";
        smiv2:max-access "read-only";
        smiv2:oid "1.3.6.1.4.1.9.9.68.1.3.3";
      }

      leaf vmVQPShutdown {
        type yang:counter32;
        description
         "The number of times, since last system
          re-initialization, a VQP response indicates 
          'shutdown'. A 'shutdown' response is a result of 
          the membership policy configured at a VMPS
          by the administrator.";
        smiv2:max-access "read-only";
        smiv2:oid "1.3.6.1.4.1.9.9.68.1.3.4";
      }

      leaf vmVQPDenied {
        type yang:counter32;
        description
         "The number of times, since last system
          re-initialization, a VQP response indicates 
          'denied'. A 'denied' response is a result of 
          the membership policy configured at a VMPS
          by the administrator.";
        smiv2:max-access "read-only";
        smiv2:oid "1.3.6.1.4.1.9.9.68.1.3.5";
      }

      leaf vmVQPWrongDomain {
        type yang:counter32;
        description
         "The number of times, since last system
          re-initialization, a VQP response indicates wrong 
          management domain. A wrong management domain 
          response indicates that the VMPS used serves a 
          management domain that is different
          from the device's management domain.";
        smiv2:max-access "read-only";
        smiv2:oid "1.3.6.1.4.1.9.9.68.1.3.6";
      }

      leaf vmVQPWrongVersion {
        type yang:counter32;
        description
         "The number of times, since last system
          re-initialization, a VQP response indicates wrong 
          VQP version. A wrong VQP version response 
          indicates that the VMPS used supports a VQP 
          version that is different from the device's 
          VQP version.";
        smiv2:max-access "read-only";
        smiv2:oid "1.3.6.1.4.1.9.9.68.1.3.7";
      }

      leaf vmInsufficientResources {
        type yang:counter32;
        description
         "The number of times, since last system
          re-initialization, a VQP response indicates 
          insufficient resources. An insufficient resources 
          response indicates that the VMPS used does not 
          have the required resources to verify the
          membership assignment requested.";
        smiv2:max-access "read-only";
        smiv2:oid "1.3.6.1.4.1.9.9.68.1.3.8";
      }
    }

    container vmStatus {
      smiv2:oid "1.3.6.1.4.1.9.9.68.1.4";

      leaf vmNotificationsEnabled {
        type boolean;
        description
         "An indication of whether the notifications/traps
          defined in this MIB are enabled.";
        smiv2:max-access "read-write";
        smiv2:oid "1.3.6.1.4.1.9.9.68.1.4.1";
      }
    }

    container vmVmpsTable {
      description
       "A table of VMPS to use. The device will use
        the the primary VMPS by default. If the
        device is unable to reach the primary server
        after vmVmpsRetries retries, it uses the first
        secondary server in the table until it runs out
        of secondary servers, in which case it will return
        to using the primary server. Entries in this table
        may be created and deleted via this MIB or
        the management console on a device.";
      smiv2:oid "1.3.6.1.4.1.9.9.68.1.1.7";

      list vmVmpsEntry {
        key "vmVmpsIpAddress";
        description
         "An entry (conceptual row) in the vmVmpsTable.";
        smiv2:oid "1.3.6.1.4.1.9.9.68.1.1.7.1";

        leaf vmVmpsIpAddress {
          type inet:ipv4-address;
          description
           "The Ip Address of the VMPS.";
          smiv2:max-access "read-only";
          smiv2:oid "1.3.6.1.4.1.9.9.68.1.1.7.1.1";
        }

        leaf vmVmpsPrimary {
          type boolean;
          description
           "The status of the VMPS. Setting this value
            to true will make this VMPS the primary server
            and make the switch use this as the current server.
            Setting this entry to true causes other rows
            to transition to false. Attempting to write
            a value of false after creation will result in
            a return of bad value. Deleting an entry whose
            value is true will result in the first entry
            in the table being set to true.";
          smiv2:max-access "read-write";
          smiv2:oid "1.3.6.1.4.1.9.9.68.1.1.7.1.2";
        }

        leaf vmVmpsRowStatus {
          type snmpv2-tc:RowStatus;
          description
           "The status of this conceptual row.";
          smiv2:max-access "read-write";
          smiv2:oid "1.3.6.1.4.1.9.9.68.1.1.7.1.3";
        }
      }
    }

    container vmMembershipSummaryTable {
      description
       "A summary of VLAN membership of non-trunk
        bridge ports. This is a convenience table
        for retrieving VLAN membership information.
        
        A row is created for a VLAN if:
        a) the VLAN exists, or
        b) a port is assigned to a non-existent VLAN.
        
        VLAN membership can only be modified via the
        vmMembershipTable.";
      smiv2:oid "1.3.6.1.4.1.9.9.68.1.2.1";

      list vmMembershipSummaryEntry {
        key "vmMembershipSummaryVlanIndex";
        description
         "An entry (conceptual row) in the
          vmMembershipSummaryTable.";
        smiv2:oid "1.3.6.1.4.1.9.9.68.1.2.1.1";

        leaf vmMembershipSummaryVlanIndex {
          type cisco-vtp:VlanIndex;
          description
           "The VLAN id of the VLAN.";
          smiv2:max-access "not-accessible";
          smiv2:oid "1.3.6.1.4.1.9.9.68.1.2.1.1.1";
        }

        leaf vmMembershipSummaryMemberPorts {
          type binary {
            length "0..128";
          }
          status deprecated;
          description
           "The set of the device's member ports that belong
            to the VLAN.
            
            Each octet within the value of this object specifies a
            set of eight ports, with the first octet specifying ports
            1 through 8, the second octet specifying ports 9
            through 16, etc.   Within each octet, the most
            significant bit represents the lowest numbered
            port, and the least significant bit represents the
            highest numbered port.  Thus, each port of the
            VLAN is represented by a single bit within the
            value of this object.  If that bit has a value of
            '1' then that port is included in the set of
            ports; the port is not included if its bit has a
            value of '0'.
            
            A port number is the value of dot1dBasePort for
            the port in the BRIDGE-MIB (RFC 1493).";
          smiv2:max-access "read-only";
          smiv2:oid "1.3.6.1.4.1.9.9.68.1.2.1.1.2";
        }

        leaf vmMembershipSummaryMember2kPorts {
          type cisco-tc:CiscoPortList;
          description
           "The set of the device's member ports that belong
            to the VLAN. It has the VLAN membership information
            of up to 2048 ports with the port number from 1 to 
            2048.
            
            Each octet within the value of this object specifies a
            set of eight ports, with the first octet specifying 
            ports 1 through 8, the second octet specifying ports 9
            through 16, etc.   Within each octet, the most
            significant bit represents the lowest numbered
            port, and the least significant bit represents the
            highest numbered port.  Thus, each port of the
            VLAN is represented by a single bit within the
            value of this object.  If that bit has a value of
            '1' then that port is included in the set of
            ports; the port is not included if its bit has a
            value of '0'.
            
            A port number is the value of dot1dBasePort for
            the port in the BRIDGE-MIB (RFC 1493).";
          smiv2:max-access "read-only";
          smiv2:oid "1.3.6.1.4.1.9.9.68.1.2.1.1.3";
        }
      }
    }

    container vmMembershipTable {
      description
       "A table for configuring VLAN port membership.
        There is one row for each bridge port that is
        assigned to a static or dynamic access port. Trunk
        ports are not  represented in this table.  An entry
        may be created and deleted when ports are created or
        deleted via SNMP or the management console on a 
        device.";
      smiv2:oid "1.3.6.1.4.1.9.9.68.1.2.2";

      list vmMembershipEntry {
        key "ifIndex";
        description
         "An entry (conceptual row) in the vmMembershipTable.";
        smiv2:oid "1.3.6.1.4.1.9.9.68.1.2.2.1";

        leaf ifIndex {
          type leafref {
            path "/if-mib:IF-MIB/if-mib:ifTable/if-mib:ifEntry/if-mib:ifIndex";
          }
        }

        leaf vmVlanType {
          type enumeration {
            enum "static" {
              value "1";
            }
            enum "dynamic" {
              value "2";
            }
            enum "multiVlan" {
              value "3";
            }
          }
          description
           "The type of VLAN membership assigned to this port.
            A port with static vlan membership is assigned to a
            single VLAN directly. A port with dynamic membership
            is assigned a single VLAN based on content of packets
            received on the port and via VQP queries to VMPS.
            A port with multiVlan membership may be assigned to
            one or more VLANs directly.
            
            A static or dynamic port membership is specified
            by the value of vmVlan. A multiVlan port membership is
            specified by the value of vmVlans.";
          smiv2:max-access "read-write";
          smiv2:oid "1.3.6.1.4.1.9.9.68.1.2.2.1.1";
        }

        leaf vmVlan {
          type int32 {
            range "0..4095";
          }
          description
           "The VLAN id of the VLAN the port is assigned to
            when vmVlanType is set to static or dynamic.
            This object is not instantiated if not applicable.
            
            The value may be 0 if the port is not assigned
            to a VLAN.
            
            If vmVlanType is static, the port is always
            assigned to a VLAN and the object may not be
            set to 0.
            
            If vmVlanType is dynamic the object's value is
            0 if the port is currently not assigned to a VLAN.
            In addition, the object may be set to 0 only.";
          smiv2:max-access "read-write";
          smiv2:oid "1.3.6.1.4.1.9.9.68.1.2.2.1.2";
        }

        leaf vmPortStatus {
          type enumeration {
            enum "inactive" {
              value "1";
            }
            enum "active" {
              value "2";
            }
            enum "shutdown" {
              value "3";
            }
          }
          description
           "An indication of the current VLAN status of the port.
            A status of inactive(1) indicates that a dynamic port
            does not yet have a VLAN assigned, or a port is 
            assigned to a VLAN that is currently not active. A 
            status of active(2) indicates that the currently 
            assigned VLAN is active. A status of shutdown(3) 
            indicates that the port has been disabled as a result
            of VQP shutdown response.";
          smiv2:max-access "read-only";
          smiv2:oid "1.3.6.1.4.1.9.9.68.1.2.2.1.3";
        }

        leaf vmVlans {
          type binary {
            length "0..128";
          }
          description
           "The VLAN(s) the port is assigned to when the
            port's vmVlanType is set to multiVlan.
            This object is not instantiated if not applicable.
            
            The port is always assigned to one or more VLANs
            and the object may not be set so that there are
            no vlans assigned.
            
            Each octet within the value of this object specifies a
            set of eight VLANs, with the first octet specifying
            VLAN id 1 through 8, the second octet specifying VLAN
            ids 9 through 16, etc.   Within each octet, the most
            significant bit represents the lowest numbered
            VLAN id, and the least significant bit represents the
            highest numbered VLAN id.  Thus, each VLAN of the
            port is represented by a single bit within the
            value of this object.  If that bit has a value of
            '1' then that VLAN is included in the set of
            VLANs; the VLAN is not included if its bit has a
            value of '0'.";
          smiv2:max-access "read-write";
          smiv2:oid "1.3.6.1.4.1.9.9.68.1.2.2.1.4";
        }

        leaf vmVlans2k {
          type binary {
            length "0..128";
          }
          description
           "The VLAN(s) the port is assigned to when the
            port's vmVlanType is set to multiVlan.
            This object is not instantiated if not applicable.
            
            The port is always assigned to one or more VLANs
            and the object may not be set so that there are
            no vlans assigned.
            
            Each octet within the value of this object specifies a
            set of eight VLANs, with the first octet specifying
            VLAN id 1024 through 1031, the second octet specifying 
            VLAN ids 1032 through 1039, etc.  Within each octet, 
            the most significant bit represents the lowest 
            numbered VLAN id, and the least significant bit 
            represents the highest numbered VLAN id.  Thus, each 
            VLAN of the port is represented by a single bit within
            the value of this object.  If that bit has a value of
            '1' then that VLAN is included in the set of
            VLANs; the VLAN is not included if its bit has a
            value of '0'.";
          smiv2:max-access "read-write";
          smiv2:oid "1.3.6.1.4.1.9.9.68.1.2.2.1.5";
        }

        leaf vmVlans3k {
          type binary {
            length "0..128";
          }
          description
           "The VLAN(s) the port is assigned to when the
            port's vmVlanType is set to multiVlan.
            This object is not instantiated if not applicable.
            
            The port is always assigned to one or more VLANs
            and the object may not be set so that there are
            no vlans assigned.
            
            Each octet within the value of this object specifies a
            set of eight VLANs, with the first octet specifying
            VLAN id 2048 through 2055, the second octet specifying 
            VLAN ids 2056 through 2063, etc.   Within each octet, 
            the most significant bit represents the lowest 
            numbered VLAN id, and the least significant bit 
            represents the highest numbered VLAN id.  Thus, each
            VLAN of the port is represented by a single bit within
            the value of this object.  If that bit has a value of
            '1' then that VLAN is included in the set of
            VLANs; the VLAN is not included if its bit has a
            value of '0'.";
          smiv2:max-access "read-write";
          smiv2:oid "1.3.6.1.4.1.9.9.68.1.2.2.1.6";
        }

        leaf vmVlans4k {
          type binary {
            length "0..128";
          }
          description
           "The VLAN(s) the port is assigned to when the
            port's vmVlanType is set to multiVlan.
            This object is not instantiated if not applicable.
            
            The port is always assigned to one or more VLANs
            and the object may not be set so that there are
            no vlans assigned.
            
            Each octet within the value of this object specifies a
            set of eight VLANs, with the first octet specifying
            VLAN id 3072 through 3079, the second octet specifying 
            VLAN ids 3040 through 3047, etc.   Within each octet, 
            the most significant bit represents the lowest 
            numbered VLAN id, and the least significant bit 
            represents the highest numbered VLAN id.  Thus, each
            VLAN of the port is represented by a single bit within
            the value of this object.  If that bit has a value of
            '1' then that VLAN is included in the set of
            VLANs; the VLAN is not included if its bit has a
            value of '0'.";
          smiv2:max-access "read-write";
          smiv2:oid "1.3.6.1.4.1.9.9.68.1.2.2.1.7";
        }
      }
    }

    container vmMembershipSummaryExtTable {
      description
       "A summary of VLAN membership of non-trunk
        bridge ports. This table is used for 
        retrieving VLAN membership information
        for the device which supports dot1dBasePort 
        with value greater than 2048.
        
        A row is created for a VLAN and a particular
        bridge port range, where at least one port 
        in the range is assigned to this VLAN.
        
        VLAN membership can only be modified via the
        vmMembershipTable.";
      smiv2:oid "1.3.6.1.4.1.9.9.68.1.2.3";

      list vmMembershipSummaryExtEntry {
        key "vmMembershipSummaryVlanIndex vmMembershipPortRangeIndex";
        description
         "An entry (conceptual row) in the
          vmMembershipSummaryExtTable.";
        smiv2:oid "1.3.6.1.4.1.9.9.68.1.2.3.1";

        leaf vmMembershipSummaryVlanIndex {
          type leafref {
            path "/CISCO-VLAN-MEMBERSHIP-MIB:CISCO-VLAN-MEMBERSHIP-MIB/CISCO-VLAN-MEMBERSHIP-MIB:vmMembershipSummaryTable/CISCO-VLAN-MEMBERSHIP-MIB:vmMembershipSummaryEntry/CISCO-VLAN-MEMBERSHIP-MIB:vmMembershipSummaryVlanIndex";
          }
        }

        leaf vmMembershipPortRangeIndex {
          type cisco-tc:CiscoPortListRange;
          description
           "The bridge port range index of this row.";
          smiv2:max-access "not-accessible";
          smiv2:oid "1.3.6.1.4.1.9.9.68.1.2.3.1.1";
        }

        leaf vmMembershipSummaryExtPorts {
          type cisco-tc:CiscoPortList;
          description
           "The set of the device's member ports that belong
            to the VLAN. It has the VLAN membership information
            of up to 2k ports with the port number starting from
            the information indicated in vmMembershipPortRangeIndex
            object of the same row. For example, if the value
            of vmMembershipPortRangeIndex is 'twoKto4K', the
            port number indicated in this object starting from
            2049 and ending to 4096. 
            
            A port number is the value of dot1dBasePort for
            the port in the BRIDGE-MIB (RFC 1493).";
          smiv2:max-access "read-only";
          smiv2:oid "1.3.6.1.4.1.9.9.68.1.2.3.1.2";
        }
      }
    }

    container vmVoiceVlanTable {
      description
       "A table for configuring the Voice VLAN-ID
        for the ports. An entry will exist for each
        interface which supports Voice Vlan feature.";
      smiv2:oid "1.3.6.1.4.1.9.9.68.1.5.1";

      list vmVoiceVlanEntry {
        key "ifIndex";
        description
         "An entry (conceptual row) in the vmVoiceVlanTable.
          Only interfaces which support Voice Vlan feature
          are shown.";
        smiv2:oid "1.3.6.1.4.1.9.9.68.1.5.1.1";

        leaf ifIndex {
          type leafref {
            path "/if-mib:IF-MIB/if-mib:ifTable/if-mib:ifEntry/if-mib:ifIndex";
          }
        }

        leaf vmVoiceVlanId {
          type int32 {
            range "0..4096";
          }
          description
           "The Voice Vlan ID (VVID) to which this
            port belongs to.
            
            0    -    The CDP packets transmitting 
                      through this port would contain
                      Appliance VLAN-ID TLV with value 
                      of 0. VoIP and related packets 
                      are expected to be sent and 
                      received with VLAN-id=0 and an 
                      802.1p priority. 
            
            1..4094 - The CDP packets transmitting
                      through this port would contain
                      Appliance VLAN-ID TLV with N.
                      VoIP and related packets are
                      expected to be sent and received
                      with VLAN-id=N and an 802.1p
                      priority.
            
            4095  -   The CDP packets transmitting
                      through this port would contain
                      Appliance VLAN-ID TLV with value
                      of 4095. VoIP and related packets
                      are expected to be sent and 
                      received untagged without an 
                      802.1p priority.
            
            4096  -   The CDP packets transmitting 
                      through this port would not 
                      include Appliance VLAN-ID TLV; 
                      or, if the VVID is not supported 
                      on the port, this MIB object will
                      not be configurable and will 
                      return 4096.";
          smiv2:max-access "read-write";
          smiv2:oid "1.3.6.1.4.1.9.9.68.1.5.1.1.1";
        }

        leaf vmVoiceVlanCdpVerifyEnable {
          type boolean;
          description
           "Enable or Disable the feature of CDP message
            verification of voice VLANs.
            
            true   - The voice VLAN vmVoiceVlan is enabled 
                     only after CDP messages are received 
                     from the IP phone.
            
            false -  The voice VLAN vmVoiceVlan is enabled
                     as soon as the IP phone interface is
                     up. There is no verification needed 
                     from CDP messages from the IP phone.";
          smiv2:max-access "read-write";
          smiv2:oid "1.3.6.1.4.1.9.9.68.1.5.1.1.2";
        }
      }
    }
  }

  notification vmVmpsChange {
    description
     "A VMPS change notification is generated whenever
      vmVmpsChanges is incremented. The IP address
      of the new VMPS is sent.";
    smiv2:oid "1.3.6.1.4.1.9.9.68.2.0.1";

    container object-1 {

      leaf vmVmpsIpAddress {
        type leafref {
          path "/CISCO-VLAN-MEMBERSHIP-MIB:CISCO-VLAN-MEMBERSHIP-MIB/CISCO-VLAN-MEMBERSHIP-MIB:vmVmpsTable/CISCO-VLAN-MEMBERSHIP-MIB:vmVmpsEntry/CISCO-VLAN-MEMBERSHIP-MIB:vmVmpsIpAddress";
        }
      }
    }
  }

  smiv2:alias "ciscoVlanMembershipMIB" {
    smiv2:oid "1.3.6.1.4.1.9.9.68";
  }

  smiv2:alias "ciscoVlanMembershipMIBObjects" {
    smiv2:oid "1.3.6.1.4.1.9.9.68.1";
  }

  smiv2:alias "vmVmps" {
    smiv2:oid "1.3.6.1.4.1.9.9.68.1.1";
  }

  smiv2:alias "vmMembership" {
    smiv2:oid "1.3.6.1.4.1.9.9.68.1.2";
  }

  smiv2:alias "vmStatistics" {
    smiv2:oid "1.3.6.1.4.1.9.9.68.1.3";
  }

  smiv2:alias "vmStatus" {
    smiv2:oid "1.3.6.1.4.1.9.9.68.1.4";
  }

  smiv2:alias "vmVoiceVlan" {
    smiv2:oid "1.3.6.1.4.1.9.9.68.1.5";
  }

  smiv2:alias "vmNotifications" {
    smiv2:oid "1.3.6.1.4.1.9.9.68.2";
  }

  smiv2:alias "vmNotificationsPrefix" {
    smiv2:oid "1.3.6.1.4.1.9.9.68.2.0";
  }

  smiv2:alias "vmMIBConformance" {
    smiv2:oid "1.3.6.1.4.1.9.9.68.3";
  }

  smiv2:alias "vmMIBCompliances" {
    smiv2:oid "1.3.6.1.4.1.9.9.68.3.1";
  }

  smiv2:alias "vmMIBGroups" {
    smiv2:oid "1.3.6.1.4.1.9.9.68.3.2";
  }

}
