/*
 * Generated by confdc --mib2yang-std
 * Source: mgmt/dmi/model/mib/src/CISCO-SESS-BORDER-CTRLR-STATS-MIB.mib
 */
/*
 * This YANG module has been generated by smidump 0.5.0:
 *
 *      smidump -f yang CISCO-SESS-BORDER-CTRLR-STATS-MIB
 *
 * Do not edit. Edit the source file instead!
 */

module CISCO-SESS-BORDER-CTRLR-STATS-MIB {

  namespace "urn:ietf:params:xml:ns:yang:smiv2:CISCO-SESS-BORDER-CTRLR-STATS-MIB";
  prefix CISCO-SESS-BORDER-CTRLR-STATS-MIB;

  import CISCO-SESS-BORDER-CTRLR-CALL-STATS-MIB {
    prefix "cisco-sess";
  }

  import SNMP-FRAMEWORK-MIB {
    prefix "snmp-framework";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: sbc-dev@cisco.com";

  description
   "The main purpose of this MIB is to define the statistics
    information for Session Border Controller application. This MIB
    categorizes the statistics information into following types:
    1. RADIUS Messages Statistics - Represents statistics of
       various RADIUS messages for RADIUS servers with which the
       client (SBC) shares a secret.
    
    2. Rf Billing Statistics- Represents Rf billing statistics 
       information which monitors the messages sent per-realm over
       IMS Rx interface by Rf billing manager(SBC).
    
    3. SIP Statistics - Represents SIP requests and various SIP
       responses on a SIP adjacency in a given interval.
    
    The Session Border Controller (SBC) enables direct IP-to-IP
    interconnect between multiple administrative domains for
    session-based services providing protocol inter-working,
    security, and admission control and management. The SBC is a
    voice over IP (VoIP) device that sits on the border of a 
    network and controls call admission to that network. 
    
    The primary purpose of an SBC is to protect the interior of the
    network from excessive call load and malicious traffic.
    Additional functions provided by the SBC include media bridging
    and billing services. 
    
    Periodic Statistics - Represents the SBC call statistics 
    information for a particular time interval. E.g. you can 
    specify that you want to retrieve statistics for a summary 
    period of the current or previous 5 minutes, 15 minutes, hour, 
    or day. The statistics for 5 minutes are divided into five 
    minute intervals past the hour - that is, at 0 minutes, 5 
    minutes, 10 minutes... past the hour.  When you retrieve 
    statistics for the current five minute period, you will be 
    given statistics from the start of the interval to the current
    time. When you retrieve statistics for the previous five 
    minutes, you will be given the statistics for the entirety of 
    the previous interval. For example, if it is currently 12:43
    -  the current 5 minute statistics cover 12:40 - 12:43
    
    -  the previous 5 minute statistics cover 12:35 - 12:40
    
    The other intervals work similarly.  15 minute statistics are 
    divided into 15 minute intervals past the hour (0 minutes, 15 
    minutes, 30 minutes, 45 minutes).  Hourly statistics are divided
    into intervals on the hour. Daily statistics are divided into
    intervals at 0:00 each day. Therefore, if you retrieve the 
    statistics at 12:43 for each of these intervals, the periods
    covered are as follows.  
    -     current 15 minutes: 12:30 - 12:43
    
    -     previous 15 minutes: 12:15 - 12:30
    
    -     current hour: 12:00 - 12:43
    
    -     last hour: 11:00 - 12:00
    
    -     current day: 00:00 - 12:43
    
    -     last day: 00:00 (the day before) - 00:00.
    
    
    GLOSSARY
    SBC: Session Border Controller
    
    CSB: CISCO Session Border Controller
    
    Adjacency: An adjacency contains the system information to be
    transmitted to next HOP.
    
    ACR: Accounting Request
    
    ACA: Accounting Accept
    
    AVP: Attribute-Value Pairs
    
    REFERENCES
    1. CISCO Session Border Controller Documents and FAQ
    http://zed.cisco.com/confluence/display/SBC/SBC";

  revision 2010-09-15 {
    description
     "Latest version of this MIB module.";
  }

  typedef CiscoSbcSIPMethod {
    type enumeration {
      enum "unknown" {
        value "1";
      }
      enum "ack" {
        value "2";
      }
      enum "bye" {
        value "3";
      }
      enum "cancel" {
        value "4";
      }
      enum "info" {
        value "5";
      }
      enum "invite" {
        value "6";
      }
      enum "message" {
        value "7";
      }
      enum "notify" {
        value "8";
      }
      enum "options" {
        value "9";
      }
      enum "prack" {
        value "10";
      }
      enum "refer" {
        value "11";
      }
      enum "register" {
        value "12";
      }
      enum "subscribe" {
        value "13";
      }
      enum "update" {
        value "14";
      }
    }
    description
     "This textual convention represents the various SIP Methods.";
  }

  typedef CiscoSbcRadiusClientType {
    type enumeration {
      enum "authentication" {
        value "1";
      }
      enum "accounting" {
        value "2";
      }
    }
    description
     "This textual convention represents the type of RADIUS client.";
  }


  container CISCO-SESS-BORDER-CTRLR-STATS-MIB {
    config false;

    container csbRadiusStatsTable {
      description
       "This table has the reporting statistics of various RADIUS
        messages for RADIUS servers with which the client (SBC) shares a
        secret. Each entry in this table is identified by a 
        value of csbRadiusStatsEntIndex. The other indices of this table
        are csbCallStatsInstanceIndex defined in 
        csbCallStatsInstanceTable and csbCallStatsServiceIndex defined
        in csbCallStatsTable.";
      smiv2:oid "1.3.6.1.4.1.9.9.757.1.1";

      list csbRadiusStatsEntry {
        key "csbCallStatsInstanceIndex csbCallStatsServiceIndex csbRadiusStatsEntIndex";
        description
         "A conceptual row in the csbRadiusStatsTable. There is an
          entry in this table for each RADIUS server, as identified by a 
          value of csbRadiusStatsEntIndex. The other indices of this 
          table are csbCallStatsInstanceIndex defined in 
          csbCallStatsInstanceTable and csbCallStatsServiceIndex defined
          in csbCallStatsTable.";
        smiv2:oid "1.3.6.1.4.1.9.9.757.1.1.1";

        leaf csbCallStatsInstanceIndex {
          type leafref {
            path "/cisco-sess:CISCO-SESS-BORDER-CTRLR-CALL-STATS-MIB/cisco-sess:csbCallStatsInstanceTable/cisco-sess:csbCallStatsInstanceEntry/cisco-sess:csbCallStatsInstanceIndex";
          }
        }

        leaf csbCallStatsServiceIndex {
          type leafref {
            path "/cisco-sess:CISCO-SESS-BORDER-CTRLR-CALL-STATS-MIB/cisco-sess:csbCallStatsTable/cisco-sess:csbCallStatsEntry/cisco-sess:csbCallStatsServiceIndex";
          }
        }

        leaf csbRadiusStatsEntIndex {
          type uint32;
          description
           "This object indicates the index of the RADIUS client entity
            that this server is configured on. This index is assigned 
            arbitrarily by the engine and is not saved over reboots.";
          smiv2:max-access "not-accessible";
          smiv2:oid "1.3.6.1.4.1.9.9.757.1.1.1.1";
        }

        leaf csbRadiusStatsClientName {
          type snmp-framework:SnmpAdminString;
          description
           "This object indicates the client name of the RADIUS client to
            which that these statistics apply.";
          smiv2:max-access "read-only";
          smiv2:oid "1.3.6.1.4.1.9.9.757.1.1.1.2";
        }

        leaf csbRadiusStatsClientType {
          type CISCO-SESS-BORDER-CTRLR-STATS-MIB:CiscoSbcRadiusClientType;
          description
           "This object indicates the type(authentication or accounting)
            of the RADIUS clients configured on SBC.";
          smiv2:max-access "read-only";
          smiv2:oid "1.3.6.1.4.1.9.9.757.1.1.1.3";
        }

        leaf csbRadiusStatsSrvrName {
          type snmp-framework:SnmpAdminString;
          description
           "This object indicates the server name of the RADIUS server to
            which that these statistics apply.";
          smiv2:max-access "read-only";
          smiv2:oid "1.3.6.1.4.1.9.9.757.1.1.1.4";
        }

        leaf csbRadiusStatsAcsReqs {
          type yang:counter64;
          units "packets";
          description
           "This object indicates the number of RADIUS Access-Request
            packets sent to this server.  This does not include
            retransmissions.";
          smiv2:max-access "read-only";
          smiv2:oid "1.3.6.1.4.1.9.9.757.1.1.1.5";
        }

        leaf csbRadiusStatsAcsRtrns {
          type yang:counter64;
          units "packets";
          description
           "This object indicates the number of RADIUS Access-Request
            packets retransmitted to this RADIUS server.";
          smiv2:max-access "read-only";
          smiv2:oid "1.3.6.1.4.1.9.9.757.1.1.1.6";
        }

        leaf csbRadiusStatsAcsAccpts {
          type yang:counter64;
          description
           "This object indicates the number of RADIUS Access-Accept
            packets (valid or invalid) received from this server.";
          smiv2:max-access "read-only";
          smiv2:oid "1.3.6.1.4.1.9.9.757.1.1.1.7";
        }

        leaf csbRadiusStatsAcsRejects {
          type yang:counter64;
          units "packets";
          description
           "This object indicates the number of RADIUS Access-Reject
            packets (valid or invalid) received from this server.";
          smiv2:max-access "read-only";
          smiv2:oid "1.3.6.1.4.1.9.9.757.1.1.1.8";
        }

        leaf csbRadiusStatsAcsChalls {
          type yang:counter64;
          units "packets";
          description
           "This object indicates the number of RADIUS Access-Challenge
            packets (valid or invalid) received from this server.";
          smiv2:max-access "read-only";
          smiv2:oid "1.3.6.1.4.1.9.9.757.1.1.1.9";
        }

        leaf csbRadiusStatsActReqs {
          type yang:counter64;
          units "packets";
          description
           "This object indicates the number of RADIUS Accounting-Request
            packets sent to this server. This does not include
            retransmissions.";
          smiv2:max-access "read-only";
          smiv2:oid "1.3.6.1.4.1.9.9.757.1.1.1.10";
        }

        leaf csbRadiusStatsActRetrans {
          type yang:counter64;
          units "packets";
          description
           "This object indicates the number of RADIUS Accounting-Request
            packets retransmitted to this RADIUS server.";
          smiv2:max-access "read-only";
          smiv2:oid "1.3.6.1.4.1.9.9.757.1.1.1.11";
        }

        leaf csbRadiusStatsActRsps {
          type yang:counter64;
          units "packets";
          description
           "This object indicates the number of RADIUS Accounting-Response
            packets (valid or invalid) received from this server.";
          smiv2:max-access "read-only";
          smiv2:oid "1.3.6.1.4.1.9.9.757.1.1.1.12";
        }

        leaf csbRadiusStatsMalformedRsps {
          type yang:counter64;
          units "packets";
          description
           "This object indicates the number of malformed RADIUS response
            packets received from this server.  Malformed packets include
            packets with an invalid length. Bad authenticators, Signature
            attributes and unknown types are not included as malformed
            access responses.";
          smiv2:max-access "read-only";
          smiv2:oid "1.3.6.1.4.1.9.9.757.1.1.1.13";
        }

        leaf csbRadiusStatsBadAuths {
          type yang:counter64;
          units "packets";
          description
           "This object indicates the number of RADIUS response packets
            containing invalid authenticators or Signature attributes
            received from this server.";
          smiv2:max-access "read-only";
          smiv2:oid "1.3.6.1.4.1.9.9.757.1.1.1.14";
        }

        leaf csbRadiusStatsPending {
          type yang:gauge32;
          units "packets";
          description
           "This object indicates the number of RADIUS request packets
            destined for this server that have not yet timed out or received
            a response. This variable is incremented when a request is sent
            and decremented on receipt of the response or on a timeout or
            retransmission.";
          smiv2:max-access "read-only";
          smiv2:oid "1.3.6.1.4.1.9.9.757.1.1.1.15";
        }

        leaf csbRadiusStatsTimeouts {
          type yang:counter64;
          units "packets";
          description
           "This object indicates the number of RADIUS request timeouts to
            this server.  After a timeout the client may retry to a
            different server or give up. A retry to a different server is
            counted as a request as well as a timeout.";
          smiv2:max-access "read-only";
          smiv2:oid "1.3.6.1.4.1.9.9.757.1.1.1.16";
        }

        leaf csbRadiusStatsUnknownType {
          type yang:counter64;
          units "packets";
          description
           "This object indicates the number of RADIUS packets of unknown
            type which were received from this server.";
          smiv2:max-access "read-only";
          smiv2:oid "1.3.6.1.4.1.9.9.757.1.1.1.17";
        }

        leaf csbRadiusStatsDropped {
          type yang:counter64;
          units "packets";
          description
           "This object indicates the number of RADIUS packets which were
            received from this server and dropped for some other reason.";
          smiv2:max-access "read-only";
          smiv2:oid "1.3.6.1.4.1.9.9.757.1.1.1.18";
        }
      }
    }

    container csbRfBillRealmStatsTable {
      description
       "This table describes the Rf billing statistics information
        which monitors the messages sent per-realm by Rf billing 
        manager(SBC). SBC sends Rf billing data using Diameter as a
        transport protocol. Rf billing uses only ACR and ACA Diameter
        messages for the transport of billing data. The
        Accounting-Record-Type AVP on the ACR message labels the type 
        of the accounting request. The following types are used by Rf
        billing.
        1.   For session-based charging, the types Start (session
        begins), Interim (session is modified) and Stop (session ends)
        are used.
        2.   For event-based charging, the type Event is used when a
        chargeable event occurs outside the scope of a session.
        
        Each row of this table is identified by a value of
        csbRfBillRealmStatsIndex and csbRfBillRealmStatsRealmName.
        The other indices of this table are csbCallStatsInstanceIndex
        defined in csbCallStatsInstanceTable and 
        csbCallStatsServiceIndex defined in csbCallStatsTable.";
      smiv2:oid "1.3.6.1.4.1.9.9.757.1.2";

      list csbRfBillRealmStatsEntry {
        key "csbCallStatsInstanceIndex csbCallStatsServiceIndex csbRfBillRealmStatsIndex csbRfBillRealmStatsRealmName";
        description
         "A conceptual row in the csbRfBillRealmStatsTable. There
          is an entry in this table for each realm, as identified by a 
          value of csbRfBillRealmStatsIndex and 
          csbRfBillRealmStatsRealmName. The other indices of this
          table are csbCallStatsInstanceIndex defined in
          csbCallStatsInstanceTable and csbCallStatsServiceIndex defined
          in csbCallStatsTable.";
        smiv2:oid "1.3.6.1.4.1.9.9.757.1.2.1";

        leaf csbCallStatsInstanceIndex {
          type leafref {
            path "/cisco-sess:CISCO-SESS-BORDER-CTRLR-CALL-STATS-MIB/cisco-sess:csbCallStatsInstanceTable/cisco-sess:csbCallStatsInstanceEntry/cisco-sess:csbCallStatsInstanceIndex";
          }
        }

        leaf csbCallStatsServiceIndex {
          type leafref {
            path "/cisco-sess:CISCO-SESS-BORDER-CTRLR-CALL-STATS-MIB/cisco-sess:csbCallStatsTable/cisco-sess:csbCallStatsEntry/cisco-sess:csbCallStatsServiceIndex";
          }
        }

        leaf csbRfBillRealmStatsIndex {
          type uint32 {
            range "0..31";
          }
          description
           "This object indicates the billing method instance index. The
            range of valid values for this field is 0 - 31.";
          smiv2:max-access "not-accessible";
          smiv2:oid "1.3.6.1.4.1.9.9.757.1.2.1.1";
        }

        leaf csbRfBillRealmStatsRealmName {
          type snmp-framework:SnmpAdminString;
          description
           "This object indicates the realm for which these statistics are
            collected. The length of this object is zero when value is not
            assigned to it.";
          smiv2:max-access "read-only";
          smiv2:oid "1.3.6.1.4.1.9.9.757.1.2.1.2";
        }

        leaf csbRfBillRealmStatsTotalStartAcrs {
          type uint32;
          units "ACRs";
          description
           "This object indicates the combined sum of successful and failed
            Start ACRs since start of day or the last time the statistics
            were reset.";
          smiv2:max-access "read-only";
          smiv2:oid "1.3.6.1.4.1.9.9.757.1.2.1.3";
        }

        leaf csbRfBillRealmStatsTotalInterimAcrs {
          type uint32;
          units "ACRs";
          description
           "This object indicates the combined sum of successful and failed
            Interim ACRs since start of day or the last time the statistics
            were reset.";
          smiv2:max-access "read-only";
          smiv2:oid "1.3.6.1.4.1.9.9.757.1.2.1.4";
        }

        leaf csbRfBillRealmStatsTotalStopAcrs {
          type uint32;
          units "ACRs";
          description
           "This object indicates the combined sum of successful and failed
            Stop ACRs since start of day or the last time the statistics
            were reset.";
          smiv2:max-access "read-only";
          smiv2:oid "1.3.6.1.4.1.9.9.757.1.2.1.5";
        }

        leaf csbRfBillRealmStatsTotalEventAcrs {
          type uint32;
          units "ACRs";
          description
           "This object indicates the combined sum of successful and failed
            Event ACRs since start of day or the last time the statistics
            were reset.";
          smiv2:max-access "read-only";
          smiv2:oid "1.3.6.1.4.1.9.9.757.1.2.1.6";
        }

        leaf csbRfBillRealmStatsSuccStartAcrs {
          type uint32;
          units "ACRs";
          description
           "This object indicates the total number of successful Start ACRs
            since start of day or the last time the statistics were reset.";
          smiv2:max-access "read-only";
          smiv2:oid "1.3.6.1.4.1.9.9.757.1.2.1.7";
        }

        leaf csbRfBillRealmStatsSuccInterimAcrs {
          type uint32;
          units "ACRs";
          description
           "This object indicates the total number of successful Interim
            ACRs since start of day or the last time the statistics were
            reset.";
          smiv2:max-access "read-only";
          smiv2:oid "1.3.6.1.4.1.9.9.757.1.2.1.8";
        }

        leaf csbRfBillRealmStatsSuccStopAcrs {
          type uint32;
          units "ACRs";
          description
           "This object indicates the total number of successful Stop ACRs
            since start of day or the last time the statistics were reset.";
          smiv2:max-access "read-only";
          smiv2:oid "1.3.6.1.4.1.9.9.757.1.2.1.9";
        }

        leaf csbRfBillRealmStatsSuccEventAcrs {
          type uint32;
          units "ACRs";
          description
           "This object indicates the total number of successful Event ACRs
            since start of day or the last time the statistics were reset.";
          smiv2:max-access "read-only";
          smiv2:oid "1.3.6.1.4.1.9.9.757.1.2.1.10";
        }

        leaf csbRfBillRealmStatsFailStartAcrs {
          type uint32;
          units "ACRs";
          description
           "This object indicates the total number of failed Start ACRs
            since start of day or the last time the statistics were reset.";
          smiv2:max-access "read-only";
          smiv2:oid "1.3.6.1.4.1.9.9.757.1.2.1.11";
        }

        leaf csbRfBillRealmStatsFailInterimAcrs {
          type uint32;
          units "ACRs";
          description
           "This object indicates the total number of failed Interim ACRs
            since start of day or the last time the statistics were reset.";
          smiv2:max-access "read-only";
          smiv2:oid "1.3.6.1.4.1.9.9.757.1.2.1.12";
        }

        leaf csbRfBillRealmStatsFailStopAcrs {
          type uint32;
          units "ACRs";
          description
           "This object indicates the total number of failed Stop ACRs
            since start of day or the last time the statistics were reset.";
          smiv2:max-access "read-only";
          smiv2:oid "1.3.6.1.4.1.9.9.757.1.2.1.13";
        }

        leaf csbRfBillRealmStatsFailEventAcrs {
          type uint32;
          units "ACRs";
          description
           "This object indicates the total number of failed Event ACRs
            since start of day or the last time the statistics were reset.";
          smiv2:max-access "read-only";
          smiv2:oid "1.3.6.1.4.1.9.9.757.1.2.1.14";
        }
      }
    }

    container csbSIPMthdCurrentStatsTable {
      description
       "This table reports count of SIP request and various SIP
        responses  for each SIP method on a SIP adjacency in a given
        interval. Each entry in this table represents a SIP method, its
        incoming and outgoing count, individual incoming and outgoing 
        count of various SIP responses for this method on a SIP
        adjacency in a given interval. To understand the meaning of 
        interval please refer <Periodic Statistics> section in 
        description of ciscoSbcStatsMIB.  
        This table is indexed on csbSIPMthdCurrentStatsAdjName,
        csbSIPMthdCurrentStatsMethod and 
        csbSIPMthdCurrentStatsInterval. The other indices of this
        table are csbCallStatsInstanceIndex defined in 
        csbCallStatsInstanceTable and csbCallStatsServiceIndex defined
        in csbCallStatsTable.";
      smiv2:oid "1.3.6.1.4.1.9.9.757.1.3";

      list csbSIPMthdCurrentStatsEntry {
        key "csbCallStatsInstanceIndex csbCallStatsServiceIndex csbSIPMthdCurrentStatsAdjName csbSIPMthdCurrentStatsMethod csbSIPMthdCurrentStatsInterval";
        description
         "A conceptual row in the csbSIPMthdCurrentStatsTable. Each row
          describes a SIP method and various responses count for this
          method on a given SIP adjacency and given interval. This table
          is indexed on csbSIPMthdCurrentStatsAdjName,
          csbSIPMthdCurrentStatsMethod and 
          csbSIPMthdCurrentStatsInterval. The other indices of this
          table are csbCallStatsInstanceIndex defined in 
          csbCallStatsInstanceTable and csbCallStatsServiceIndex defined
          in csbCallStatsTable.";
        smiv2:oid "1.3.6.1.4.1.9.9.757.1.3.1";

        leaf csbCallStatsInstanceIndex {
          type leafref {
            path "/cisco-sess:CISCO-SESS-BORDER-CTRLR-CALL-STATS-MIB/cisco-sess:csbCallStatsInstanceTable/cisco-sess:csbCallStatsInstanceEntry/cisco-sess:csbCallStatsInstanceIndex";
          }
        }

        leaf csbCallStatsServiceIndex {
          type leafref {
            path "/cisco-sess:CISCO-SESS-BORDER-CTRLR-CALL-STATS-MIB/cisco-sess:csbCallStatsTable/cisco-sess:csbCallStatsEntry/cisco-sess:csbCallStatsServiceIndex";
          }
        }

        leaf csbSIPMthdCurrentStatsAdjName {
          type snmp-framework:SnmpAdminString;
          description
           "This object indicates the name of the SIP adjacency for which
            stats related with SIP request and all kind of corresponding SIP
            responses are reported. The object acts as an index of the
            table.";
          smiv2:max-access "read-only";
          smiv2:oid "1.3.6.1.4.1.9.9.757.1.3.1.1";
        }

        leaf csbSIPMthdCurrentStatsMethod {
          type CISCO-SESS-BORDER-CTRLR-STATS-MIB:CiscoSbcSIPMethod;
          description
           "This object indicates the SIP method Request. The object acts
            as an index of the table.";
          smiv2:max-access "not-accessible";
          smiv2:oid "1.3.6.1.4.1.9.9.757.1.3.1.2";
        }

        leaf csbSIPMthdCurrentStatsInterval {
          type cisco-sess:CiscoSbcPeriodicStatsInterval;
          description
           "This object indicates the interval for which the periodic
            statistics information is to be displayed. The interval
            values can be 5 minutes, 15 minutes, 1 hour , 1 Day. This 
            object acts as an index for the table.";
          smiv2:max-access "not-accessible";
          smiv2:oid "1.3.6.1.4.1.9.9.757.1.3.1.3";
        }

        leaf csbSIPMthdCurrentStatsMethodName {
          type snmp-framework:SnmpAdminString;
          description
           "This object indicates the text representation of the SIP
            method request. E.g. INVITE, ACK, BYE etc.";
          smiv2:max-access "read-only";
          smiv2:oid "1.3.6.1.4.1.9.9.757.1.3.1.4";
        }

        leaf csbSIPMthdCurrentStatsReqIn {
          type yang:gauge32;
          units "requests";
          description
           "This object indicates the total incoming SIP message requests
            of this type on this SIP adjacency.";
          smiv2:max-access "read-only";
          smiv2:oid "1.3.6.1.4.1.9.9.757.1.3.1.5";
        }

        leaf csbSIPMthdCurrentStatsReqOut {
          type yang:gauge32;
          units "requests";
          description
           "This object indicates the total outgoing SIP message requests
            of this type on this SIP adjacency.";
          smiv2:max-access "read-only";
          smiv2:oid "1.3.6.1.4.1.9.9.757.1.3.1.6";
        }

        leaf csbSIPMthdCurrentStatsResp1xxIn {
          type yang:gauge32;
          units "responses";
          description
           "This object indicates the total 1xx responses for this method
            received on this SIP adjacency.";
          smiv2:max-access "read-only";
          smiv2:oid "1.3.6.1.4.1.9.9.757.1.3.1.7";
        }

        leaf csbSIPMthdCurrentStatsResp1xxOut {
          type yang:gauge32;
          units "responses";
          description
           "This object indicates the total 1xx responses for this method
            sent on this SIP adjacency.";
          smiv2:max-access "read-only";
          smiv2:oid "1.3.6.1.4.1.9.9.757.1.3.1.8";
        }

        leaf csbSIPMthdCurrentStatsResp2xxIn {
          type yang:gauge32;
          units "responses";
          description
           "This object indicates the total 2xx responses for this method
            received on this SIP adjacency.";
          smiv2:max-access "read-only";
          smiv2:oid "1.3.6.1.4.1.9.9.757.1.3.1.9";
        }

        leaf csbSIPMthdCurrentStatsResp2xxOut {
          type yang:gauge32;
          units "responses";
          description
           "This object indicates the total 2xx responses for this method
            sent on this SIP adjacency.";
          smiv2:max-access "read-only";
          smiv2:oid "1.3.6.1.4.1.9.9.757.1.3.1.10";
        }

        leaf csbSIPMthdCurrentStatsResp3xxIn {
          type yang:gauge32;
          units "responses";
          description
           "This object indicates the total 3xx responses for this method
            received on this SIP adjacency.";
          smiv2:max-access "read-only";
          smiv2:oid "1.3.6.1.4.1.9.9.757.1.3.1.11";
        }

        leaf csbSIPMthdCurrentStatsResp3xxOut {
          type yang:gauge32;
          units "responses";
          description
           "This object indicates the total 3xx responses for this method
            sent on this SIP adjacency.";
          smiv2:max-access "read-only";
          smiv2:oid "1.3.6.1.4.1.9.9.757.1.3.1.12";
        }

        leaf csbSIPMthdCurrentStatsResp4xxIn {
          type yang:gauge32;
          units "responses";
          description
           "This object indicates the total 4xx responses for this method
            received on this SIP adjacency.";
          smiv2:max-access "read-only";
          smiv2:oid "1.3.6.1.4.1.9.9.757.1.3.1.13";
        }

        leaf csbSIPMthdCurrentStatsResp4xxOut {
          type yang:gauge32;
          units "responses";
          description
           "This object indicates the total 4xx responses for this method
            sent on this SIP adjacency.";
          smiv2:max-access "read-only";
          smiv2:oid "1.3.6.1.4.1.9.9.757.1.3.1.14";
        }

        leaf csbSIPMthdCurrentStatsResp5xxIn {
          type yang:gauge32;
          units "responses";
          description
           "This object indicates the total 5xx responses for this method
            received on this SIP adjacency.";
          smiv2:max-access "read-only";
          smiv2:oid "1.3.6.1.4.1.9.9.757.1.3.1.15";
        }

        leaf csbSIPMthdCurrentStatsResp5xxOut {
          type yang:gauge32;
          units "responses";
          description
           "This object indicates the total 5xx responses for this method
            sent on this SIP adjacency.";
          smiv2:max-access "read-only";
          smiv2:oid "1.3.6.1.4.1.9.9.757.1.3.1.16";
        }

        leaf csbSIPMthdCurrentStatsResp6xxIn {
          type yang:gauge32;
          units "responses";
          description
           "This object indicates the total 6xx responses for this method
            received on this SIP adjacency.";
          smiv2:max-access "read-only";
          smiv2:oid "1.3.6.1.4.1.9.9.757.1.3.1.17";
        }

        leaf csbSIPMthdCurrentStatsResp6xxOut {
          type yang:gauge32;
          units "responses";
          description
           "This object indicates the total 6xx responses for this method
            sent on this SIP adjacency.";
          smiv2:max-access "read-only";
          smiv2:oid "1.3.6.1.4.1.9.9.757.1.3.1.18";
        }
      }
    }

    container csbSIPMthdHistoryStatsTable {
      description
       "This table provide historical count of SIP request and various
        SIP responses for each SIP method on a SIP adjacency in various
        interval length defined by the csbSIPMthdHistoryStatsInterval
        object. Each entry in this table represents a SIP method, its
        incoming and outgoing count, individual incoming and outgoing 
        count of various SIP responses for this method on a SIP
        adjacency in a given interval. The possible values of interval
        will be previous 5 minutes, previous 15 minutes, previous 1 hour
        and previous day. To understand the meaning of interval please
        refer <Periodic Statistics> description of ciscoSbcStatsMIB.
        This table is indexed on csbSIPMthdHistoryStatsAdjName,
        csbSIPMthdHistoryStatsMethod and 
        csbSIPMthdHistoryStatsInterval. The other indices of this
        table are csbCallStatsInstanceIndex defined in 
        csbCallStatsInstanceTable and csbCallStatsServiceIndex defined
        in csbCallStatsTable.";
      smiv2:oid "1.3.6.1.4.1.9.9.757.1.4";

      list csbSIPMthdHistoryStatsEntry {
        key "csbCallStatsInstanceIndex csbCallStatsServiceIndex csbSIPMthdHistoryStatsAdjName csbSIPMthdHistoryStatsMethod csbSIPMthdHistoryStatsInterval";
        description
         "A conceptual row in the csbSIPMthdHistoryStatsTable. The
          entries in this table are updated as interval completes in
          the csbSIPMthdCurrentStatsTable table and the data is 
          moved from that table to this one.
          This table is indexed on csbSIPMthdHistoryStatsAdjName,
          csbSIPMthdHistoryStatsMethod and
          csbSIPMthdHistoryStatsInterval. The other indices of this 
          table are csbCallStatsInstanceIndex defined in
          csbCallStatsInstanceTable and csbCallStatsServiceIndex
          defined in csbCallStatsTable.";
        smiv2:oid "1.3.6.1.4.1.9.9.757.1.4.1";

        leaf csbCallStatsInstanceIndex {
          type leafref {
            path "/cisco-sess:CISCO-SESS-BORDER-CTRLR-CALL-STATS-MIB/cisco-sess:csbCallStatsInstanceTable/cisco-sess:csbCallStatsInstanceEntry/cisco-sess:csbCallStatsInstanceIndex";
          }
        }

        leaf csbCallStatsServiceIndex {
          type leafref {
            path "/cisco-sess:CISCO-SESS-BORDER-CTRLR-CALL-STATS-MIB/cisco-sess:csbCallStatsTable/cisco-sess:csbCallStatsEntry/cisco-sess:csbCallStatsServiceIndex";
          }
        }

        leaf csbSIPMthdHistoryStatsAdjName {
          type snmp-framework:SnmpAdminString;
          description
           "This object indicates the name of the SIP adjacency for which
            stats related with SIP request and all kind of corresponding SIP
            responses are reported. The object acts as an index of the
            table.";
          smiv2:max-access "read-only";
          smiv2:oid "1.3.6.1.4.1.9.9.757.1.4.1.1";
        }

        leaf csbSIPMthdHistoryStatsMethod {
          type CISCO-SESS-BORDER-CTRLR-STATS-MIB:CiscoSbcSIPMethod;
          description
           "This object indicates the SIP method Request. The object acts
            as an index of the table.";
          smiv2:max-access "not-accessible";
          smiv2:oid "1.3.6.1.4.1.9.9.757.1.4.1.2";
        }

        leaf csbSIPMthdHistoryStatsInterval {
          type cisco-sess:CiscoSbcPeriodicStatsInterval;
          description
           "This object indicates the interval for which the historical
            statistics information is to be displayed. The interval
            values can be previous 5 minutes, previous 15 minutes, 
            previous 1 hour and previous 1 Day. This object acts as an 
            index for the table.";
          smiv2:max-access "not-accessible";
          smiv2:oid "1.3.6.1.4.1.9.9.757.1.4.1.3";
        }

        leaf csbSIPMthdHistoryStatsMethodName {
          type snmp-framework:SnmpAdminString;
          description
           "This object indicates the text representation of the SIP
            method request. E.g. INVITE, ACK, BYE etc.";
          smiv2:max-access "read-only";
          smiv2:oid "1.3.6.1.4.1.9.9.757.1.4.1.4";
        }

        leaf csbSIPMthdHistoryStatsReqIn {
          type yang:gauge32;
          units "requests";
          description
           "This object indicates the total incoming SIP message requests
            of this type on this SIP adjacency.";
          smiv2:max-access "read-only";
          smiv2:oid "1.3.6.1.4.1.9.9.757.1.4.1.5";
        }

        leaf csbSIPMthdHistoryStatsReqOut {
          type yang:gauge32;
          units "requests";
          description
           "This object indicates the total outgoing SIP message requests
            of this type on this SIP adjacency.";
          smiv2:max-access "read-only";
          smiv2:oid "1.3.6.1.4.1.9.9.757.1.4.1.6";
        }

        leaf csbSIPMthdHistoryStatsResp1xxIn {
          type yang:gauge32;
          units "responses";
          description
           "This object indicates the total 1xx responses for this method
            received on this SIP adjacency.";
          smiv2:max-access "read-only";
          smiv2:oid "1.3.6.1.4.1.9.9.757.1.4.1.7";
        }

        leaf csbSIPMthdHistoryStatsResp1xxOut {
          type yang:gauge32;
          units "responses";
          description
           "This object indicates the total 1xx responses for this method
            sent on this SIP adjacency.";
          smiv2:max-access "read-only";
          smiv2:oid "1.3.6.1.4.1.9.9.757.1.4.1.8";
        }

        leaf csbSIPMthdHistoryStatsResp2xxIn {
          type yang:gauge32;
          units "responses";
          description
           "This object indicates the total 2xx responses for this method
            received on this SIP adjacency.";
          smiv2:max-access "read-only";
          smiv2:oid "1.3.6.1.4.1.9.9.757.1.4.1.9";
        }

        leaf csbSIPMthdHistoryStatsResp2xxOut {
          type yang:gauge32;
          units "responses";
          description
           "This object indicates the total 2xx responses for this method
            sent on this SIP adjacency.";
          smiv2:max-access "read-only";
          smiv2:oid "1.3.6.1.4.1.9.9.757.1.4.1.10";
        }

        leaf csbSIPMthdHistoryStatsResp3xxIn {
          type yang:gauge32;
          units "responses";
          description
           "This object indicates the total 3xx responses for this method
            received on this SIP adjacency.";
          smiv2:max-access "read-only";
          smiv2:oid "1.3.6.1.4.1.9.9.757.1.4.1.11";
        }

        leaf csbSIPMthdHistoryStatsResp3xxOut {
          type yang:gauge32;
          units "responses";
          description
           "This object indicates the total 3xx responses for this method
            sent on this SIP adjacency.";
          smiv2:max-access "read-only";
          smiv2:oid "1.3.6.1.4.1.9.9.757.1.4.1.12";
        }

        leaf csbSIPMthdHistoryStatsResp4xxIn {
          type yang:gauge32;
          units "responses";
          description
           "This object indicates the total 4xx responses for this method
            received on this SIP adjacency.";
          smiv2:max-access "read-only";
          smiv2:oid "1.3.6.1.4.1.9.9.757.1.4.1.13";
        }

        leaf csbSIPMthdHistoryStatsResp4xxOut {
          type yang:gauge32;
          units "responses";
          description
           "This object indicates the total 4xx responses for this method
            sent on this SIP adjacency.";
          smiv2:max-access "read-only";
          smiv2:oid "1.3.6.1.4.1.9.9.757.1.4.1.14";
        }

        leaf csbSIPMthdHistoryStatsResp5xxIn {
          type yang:gauge32;
          units "responses";
          description
           "This object indicates the total 5xx responses for this method
            received on this SIP adjacency.";
          smiv2:max-access "read-only";
          smiv2:oid "1.3.6.1.4.1.9.9.757.1.4.1.15";
        }

        leaf csbSIPMthdHistoryStatsResp5xxOut {
          type yang:gauge32;
          units "responses";
          description
           "This object indicates the total 5xx responses for this method
            sent on this SIP adjacency.";
          smiv2:max-access "read-only";
          smiv2:oid "1.3.6.1.4.1.9.9.757.1.4.1.16";
        }

        leaf csbSIPMthdHistoryStatsResp6xxIn {
          type yang:gauge32;
          units "responses";
          description
           "This object indicates the total 6xx responses for this method
            received on this SIP adjacency.";
          smiv2:max-access "read-only";
          smiv2:oid "1.3.6.1.4.1.9.9.757.1.4.1.17";
        }

        leaf csbSIPMthdHistoryStatsResp6xxOut {
          type yang:gauge32;
          units "responses";
          description
           "This object indicates the total 6xx responses for this method
            sent on this SIP adjacency.";
          smiv2:max-access "read-only";
          smiv2:oid "1.3.6.1.4.1.9.9.757.1.4.1.18";
        }
      }
    }

    container csbSIPMthdRCCurrentStatsTable {
      description
       "This table reports SIP method request and response code
        statistics for each method and response code combination on
        given SIP adjacency in a given interval. To understand the 
        meaning of interval please refer <Periodic Statistics> section
        in description of ciscoSbcStatsMIB. An exact lookup will return
        a row only  if -
        1) detailed response code statistics are turned on in SBC
        2) response code  messages sent or received is non zero for 
           given SIP adjacency, method and interval.
        Also an inexact lookup will only return rows for messages with
        non-zero counts, to protect the user from large numbers of rows 
        for response codes which have not been received or sent.";
      smiv2:oid "1.3.6.1.4.1.9.9.757.1.5";

      list csbSIPMthdRCCurrentStatsEntry {
        key "csbCallStatsInstanceIndex csbCallStatsServiceIndex csbSIPMthdRCCurrentStatsAdjName csbSIPMthdRCCurrentStatsMethod csbSIPMthdRCCurrentStatsRespCode csbSIPMthdRCCurrentStatsInterval";
        description
         "A conceptual row in the csbSIPMthdRCCurrentStatsTable. Each
          entry in this table represents a method and response code
          combination. Each entry in this table is identified by a value
          of csbSIPMthdRCCurrentStatsAdjName,
          csbSIPMthdRCCurrentStatsMethod,
          csbSIPMthdRCCurrentStatsRespCode and
          csbSIPMthdRCCurrentStatsInterval. The other indices of this
          table are csbCallStatsInstanceIndex defined in
          csbCallStatsInstanceTable and csbCallStatsServiceIndex defined
          in csbCallStatsTable.";
        smiv2:oid "1.3.6.1.4.1.9.9.757.1.5.1";

        leaf csbCallStatsInstanceIndex {
          type leafref {
            path "/cisco-sess:CISCO-SESS-BORDER-CTRLR-CALL-STATS-MIB/cisco-sess:csbCallStatsInstanceTable/cisco-sess:csbCallStatsInstanceEntry/cisco-sess:csbCallStatsInstanceIndex";
          }
        }

        leaf csbCallStatsServiceIndex {
          type leafref {
            path "/cisco-sess:CISCO-SESS-BORDER-CTRLR-CALL-STATS-MIB/cisco-sess:csbCallStatsTable/cisco-sess:csbCallStatsEntry/cisco-sess:csbCallStatsServiceIndex";
          }
        }

        leaf csbSIPMthdRCCurrentStatsAdjName {
          type snmp-framework:SnmpAdminString;
          description
           "This identifies the name of the adjacency for which statistics
            are reported. This object acts as an index for the table.";
          smiv2:max-access "read-only";
          smiv2:oid "1.3.6.1.4.1.9.9.757.1.5.1.1";
        }

        leaf csbSIPMthdRCCurrentStatsMethod {
          type CISCO-SESS-BORDER-CTRLR-STATS-MIB:CiscoSbcSIPMethod;
          description
           "This object indicates the SIP method request. This object acts
            as an index for the table.";
          smiv2:max-access "not-accessible";
          smiv2:oid "1.3.6.1.4.1.9.9.757.1.5.1.2";
        }

        leaf csbSIPMthdRCCurrentStatsRespCode {
          type uint32;
          description
           "This object indicates the response code for the SIP message
            request. The range of valid values for SIP response codes is 100
            - 999. This object acts as an index for the table.";
          smiv2:max-access "not-accessible";
          smiv2:oid "1.3.6.1.4.1.9.9.757.1.5.1.3";
        }

        leaf csbSIPMthdRCCurrentStatsInterval {
          type cisco-sess:CiscoSbcPeriodicStatsInterval;
          description
           "This object identifies the interval for which the periodic
            statistics information is to be displayed. The interval
            values can be 5 min, 15 mins, 1 hour , 1 Day. This object acts
            as an index for the table.";
          smiv2:max-access "not-accessible";
          smiv2:oid "1.3.6.1.4.1.9.9.757.1.5.1.4";
        }

        leaf csbSIPMthdRCCurrentStatsMethodName {
          type snmp-framework:SnmpAdminString;
          description
           "This object indicates the text representation of the SIP
            method request. E.g. INVITE, ACK, BYE etc.";
          smiv2:max-access "read-only";
          smiv2:oid "1.3.6.1.4.1.9.9.757.1.5.1.5";
        }

        leaf csbSIPMthdRCCurrentStatsRespIn {
          type yang:gauge32;
          units "responses";
          description
           "This object indicates the total SIP messages with this response
            code this method received on this SIP adjacency.";
          smiv2:max-access "read-only";
          smiv2:oid "1.3.6.1.4.1.9.9.757.1.5.1.6";
        }

        leaf csbSIPMthdRCCurrentStatsRespOut {
          type yang:gauge32;
          units "responses";
          description
           "This object indicates the total SIP messages with this response
            code for this method sent on this SIP adjacency.";
          smiv2:max-access "read-only";
          smiv2:oid "1.3.6.1.4.1.9.9.757.1.5.1.7";
        }
      }
    }

    container csbSIPMthdRCHistoryStatsTable {
      description
       "This table reports historical data for SIP method request and
        response code statistics for each method and response code 
        combination in a given past interval. The possible values of 
        interval will be previous 5 minutes, previous 15 minutes, 
        previous 1 hour and previous day. To understand the 
        meaning of interval please refer <Periodic Statistics> section
        in description of ciscoSbcStatsMIB. An exact lookup will return
        a row only  if -
        1) detailed response code statistics are turned on in SBC
        2) response code  messages sent or received is non zero for 
           given SIP adjacency, method and interval.
        Also an inexact lookup will only return rows for messages with
        non-zero counts, to protect the user from large numbers of rows
        for response codes which have not been received or sent.";
      smiv2:oid "1.3.6.1.4.1.9.9.757.1.6";

      list csbSIPMthdRCHistoryStatsEntry {
        key "csbCallStatsInstanceIndex csbCallStatsServiceIndex csbSIPMthdRCHistoryStatsAdjName csbSIPMthdRCHistoryStatsMethod csbSIPMthdRCHistoryStatsRespCode csbSIPMthdRCHistoryStatsInterval";
        description
         "A conceptual row in the csbSIPMthdRCHistoryStatsTable. The
          entries in this table are updated as interval completes in
          the csbSIPMthdRCCurrentStatsTable table and the data is 
          moved from that table to this one. Each entry in this table 
          is identified by a value of csbSIPMthdRCHistoryStatsAdjName, 
          csbSIPMthdRCHistoryStatsMethod,
          csbSIPMthdRCHistoryStatsRespCode and
          csbSIPMthdRCHistoryStatsInterval. The other indices of this
          table are csbCallStatsInstanceIndex defined in
          csbCallStatsInstanceTable and csbCallStatsServiceIndex defined
          in csbCallStatsTable.";
        smiv2:oid "1.3.6.1.4.1.9.9.757.1.6.1";

        leaf csbCallStatsInstanceIndex {
          type leafref {
            path "/cisco-sess:CISCO-SESS-BORDER-CTRLR-CALL-STATS-MIB/cisco-sess:csbCallStatsInstanceTable/cisco-sess:csbCallStatsInstanceEntry/cisco-sess:csbCallStatsInstanceIndex";
          }
        }

        leaf csbCallStatsServiceIndex {
          type leafref {
            path "/cisco-sess:CISCO-SESS-BORDER-CTRLR-CALL-STATS-MIB/cisco-sess:csbCallStatsTable/cisco-sess:csbCallStatsEntry/cisco-sess:csbCallStatsServiceIndex";
          }
        }

        leaf csbSIPMthdRCHistoryStatsAdjName {
          type snmp-framework:SnmpAdminString;
          description
           "This identifies the name of the adjacency for which statistics
            are reported. This object acts as an index for the table.";
          smiv2:max-access "read-only";
          smiv2:oid "1.3.6.1.4.1.9.9.757.1.6.1.1";
        }

        leaf csbSIPMthdRCHistoryStatsMethod {
          type CISCO-SESS-BORDER-CTRLR-STATS-MIB:CiscoSbcSIPMethod;
          description
           "This object indicates the SIP method request. This object acts
            as an index for the table.";
          smiv2:max-access "not-accessible";
          smiv2:oid "1.3.6.1.4.1.9.9.757.1.6.1.2";
        }

        leaf csbSIPMthdRCHistoryStatsMethodName {
          type snmp-framework:SnmpAdminString;
          description
           "This object indicates the text representation of the SIP
            method request. E.g. INVITE, ACK, BYE etc.";
          smiv2:max-access "read-only";
          smiv2:oid "1.3.6.1.4.1.9.9.757.1.6.1.3";
        }

        leaf csbSIPMthdRCHistoryStatsRespCode {
          type uint32;
          description
           "This object indicates the response code for the SIP message
            request. The range of valid values for SIP response codes is 100
            - 999. This object acts as an index for the table.";
          smiv2:max-access "not-accessible";
          smiv2:oid "1.3.6.1.4.1.9.9.757.1.6.1.4";
        }

        leaf csbSIPMthdRCHistoryStatsInterval {
          type cisco-sess:CiscoSbcPeriodicStatsInterval;
          description
           "This object identifies the interval for which the periodic
            statistics information is to be displayed. The interval
            values can be previous 5 min, previous 15 mins, previous 1 
            hour , previous 1 Day. This object acts as an index for the
            table.";
          smiv2:max-access "not-accessible";
          smiv2:oid "1.3.6.1.4.1.9.9.757.1.6.1.5";
        }

        leaf csbSIPMthdRCHistoryStatsRespIn {
          type yang:gauge32;
          units "responses";
          description
           "This object indicates the total SIP messages with this response
            code this method received on this SIP adjacency.";
          smiv2:max-access "read-only";
          smiv2:oid "1.3.6.1.4.1.9.9.757.1.6.1.6";
        }

        leaf csbSIPMthdRCHistoryStatsRespOut {
          type yang:gauge32;
          units "responses";
          description
           "This object indicates the total SIP messages with this response
            code for this method sent on this SIP adjacency.";
          smiv2:max-access "read-only";
          smiv2:oid "1.3.6.1.4.1.9.9.757.1.6.1.7";
        }
      }
    }
  }

  smiv2:alias "ciscoSbcStatsMIB" {
    smiv2:oid "1.3.6.1.4.1.9.9.757";
  }

  smiv2:alias "ciscoSbcStatsMIBNotifs" {
    smiv2:oid "1.3.6.1.4.1.9.9.757.0";
  }

  smiv2:alias "ciscoSbcStatsMIBObjects" {
    smiv2:oid "1.3.6.1.4.1.9.9.757.1";
  }

  smiv2:alias "ciscoSbcStatsMIBConform" {
    smiv2:oid "1.3.6.1.4.1.9.9.757.2";
  }

  smiv2:alias "csbStatsMIBCompliances" {
    smiv2:oid "1.3.6.1.4.1.9.9.757.2.1";
  }

  smiv2:alias "csbStatsMIBGroups" {
    smiv2:oid "1.3.6.1.4.1.9.9.757.2.2";
  }

}
