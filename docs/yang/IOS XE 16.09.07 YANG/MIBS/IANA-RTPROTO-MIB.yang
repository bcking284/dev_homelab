/*
 * Generated by confdc --mib2yang-std
 * Source: mgmt/dmi/model/mib/src/IANA-RTPROTO-MIB.mib
 */
/*
 * This YANG module has been generated by smidump 0.5.0:
 *
 *      smidump -f yang IANA-RTPROTO-MIB
 *
 * Do not edit. Edit the source file instead!
 */

module IANA-RTPROTO-MIB {

  namespace "urn:ietf:params:xml:ns:yang:smiv2:IANA-RTPROTO-MIB";
  prefix IANA-RTPROTO-MIB;

  import ietf-yang-smiv2 {
    prefix "smiv2";
  }

  organization
   "IANA";

  contact
   " Internet Assigned Numbers Authority
    Internet Corporation for Assigned Names and Numbers
    4676 Admiralty Way, Suite 330
    Marina del Rey, CA 90292-6601
    
    Phone: +1 310 823 9358
    EMail: iana@iana.org";

  description
   "This MIB module defines the IANAipRouteProtocol and
    IANAipMRouteProtocol textual conventions for use in MIBs
    which need to identify unicast or multicast routing
    mechanisms.
    
    Any additions or changes to the contents of this MIB module
    require either publication of an RFC, or Designated Expert
    Review as defined in RFC 2434, Guidelines for Writing an
    IANA Considerations Section in RFCs.  The Designated Expert 
    will be selected by the IESG Area Director(s) of the Routing
    Area.";

  revision 2000-09-26 {
    description
     "Original version, published in coordination
      with RFC 2932.";
  }

  typedef IANAipRouteProtocol {
    type enumeration {
      enum "other" {
        value "1";
      }
      enum "local" {
        value "2";
      }
      enum "netmgmt" {
        value "3";
      }
      enum "icmp" {
        value "4";
      }
      enum "egp" {
        value "5";
      }
      enum "ggp" {
        value "6";
      }
      enum "hello" {
        value "7";
      }
      enum "rip" {
        value "8";
      }
      enum "isIs" {
        value "9";
      }
      enum "esIs" {
        value "10";
      }
      enum "ciscoIgrp" {
        value "11";
      }
      enum "bbnSpfIgp" {
        value "12";
      }
      enum "ospf" {
        value "13";
      }
      enum "bgp" {
        value "14";
      }
      enum "idpr" {
        value "15";
      }
      enum "ciscoEigrp" {
        value "16";
      }
      enum "dvmrp" {
        value "17";
      }
    }
    description
     "A mechanism for learning routes.  Inclusion of values for
      routing protocols is not intended to imply that those
      protocols need be supported.";
  }

  typedef IANAipMRouteProtocol {
    type enumeration {
      enum "other" {
        value "1";
      }
      enum "local" {
        value "2";
      }
      enum "netmgmt" {
        value "3";
      }
      enum "dvmrp" {
        value "4";
      }
      enum "mospf" {
        value "5";
      }
      enum "pimSparseDense" {
        value "6";
      }
      enum "cbt" {
        value "7";
      }
      enum "pimSparseMode" {
        value "8";
      }
      enum "pimDenseMode" {
        value "9";
      }
      enum "igmpOnly" {
        value "10";
      }
      enum "bgmp" {
        value "11";
      }
      enum "msdp" {
        value "12";
      }
    }
    description
     "The multicast routing protocol.  Inclusion of values for
      multicast routing protocols is not intended to imply that
      those protocols need be supported.";
  }

  smiv2:alias "ianaRtProtoMIB" {
    smiv2:oid "1.3.6.1.2.1.84";
  }

}
