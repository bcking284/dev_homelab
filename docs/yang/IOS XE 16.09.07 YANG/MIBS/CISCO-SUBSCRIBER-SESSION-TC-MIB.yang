/*
 * Generated by confdc --mib2yang-std
 * Source: mgmt/dmi/model/mib/src/CISCO-SUBSCRIBER-SESSION-TC-MIB.mib
 */
/*
 * This YANG module has been generated by smidump 0.5.0:
 *
 *      smidump -f yang CISCO-SUBSCRIBER-SESSION-TC-MIB
 *
 * Do not edit. Edit the source file instead!
 */

module CISCO-SUBSCRIBER-SESSION-TC-MIB {

  namespace "urn:ietf:params:xml:ns:yang:smiv2:CISCO-SUBSCRIBER-SESSION-TC-MIB";
  prefix CISCO-SUBSCRIBER-SESSION-TC-MIB;

  import ietf-yang-smiv2 {
    prefix "smiv2";
  }

  organization
   "Cisco Systems, Inc.";

  contact
   "Cisco Systems
    Customer Service
    
    Postal: 170 W Tasman Drive
    San Jose, CA 95134
    
    Tel: +1 800 553-NETS
    
    E-mail: cs-snmp@cisco.com";

  description
   "This MIB module defines textual conventions describing
    subscriber sessions.";

  revision 2012-01-27 {
    description
     "[Revision added by libsmi due to a LAST-UPDATED clause.]";
  }

  revision 2007-09-26 {
    description
     "The initial version of the MIB module.";
  }

  typedef SubSessionType {
    type enumeration {
      enum "all" {
        value "1";
      }
      enum "other" {
        value "2";
      }
      enum "pppSubscriber" {
        value "3";
      }
      enum "pppoeSubscriber" {
        value "4";
      }
      enum "l2tpSubscriber" {
        value "5";
      }
      enum "l2fSubscriber" {
        value "6";
      }
      enum "ipInterfaceSubscriber" {
        value "7";
      }
      enum "ipPktSubscriber" {
        value "8";
      }
      enum "ipDhcpv4Subscriber" {
        value "9";
      }
      enum "ipRadiusSubscriber" {
        value "10";
      }
      enum "l2MacSubscriber" {
        value "11";
      }
      enum "l2Dhcpv4Subscriber" {
        value "12";
      }
      enum "l2RadiusSubscriber" {
        value "13";
      }
    }
    description
     "An enumerated integer-value describing the type of subscriber
      session.  This value has the intent of refining the interface
      type assigned to a subscriber session.  The interface type
      assigned to a subscriber session groups those types of
      subscriber sessions with similar interface semantics.
      
      A PPP subscriber session consists of a PPP connection
      (RFC-1661)
      and has an interface type of 'ppp'.  The following subscriber
      types refine PPP subscriber sessions:
      
          'pppSubscriber'
              A PPP connection initiated over a circuit (e.g., an
      ISDN
              line or ATM VC) using the LCP (RFC-1661).
      
          'pppoeSubscriber'
              A PPP connection over Ethernet (RFC-2516), initiated
              by a PADI (PPPoE Active Discovery Initiation) packet.
      
          'l2tpSubscriber'
              A PPP connection over an L2TP tunnel (RFC-2661),
              initiated by an Incoming-Call-Request control message.
      
          'l2fSubscriber'
              A PPP connection over an L2F tunnel (RFC-2341),
              initiated by a L2F_OPEN message with a non-zero MID.
      
      An IP subscriber session consists of the routed traffic
      associated with a subscriber IP address having an interface
      type of 'ipSubscriber'.  Routed traffic describes IP traffic
      that transits at least one router.  If a subscriber's IP
      address
      is not unique to the system, further distinguishing
      characteristics, such as VRF or MAC address, form part of the
      subscriber's identity.  The following subscriber types refine
      IP
      subscriber sessions:
      
          'ipInterfaceSubscriber'
              An IP subcriber session provisioned by the system's
              configuration which consists of all traffic received by
              the interface to which the provisioning applies.
      
          'ipPktSubscriber'
              An IP subscriber session initiated by the receipt of
      the
              first packet received with an unclassified source IP
              address.
      
          'ipDhcpv4Subscriber'
              An IP subscriber session initiated by the receipt of a
              DHCPv4 DISCOVER packet (RFC-2131).
      
          'ipRadiusSubscriber'
              An IP subscriber session initiated by the receipt of a
              RADIUS Access-Request packet (RFC-2865).
      
      An L2 subscriber session consists of the non-routed traffic
      associated with a subscriber IP address having an interface
      type of 'l2Subscriber'.  Non-routed traffic describes IP
      traffic
      that doesn't transit a router, meaning that the subscriber must
      be directly connected to the system or have a connection
      through
      an L2 access network (e.g., bridges, switches, and tunnels).
      The
      following subscriber types refine L2 subscriber sessions:
      
          'l2MacPacketSubscriber'
              An L2 subscriber session initiated by the receipt of
      the
              first layer 2 packet with an unclassified source MAC
              address.
      
          'l2Dhcpv4Subscriber'
              An L2 subscriber session initiated by the receipt of a
              DHCPv4 DISCOVER packet (RFC-2131).
      
          'l2RadiusSucriber'
              An L2 subscriber session initiated by the receipt of a
              RADIUS Access-Request packet (RFC-2865).
      
      The system should assign the value 'other' to any subscriber
      session not recognized by the implementation of a MIB module
      using this textual convention.
      
      The value 'all' represents a special value used to indicate all
      subscriber session types.  For example, a scope of aggregation
      that includes all subscriber session types uses this value to
      indicate this fact.";
    reference
     "W. Simpson, 'The Point-to-Point Protocol (PPP)',
      RFC-1661,
      July 1994.
      
      R. Droms, 'Dynamic Host Configuration Protocol', RFC-2131,
      March
      1997.
      
      A. Valencia, M. Littlewood, T. Kolar, 'Cisco Layer Two
      Forwarding Protocol (L2F)', RFC-2341, May 1998.
      
      L. Mamakos, K. Lidl, J. Evarts, D. Carrel, D. Simone, and
      R. Wheeler, 'A Method for Transmitting PPP Over Ethernet
      (PPPoE)', RFC-2516, February 1999.
      
      W. Townsley, A. Valencia, A. Rubens, G. Pall, G. Zorn,
      and
      B. Palter, 'Layer Two Tunneling Protocol (L2TP)',
      RFC-2661,
      August 1999.
      
      C. Rigney, S. Willens, A. Rubens, and W. Simpson, 'Remote
      Authentication Dial-In User Service (RADIUS)', RFC-2865,
      June
      2000.";
  }

  typedef SubSessionTypes {
    type bits {
      bit pppSubscriber {
        position "0";
      }
      bit pppoeSubscriber {
        position "1";
      }
      bit l2tpSubscriber {
        position "2";
      }
      bit l2fSubscriber {
        position "3";
      }
      bit ipInterfaceSubscriber {
        position "4";
      }
      bit ipPktSubscriber {
        position "5";
      }
      bit ipDhcpv4Subscriber {
        position "6";
      }
      bit ipRadiusSubscriber {
        position "7";
      }
      bit l2MacSubscriber {
        position "8";
      }
      bit l2Dhcpv4Subscriber {
        position "9";
      }
      bit l2RadiusSubscriber {
        position "10";
      }
    }
    description
     "A bit string describing a set of subscriber session types:
      
      'pppSubscriber'
          A PPP connection initiated over a circuit (e.g., an ISDN
          line or ATM VC) using the LCP (RFC-1661).
      
      'pppoeSubscriber'
          A PPP connection over Ethernet (RFC-2516), initiated
          by a PADI (PPPoE Active Discovery Initiation) packet.
      
      'l2tpSubscriber'
          A PPP connection over an L2TP tunnel (RFC-2661),
          initiated by an Incoming-Call-Request control message.
      
      'l2fSubscriber'
          A PPP connection over an L2F tunnel (RFC-2341),
          initiated by a L2F_OPEN message with a non-zero MID.
      
      'ipInterfaceSubscriber'
          An IP subcriber session provisioned by the system's
          configuration which consists of all traffic received by
          the interface the provisioning applies.
      
      'ipPktSubscriber'
          An IP subscriber session initiated by the receipt of
          the first packet received with an unclassified source IP
          address.
      
      'ipDhcpv4Subscriber'
          An IP subscriber session initiated by the receipt of a
          DHCPv4 DISCOVER packet (RFC-2131).
      
      'ipRadiusSubscriber'
          An IP subscriber session initiated by the receipt of a
          RADIUS Access-Request packet (RFC-2865).
      
      'l2MacSubscriber'
          An L2 subscriber session initiated by the receipt of the
          first layer 2 packet with an unclassified source MAC
          address.
      
      'l2Dhcpv4Subscriber'
          An L2 subscriber session initiated by the receipt of a
          DHCPv4 DISCOVER packet (RFC-2131).
      
      'l2RadiusSubscriber'
          An L2 subscriber session initiated by the receipt of a
          RADIUS Access-Request packet (RFC-2865).
      
      For more details regarding subscriber session types, see the
      descriptive text associated with the SubSessionType textual
      convention.";
    reference
     "W. Simpson, 'The Point-to-Point Protocol (PPP)', RFC-1661,
      July 1994.
      
      R. Droms, 'Dynamic Host Configuration Protocol', RFC-2131, March
      1997.
      
      A. Valencia, M. Littlewood, T. Kolar, 'Cisco Layer Two
      Forwarding Protocol (L2F)', RFC-2341, May 1998.
      
      L. Mamakos, K. Lidl, J. Evarts, D. Carrel, D. Simone, and
      R. Wheeler, 'A Method for Transmitting PPP Over Ethernet
      (PPPoE)', RFC-2516, February 1999.
      
      W. Townsley, A. Valencia, A. Rubens, G. Pall, G. Zorn, and
      B. Palter, 'Layer Two Tunneling Protocol (L2TP)', RFC-2661,
      August 1999.
      
      C. Rigney, S. Willens, A. Rubens, and W. Simpson, 'Remote
      Authentication Dial-In User Service (RADIUS)', RFC-2865, June
      2000.";
  }

  typedef SubSessionState {
    type enumeration {
      enum "other" {
        value "1";
      }
      enum "pending" {
        value "2";
      }
      enum "up" {
        value "3";
      }
    }
    description
     "An enumerated integer-value describing the state of a
      subscriber session:
      
          'other'
              The subscriber session is in a state not recognized by
              the implementation of a MIB module using this textual
              convention.
      
          'pending'
              The subscriber session is in the PENDING state;
              that is, the subscriber session has been initiated and
              the system is in the process of establishing the
              subscriber session.
      
          'up'
              The subscriber session is in the UP state; that is, the
              system has established the subscriber session.";
  }

  typedef SubSessionRedundancyMode {
    type enumeration {
      enum "none" {
        value "1";
      }
      enum "other" {
        value "2";
      }
      enum "active" {
        value "3";
      }
      enum "standby" {
        value "4";
      }
    }
    description
     "An enumerated integer-value describing the redundancy mode in
      which a subscriber session is operating:
      
          'none'
              The subscriber session is not part of a redundant
              configuration.
      
          'other'
              The subscriber session is part of a redundant
              configuration and is in a state not recognized by this
              MIB module.
      
          'active'
              The subscriber session is part of a redundant
              configuration and is forwarding traffic from the
              subscriber.
      
          'standby'
              The subscriber session is part of a redundant
              configuration and ready to become active in the case of
              a fail-over event (e.g., linecard failure).";
  }

  smiv2:alias "ciscoSubscriberSessionTcMIB" {
    smiv2:oid "1.3.6.1.4.1.9.9.785";
  }

}
