/*
 * Generated by confdc --mib2yang-std
 * Source: mgmt/dmi/model/mib/src/CISCO-VPDN-MGMT-MIB.mib
 */
/*
 * This YANG module has been generated by smidump 0.5.0:
 *
 *      smidump -f yang CISCO-VPDN-MGMT-MIB
 *
 * Do not edit. Edit the source file instead!
 */

module CISCO-VPDN-MGMT-MIB {

  namespace "urn:ietf:params:xml:ns:yang:smiv2:CISCO-VPDN-MGMT-MIB";
  prefix CISCO-VPDN-MGMT-MIB;

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-vpdn@cisco.com";

  description
   "The MIB module for VPDN.
    
    Overview of VPDN MIB
    
    MIB description
    
    This MIB is to support the Virtual Private Dialup Network (VPDN)
    feature of Cisco IOS.  VPDN handles the forwarding of PPP links
    from an Internet Provider (ISP) to a Home Gateway.
    
    The VPDN MIB provides the operational information on Cisco's
    VPDN tunnelling implementation.  The following entities are
    managed:
    1) Global VPDN information
    2) VPDN tunnel information
    3) VPDN tunnel's user information
    4) Failure history per user
    
    The following example configuration shows how the VPDN MIB
    returns VPDN information, from either CISCO A - Network Access
    Server (NAS) or CISCO B - Tunnel Server (TS).  The User call is
    projected by either domain name or Dialed Number Identification
    Service (DNIS).
    
    The terms NAS and TS are generic terms refering to the VPDN
    systems.
    
    The following table shows the corresponding technology-specific
    terms.
    
          Network Access Server            Tunnel Server
          ------------------------------   -------------------------
    L2F   Network Access Server    (NAS)   Home Gateway (HGW)
    L2TP  L2TP Access Concentrator (LAC)   L2TP Network Server (LNS)
    PPTP  PPTP Access Concentrator (PAC)   PPTP Network Server (PNS)
    
               (NAS)                          (TS)
    User ===== Cisco A ===== IP Network ===== Cisco B ===== Server
                    |                          |
                    +========== VPDN ==========+
    
    1) The VPDN global entry identifies the system wide VPDN
       information.
    2) The VPDN tunnel table identifies the active VPDN tunnels on
       Cisco A and Cisco B.  The table contains an entry for each
       active tunnel on the system.
    3) The VPDN tunnel user table identifies the active users for
       each active tunnel on each system and provides relevant
       information for each user.
    4) The VPDN failure history table identifies the last failure
       recorded per user and provides relevant information.";

  revision 2009-06-16 {
    description
     "[Revision added by libsmi due to a LAST-UPDATED clause.]";
  }

  revision 2006-01-20 {
    description
     "Obsoleted the following deprecated L2F specific objects.
      These set of objects have been replaced by the 
      corresponding multi-protocol objects since 1999-03-24.
      
      Obsoleted Objects       Existing replacements
      =================       =====================
      cvpdnTunnelTotal        cvpdnSystemTable
      cvpdnSessionTotal       cvpdnSystemTable
      cvpdnDeniedUsersTotal   cvpdnSystemTable
      cvpdnTunnelTable        cvpdnTunnelAttrTable
      cvpdnTunnelSessionTable cvpdnSessionAttrTable
      
      Deprecated the following objects and added corresponding
      InetAddressType/InetAddress compliant counterparts:
      
      Deprecated Objects   Added Replacements
      ==================   ==================
      cvpdnTunnelAttrLocalIpAddress  
                           cvpdnTunnelAttrLocalInetAddressType
                           cvpdnTunnelAttrLocalInetAddress
      cvpdnTunnelAttrSourceIpAddress 
                           cvpdnTunnelAttrSourceInetAddressType
                           cvpdnTunnelAttrSourceInetAddress
      cvpdnTunnelAttrRemoteIpAddress 
                           cvpdnTunnelAttrRemoteInetAddressType
                           cvpdnTunnelAttrRemoteInetAddress
      cvpdnUnameToFailHistSourceIp   
                           cvpdnUnameToFailHistSourceInetType
                           cvpdnUnameToFailHistSourceInetAddr
      cvpdnUnameToFailHistDestIp     
                           cvpdnUnameToFailHistDestInetType
                           cvpdnUnameToFailHistDestInetAddr
      
      Added two new values, 'pwUp' and 'pwDown', for the
      existing object cvpdnNotifSessionEvent to support
      pseudowire status change event reporting.";
  }

  revision 2004-06-08 {
    description
     "Deprecated the cvpdnBundleEndpointType object since it's
      values did not align with the PPP protocol. This object was
      replaced by cvpdnBundleEndpointClass.";
  }

  revision 2004-04-02 {
    description
     "Added support for Multilink PPP VPDN information.  Modified
      the cvpdnSessionAttrTable to add objects that specify the
      multilink PPP bundle to which a session belongs.  Added
      scalar objects to hold the total number of multilink PPP
      bundles comprised of one, two, and more than two links.
      Added the cvpdnBundleTable that describes the PPP multilink
      bundle.  Added the cvpdnChildBundleTable to expose the
      containment relationship between the multilink PPP bundle
      and the VPDN tunnel.";
  }

  revision 2002-07-08 {
    description
     "Added support for VPDN Template information.  The template
      table reports the number of active sessions for each
      template.  This number is the sum of active sessions for
      all VPDN groups associated with each template.";
  }

  revision 2002-05-17 {
    description
     "Changed cvpdnSessionAttrVirtualCircuitID to an Unsigned32
      object.  Also, moved Unsigned32 import to SNMPv2-SMI.";
  }

  revision 2002-04-02 {
    description
     "Added virtual circuit ID, packets dropped, and notification
      objects for WAN/IP support.";
  }

  revision 2000-01-12 {
    description
     "Added support for Point-to-Point Tunneling Protocol (PPTP).
      Changed object descriptions to use generic terms.";
  }

  revision 1999-03-24 {
    description
     "Added support for multiple tunnel protocols with these
      tables
       1) cvpdnSystemTable
       2) cvpdnTunnelAttrTable
       3) cvpdnTunnelSessionAttrTable
      
      Deprecated objects and tables duplicated by the three new
      tables
       1) cvpdnTunnelTotal, cvpdnSessionTotal,
          cvpdnDeniedUsersTotal
       2) cvpdnTunnelTable
       3) cvpdnTunnelSessionTable";
  }

  revision 1997-07-15 {
    description
     "Initial version of this MIB module.";
  }

  typedef TunnelType {
    type enumeration {
      enum "l2f" {
        value "1";
      }
      enum "l2tp" {
        value "2";
      }
      enum "pptp" {
        value "3";
      }
    }
    description
     "The tunnel type.  This is the tunnel protocol of a VPDN
      tunnel.";
  }

  typedef EndpointClass {
    type enumeration {
      enum "none" {
        value "1";
      }
      enum "local" {
        value "2";
      }
      enum "ipV4Address" {
        value "3";
      }
      enum "macAddress" {
        value "4";
      }
      enum "magicNumber" {
        value "5";
      }
      enum "phone" {
        value "6";
      }
    }
    description
     "The endpoint discriminator class supplied by the remote peer in
      a PPP Multilink bundle.
      
      RFC 1990 defines the following classes:
      
      none:        Class 0 - Null Class.  No endpoint discriminator
                   is being used.  The endpoint discriminator should
                   contain a SnmpAdminString (SIZE (0)) value.
      
      local:       Class 1 - Locally Assigned Address.  This class is
                   defined to permit a local assignment in the case
                   where use of one of the globally unique classes is
                   not possible.  The endpoint discriminator should
                   contain a SnmpAdminString (SIZE(1..20)) value.
      
      ipV4Address: Class 2 - Internet Protocol (IP) Address.  An
                   address in this class contains an IP host address.
                   The endpoint discriminator should contain a
                   InetAddressIPv4 value.
      
      macAddress:  Class 3 - IEEE 802.1 Globally Assigned MAC
                   Address.  An address in this class contains an
                   IEEE 802.1 MAC address in canonical (802.3)
                   format.  The endpoint discriminator should contain
                   a MacAddress value.
      
      magicNumber: Class 4 - PPP Magic-Number Block.  This is not an
                   address but a block of 1 to 5 concatenated 32 bit
                   PPP Magic-Numbers.  The endpoint discriminator
                   should contain an OCTET STRING (SIZE (4|8|12|16|
                   20)) value.
      
      phone:       Class 5 - Public Switched Network Directory 
                   Number.  An address in this class contains an
                   octet sequence as defined by I.331 (E.164)
                   representing an international telephone directory
                   number suitable for use to access the endpoint via
                   the public switched telephone network.  The
                   endpoint discriminator should contain a
                   SnmpAdminString (SIZE(1..15)) value.";
    reference
     "The PPP Multilink Protocol (MP), RFC 1990, Section 5.1.3.";
  }


  container CISCO-VPDN-MGMT-MIB {
    config false;

    container ciscoVpdnMgmtMIBNotifs {
      smiv2:oid "1.3.6.1.4.1.9.10.24.0";

      leaf cvpdnNotifSessionID {
        type int32 {
          range "0..65535";
        }
        description
         "This object contains the local session ID of the L2X
          session for which this notification has been
          generated.";
        smiv2:max-access "read-only";
        smiv2:oid "1.3.6.1.4.1.9.10.24.0.1";
      }

      leaf cvpdnNotifSessionEvent {
        type enumeration {
          enum "up" {
            value "1";
          }
          enum "down" {
            value "2";
          }
          enum "pwUp" {
            value "3";
          }
          enum "pwDown" {
            value "4";
          }
        }
        description
         "Indicates the event that generated the L2X session
          notification.
          
          The events are represented as follows:
          
          up:     Session has come up.
          
          down:   Session has gone down.
          
          pwUp:   Pseudowire associated with this 
                  session has come up.
          
          pwDown: Pseudowire associated with this 
                  session has gone down.";
        smiv2:max-access "read-only";
        smiv2:oid "1.3.6.1.4.1.9.10.24.0.2";
      }
    }

    container cvpdnSystemInfo {
      smiv2:oid "1.3.6.1.4.1.9.10.24.1.1";

      leaf cvpdnTunnelTotal {
        type yang:gauge32;
        units "tunnels";
        status obsolete;
        description
         "The total number of VPDN tunnels that are currently
          active within this system.";
        smiv2:max-access "read-only";
        smiv2:oid "1.3.6.1.4.1.9.10.24.1.1.1";
      }

      leaf cvpdnSessionTotal {
        type yang:gauge32;
        units "users";
        status obsolete;
        description
         "The total number of active users in all the active VPDN
          tunnels within this system.";
        smiv2:max-access "read-only";
        smiv2:oid "1.3.6.1.4.1.9.10.24.1.1.2";
      }

      leaf cvpdnDeniedUsersTotal {
        type yang:counter32;
        units "attempts";
        status obsolete;
        description
         "The total number of denied user attempts to all the
          active VPDN tunnels within this system.";
        smiv2:max-access "read-only";
        smiv2:oid "1.3.6.1.4.1.9.10.24.1.1.3";
      }

      leaf cvpdnSystemNotifSessionEnabled {
        type boolean;
        description
         "Indicates whether Layer 2 VPN session notifications are
          enabled.";
        smiv2:defval "false";
        smiv2:max-access "read-only";
        smiv2:oid "1.3.6.1.4.1.9.10.24.1.1.5";
      }

      leaf cvpdnSystemClearSessions {
        type enumeration {
          enum "none" {
            value "1";
          }
          enum "all" {
            value "2";
          }
          enum "l2f" {
            value "3";
          }
          enum "l2tp" {
            value "4";
          }
          enum "pptp" {
            value "5";
          }
        }
        description
         "Clears all the sessions in a given tunnel type.  When
          reading this object, the value of 'none' will always be
          returned.
          
          When setting these values, the following operations will be
          performed:
          
              none: no operation.
          
              all:  clears all the sessions in all the tunnels.
          
              l2f:  clears all the L2F sessions.
          
              l2tp: clears all the L2TP sessions.
          
              pptp: clears all the PPTP sessions.";
        smiv2:max-access "read-write";
        smiv2:oid "1.3.6.1.4.1.9.10.24.1.1.6";
      }
    }

    container cvpdnMultilinkInfo {
      smiv2:oid "1.3.6.1.4.1.9.10.24.1.6";

      leaf cvpdnBundlesWithOneLink {
        type yang:gauge32;
        description
         "The total number of bundles comprised of a single link.";
        smiv2:max-access "read-only";
        smiv2:oid "1.3.6.1.4.1.9.10.24.1.6.1";
      }

      leaf cvpdnBundlesWithTwoLinks {
        type yang:gauge32;
        description
         "The total number of bundles comprised of two links.";
        smiv2:max-access "read-only";
        smiv2:oid "1.3.6.1.4.1.9.10.24.1.6.2";
      }

      leaf cvpdnBundlesWithMoreThanTwoLinks {
        type yang:gauge32;
        description
         "The total number of bundles comprised of more than two
          links.";
        smiv2:max-access "read-only";
        smiv2:oid "1.3.6.1.4.1.9.10.24.1.6.3";
      }

      leaf cvpdnBundleLastChanged {
        type yang:timestamp;
        description
         "The value of the sysUpTime object when the contents of
          cvpdnBundleTable last changed.";
        smiv2:max-access "read-only";
        smiv2:oid "1.3.6.1.4.1.9.10.24.1.6.5";
      }
    }

    container cvpdnSystemTable {
      description
       "Table of information about the VPDN system for all tunnel
        types.";
      smiv2:oid "1.3.6.1.4.1.9.10.24.1.1.4";

      list cvpdnSystemEntry {
        key "cvpdnSystemTunnelType";
        description
         "An entry in the table, containing information about a
          single type of VPDN tunnel.";
        smiv2:oid "1.3.6.1.4.1.9.10.24.1.1.4.1";

        leaf cvpdnSystemTunnelType {
          type CISCO-VPDN-MGMT-MIB:TunnelType;
          description
           "The tunnel type.  This is the tunnel protocol.";
          smiv2:max-access "not-accessible";
          smiv2:oid "1.3.6.1.4.1.9.10.24.1.1.4.1.1";
        }

        leaf cvpdnSystemTunnelTotal {
          type yang:gauge32;
          units "tunnels";
          description
           "The total number of VPDN tunnels that are currently active
            of this tunnel type.";
          smiv2:max-access "read-only";
          smiv2:oid "1.3.6.1.4.1.9.10.24.1.1.4.1.2";
        }

        leaf cvpdnSystemSessionTotal {
          type yang:gauge32;
          units "sessions";
          description
           "The total number of active sessions in all the active VPDN
            tunnels of this tunnel type.";
          smiv2:max-access "read-only";
          smiv2:oid "1.3.6.1.4.1.9.10.24.1.1.4.1.3";
        }

        leaf cvpdnSystemDeniedUsersTotal {
          type yang:counter32;
          units "attempts";
          description
           "The total number of denied user attempts to all the VPDN
            tunnels of this tunnel type since last system
            re-initialization.";
          smiv2:max-access "read-only";
          smiv2:oid "1.3.6.1.4.1.9.10.24.1.1.4.1.4";
        }

        leaf cvpdnSystemInitialConnReq {
          type yang:counter32;
          units "attempts";
          description
           "The total number tunnel connection attempts on all the VPDN
            tunnels of this tunnel type since last system
            re-initialization.";
          smiv2:max-access "read-only";
          smiv2:oid "1.3.6.1.4.1.9.10.24.1.1.4.1.5";
        }

        leaf cvpdnSystemSuccessConnReq {
          type yang:counter32;
          units "attempts";
          description
           "The total number tunnel Successful connection attempts in VPDN
            tunnels of this tunnel type since last system
            re-initialization.";
          smiv2:max-access "read-only";
          smiv2:oid "1.3.6.1.4.1.9.10.24.1.1.4.1.6";
        }

        leaf cvpdnSystemFailedConnReq {
          type yang:counter32;
          units "attempts";
          description
           "The total number tunnel Failed connection attempts in VPDN
            tunnels of this tunnel type since last system
            re-initialization.";
          smiv2:max-access "read-only";
          smiv2:oid "1.3.6.1.4.1.9.10.24.1.1.4.1.7";
        }
      }
    }

    container cvpdnTunnelTable {
      status obsolete;
      description
       "Table of information about the active VPDN tunnels.";
      smiv2:oid "1.3.6.1.4.1.9.10.24.1.2.1";

      list cvpdnTunnelEntry {
        key "cvpdnTunnelTunnelId";
        status obsolete;
        description
         "An entry in the table, containing information about a
          single active VPDN tunnel.";
        smiv2:oid "1.3.6.1.4.1.9.10.24.1.2.1.1";

        leaf cvpdnTunnelTunnelId {
          type uint32;
          status obsolete;
          description
           "The Tunnel ID of an active VPDN tunnel.  If it is the
            instigator of the tunnel, the ID is the HGW/LNS tunnel
            ID, otherwise it is the NAS/LAC tunnel ID.";
          smiv2:max-access "not-accessible";
          smiv2:oid "1.3.6.1.4.1.9.10.24.1.2.1.1.1";
        }

        leaf cvpdnTunnelRemoteTunnelId {
          type uint32;
          status obsolete;
          description
           "The remote Tunnel ID of an active VPDN tunnel.  If it
            is the instigator of the tunnel, the ID is the NAS/LAC
            tunnel ID, otherwise it is the HGW/LNS tunnel ID.";
          smiv2:max-access "read-only";
          smiv2:oid "1.3.6.1.4.1.9.10.24.1.2.1.1.2";
        }

        leaf cvpdnTunnelLocalName {
          type snmpv2-tc:DisplayString {
            length "1..255";
          }
          status obsolete;
          description
           "The local name of an active VPDN tunnel.  It will be
            the NAS/LAC name of the tunnel if the router serves as
            the NAS/LAC, or the HGW/LNS name of the tunnel if the
            system serves as the home gateway.  Typically, the
            local name is the configured host name of the router.";
          smiv2:max-access "read-only";
          smiv2:oid "1.3.6.1.4.1.9.10.24.1.2.1.1.3";
        }

        leaf cvpdnTunnelRemoteName {
          type snmpv2-tc:DisplayString {
            length "1..255";
          }
          status obsolete;
          description
           "The remote name of an active VPDN tunnel.  It will be
            the home gateway name of the tunnel if the system is a
            NAS/LAC, or the NAS/LAC name of the tunnel if the
            system serves as the home gateway.";
          smiv2:max-access "read-only";
          smiv2:oid "1.3.6.1.4.1.9.10.24.1.2.1.1.4";
        }

        leaf cvpdnTunnelRemoteEndpointName {
          type snmpv2-tc:DisplayString {
            length "1..255";
          }
          status obsolete;
          description
           "The remote end point name of an active VPDN tunnel.
            This name is either the domain name or the DNIS that
            this tunnel is projected with.";
          smiv2:max-access "read-only";
          smiv2:oid "1.3.6.1.4.1.9.10.24.1.2.1.1.5";
        }

        leaf cvpdnTunnelLocalInitConnection {
          type boolean;
          status obsolete;
          description
           "This object indicates whether the tunnel was generated
            locally or not.";
          smiv2:max-access "read-only";
          smiv2:oid "1.3.6.1.4.1.9.10.24.1.2.1.1.6";
        }

        leaf cvpdnTunnelOrigCause {
          type enumeration {
            enum "domain" {
              value "1";
            }
            enum "dnis" {
              value "2";
            }
            enum "stack" {
              value "3";
            }
          }
          status obsolete;
          description
           "The cause which originated an active VPDN tunnel.  The
            tunnel can be projected via domain name, DNIS or a
            stack group (SGBP).";
          smiv2:max-access "read-only";
          smiv2:oid "1.3.6.1.4.1.9.10.24.1.2.1.1.7";
        }

        leaf cvpdnTunnelState {
          type enumeration {
            enum "unknown" {
              value "1";
            }
            enum "opening" {
              value "2";
            }
            enum "open" {
              value "3";
            }
            enum "closing" {
              value "4";
            }
          }
          status obsolete;
          description
           "The current state of an active VPDN tunnel.  Each state
            code is explained below:
            
                   unknown: The current state of the tunnel is
                            unknown.
            
                   opening: The tunnel has just been instigated and
                            is pending for a remote end reply to
                            complete the process.
            
                   open:    The tunnel is active.
            
                   closing: The tunnel has just been shut down and
                            is pending for the remote end to reply
                            to complete the process.";
          smiv2:max-access "read-only";
          smiv2:oid "1.3.6.1.4.1.9.10.24.1.2.1.1.8";
        }

        leaf cvpdnTunnelActiveSessions {
          type yang:gauge32;
          units "sessions";
          status obsolete;
          description
           "The total number of active session currently in the
            tunnel.";
          smiv2:max-access "read-only";
          smiv2:oid "1.3.6.1.4.1.9.10.24.1.2.1.1.9";
        }

        leaf cvpdnTunnelDeniedUsers {
          type yang:counter32;
          units "calls";
          status obsolete;
          description
           "A count of the accumulated total of denied users for
            the tunnel.";
          smiv2:max-access "read-only";
          smiv2:oid "1.3.6.1.4.1.9.10.24.1.2.1.1.10";
        }

        leaf cvpdnTunnelSoftshut {
          type boolean;
          status obsolete;
          description
           "A VPDN tunnel can be put into a soft shut state to
            prevent any new user session to be added.  This object
            specifies whether this tunnel has been soft shut.";
          smiv2:max-access "read-only";
          smiv2:oid "1.3.6.1.4.1.9.10.24.1.2.1.1.12";
        }

        leaf cvpdnTunnelNetworkServiceType {
          type enumeration {
            enum "ip" {
              value "1";
            }
          }
          status obsolete;
          description
           "The type of network service used in the active tunnel.
            For now it is IP only.";
          smiv2:max-access "read-only";
          smiv2:oid "1.3.6.1.4.1.9.10.24.1.2.1.1.13";
        }

        leaf cvpdnTunnelLocalIpAddress {
          type inet:ipv4-address;
          status obsolete;
          description
           "The local IP address of the tunnel.  This IP address is
            that of the interface at the local end of the tunnel.";
          smiv2:max-access "read-only";
          smiv2:oid "1.3.6.1.4.1.9.10.24.1.2.1.1.14";
        }

        leaf cvpdnTunnelSourceIpAddress {
          type inet:ipv4-address;
          status obsolete;
          description
           "The source IP address of the tunnel.  This IP address
            is the user configurable IP address for Stack Group
            Biding Protocol (SGBP) via the CLI command:
            vpdn source-ip";
          reference
           "The Stack Group Biding Protocol (SGBP), United States 
            Patent 6073176";
          smiv2:max-access "read-only";
          smiv2:oid "1.3.6.1.4.1.9.10.24.1.2.1.1.15";
        }

        leaf cvpdnTunnelRemoteIpAddress {
          type inet:ipv4-address;
          status obsolete;
          description
           "The remote IP address of the tunnel.  This IP address
            is that of the interface at the remote end of the
            tunnel.";
          smiv2:max-access "read-only";
          smiv2:oid "1.3.6.1.4.1.9.10.24.1.2.1.1.16";
        }
      }
    }

    container cvpdnTunnelAttrTable {
      description
       "Table of information about the active VPDN tunnels.  An
        entry is added to the table when a new tunnel is initiated
        and removed from the table when the tunnel is terminated.";
      smiv2:oid "1.3.6.1.4.1.9.10.24.1.2.2";

      list cvpdnTunnelAttrEntry {
        key "cvpdnSystemTunnelType cvpdnTunnelAttrTunnelId";
        description
         "An entry in the table, containing information about a
          single active VPDN tunnel.";
        smiv2:oid "1.3.6.1.4.1.9.10.24.1.2.2.1";

        leaf cvpdnSystemTunnelType {
          type leafref {
            path "/CISCO-VPDN-MGMT-MIB:CISCO-VPDN-MGMT-MIB/CISCO-VPDN-MGMT-MIB:cvpdnSystemTable/CISCO-VPDN-MGMT-MIB:cvpdnSystemEntry/CISCO-VPDN-MGMT-MIB:cvpdnSystemTunnelType";
          }
        }

        leaf cvpdnTunnelAttrTunnelId {
          type int32 {
            range "0..65535";
          }
          description
           "The Tunnel ID of an active VPDN tunnel.  If this end is the
            instigator of the tunnel, the ID is the TS tunnel ID,
            otherwise it is the NAS tunnel ID.
            
            Two distinct tunnels with the same tunnel ID may exist, but
            with different tunnel types.";
          smiv2:max-access "not-accessible";
          smiv2:oid "1.3.6.1.4.1.9.10.24.1.2.2.1.1";
        }

        leaf cvpdnTunnelAttrRemoteTunnelId {
          type int32 {
            range "0..65535";
          }
          description
           "The remote Tunnel ID of an active VPDN tunnel.  If this end
            is the instigator of the tunnel, the ID is the NAS tunnel
            ID, otherwise it is the TS tunnel ID.";
          smiv2:max-access "read-only";
          smiv2:oid "1.3.6.1.4.1.9.10.24.1.2.2.1.2";
        }

        leaf cvpdnTunnelAttrLocalName {
          type snmpv2-tc:DisplayString {
            length "1..255";
          }
          description
           "The local name of an active VPDN tunnel.  It will be the
            NAS name of the tunnel if the system serves as the NAS, or
            the TS name of the tunnel if the system serves as the
            tunnel server.  Typically, the local name is the configured
            host name of the system.";
          smiv2:max-access "read-only";
          smiv2:oid "1.3.6.1.4.1.9.10.24.1.2.2.1.3";
        }

        leaf cvpdnTunnelAttrRemoteName {
          type snmpv2-tc:DisplayString {
            length "1..255";
          }
          description
           "The remote name of an active VPDN tunnel.  It will be the
            tunnel server name of the tunnel if the system is a NAS,
            or the NAS name of the tunnel if the system serves as the
            tunnel server.";
          smiv2:max-access "read-only";
          smiv2:oid "1.3.6.1.4.1.9.10.24.1.2.2.1.4";
        }

        leaf cvpdnTunnelAttrRemoteEndpointName {
          type snmpv2-tc:DisplayString {
            length "1..255";
          }
          description
           "The remote end point name of an active VPDN tunnel.  This
            name is either the domain name or the DNIS that this tunnel
            is projected with.";
          smiv2:max-access "read-only";
          smiv2:oid "1.3.6.1.4.1.9.10.24.1.2.2.1.5";
        }

        leaf cvpdnTunnelAttrLocalInitConnection {
          type boolean;
          description
           "This object indicates whether the tunnel was originated
            locally or not.  If it's true, the tunnel was originated
            locally.";
          smiv2:max-access "read-only";
          smiv2:oid "1.3.6.1.4.1.9.10.24.1.2.2.1.6";
        }

        leaf cvpdnTunnelAttrOrigCause {
          type enumeration {
            enum "domain" {
              value "1";
            }
            enum "dnis" {
              value "2";
            }
            enum "stack" {
              value "3";
            }
            enum "xconnect" {
              value "4";
            }
          }
          description
           "The cause which originated an active VPDN tunnel.  The
            tunnel can be projected via domain name, DNIS, stack group,
            or L2 Xconnect.";
          smiv2:max-access "read-only";
          smiv2:oid "1.3.6.1.4.1.9.10.24.1.2.2.1.7";
        }

        leaf cvpdnTunnelAttrState {
          type enumeration {
            enum "unknown" {
              value "1";
            }
            enum "l2fOpening" {
              value "2";
            }
            enum "l2fOpenWait" {
              value "3";
            }
            enum "l2fOpen" {
              value "4";
            }
            enum "l2fClosing" {
              value "5";
            }
            enum "l2fCloseWait" {
              value "6";
            }
            enum "l2tpIdle" {
              value "7";
            }
            enum "l2tpWaitCtlReply" {
              value "8";
            }
            enum "l2tpEstablished" {
              value "9";
            }
            enum "l2tpShuttingDown" {
              value "10";
            }
            enum "l2tpNoSessionLeft" {
              value "11";
            }
            enum "pptpIdle" {
              value "12";
            }
            enum "pptpWaitConnect" {
              value "13";
            }
            enum "pptpWaitCtlRequest" {
              value "14";
            }
            enum "pptpWaitCtlReply" {
              value "15";
            }
            enum "pptpEstablished" {
              value "16";
            }
            enum "pptpWaitStopReply" {
              value "17";
            }
            enum "pptpTerminal" {
              value "18";
            }
          }
          description
           "The current state of an active VPDN tunnel.
            Tunnels of type l2f will have states with the 'l2f' prefix.
            Tunnels of type l2tp will have states with the 'l2tp'
            prefix.
            Tunnels of type pptp will have states with the 'pptp'
            prefix.
            
            Each state code is explained below:
            
                unknown:            The current state of the tunnel is
                                    unknown.
            
                l2fOpening:         The tunnel has just been initiated
                                    and is pending for a remote end
                                    reply to complete the process.
            
                l2fOpenWait:        This end received a tunnel open
                                    request from the remote end and is
                                    waiting for the tunnel to be
                                    established.
            
                l2fOpen:            The tunnel is active.
            
                l2fClosing:         This end received a tunnel close
                                    request.
            
                l2fCloseWait:       The tunnel has just been shut down
                                    and is pending for the remote end
                                    to reply to complete the process.
            
                l2tpIdle:           No tunnel is initiated yet.
            
                l2tpWaitCtlReply:   The tunnel has been initiated and
                                    is pending for a remote end reply
                                    to complete the process.
            
                l2tpEstablished:    The tunnel is active.
            
                l2tpShuttingDown:   The tunnel is in progress of
                                    shutting down.
            
                l2tpNoSessionLeft:  There is no session left in the
                                    tunnel.
            
                pptpIdle:           No tunnel is initiated yet.
            
                pptpWaitConnect:    The tunnel is waiting for a TCP
                                    connection.
            
                pptpWaitCtlRequest: The tunnel has been initiated and
                                    is pending for a remote end
                                    request.
            
                pptpWaitCtlReply:   The tunnel has been initiated and
                                    is pending for a remote end reply.
            
                pptpEstablished:    The tunnel is active.
            
                pptpWaitStopReply:  The tunnel is being shut down and
                                    is pending for a remote end reply.
            
                pptpTerminal:       The tunnel has been shut down.";
          smiv2:max-access "read-only";
          smiv2:oid "1.3.6.1.4.1.9.10.24.1.2.2.1.8";
        }

        leaf cvpdnTunnelAttrActiveSessions {
          type yang:gauge32;
          units "sessions";
          description
           "The total number of active session currently in the
            tunnel.";
          smiv2:max-access "read-only";
          smiv2:oid "1.3.6.1.4.1.9.10.24.1.2.2.1.9";
        }

        leaf cvpdnTunnelAttrDeniedUsers {
          type yang:counter32;
          units "calls";
          description
           "A count of the accumulated total of denied users for the
            tunnel.";
          smiv2:max-access "read-only";
          smiv2:oid "1.3.6.1.4.1.9.10.24.1.2.2.1.10";
        }

        leaf cvpdnTunnelAttrSoftshut {
          type boolean;
          description
           "A VPDN tunnel can be put into a soft shut state to prevent
            any new session to be added.  This object specifies whether
            this tunnel has been soft shut.  If its true, it has been
            soft shut.";
          smiv2:max-access "read-only";
          smiv2:oid "1.3.6.1.4.1.9.10.24.1.2.2.1.11";
        }

        leaf cvpdnTunnelAttrNetworkServiceType {
          type enumeration {
            enum "ip" {
              value "1";
            }
          }
          description
           "The type of network service used in the active tunnel.";
          smiv2:max-access "read-only";
          smiv2:oid "1.3.6.1.4.1.9.10.24.1.2.2.1.12";
        }

        leaf cvpdnTunnelAttrLocalIpAddress {
          type inet:ipv4-address;
          status deprecated;
          description
           "The local IP address of the tunnel.  This IP address is
            that of the interface at the local end of the tunnel.";
          smiv2:max-access "read-only";
          smiv2:oid "1.3.6.1.4.1.9.10.24.1.2.2.1.13";
        }

        leaf cvpdnTunnelAttrSourceIpAddress {
          type inet:ipv4-address;
          status deprecated;
          description
           "The source IP address of the tunnel.  This IP address is
            the user configurable IP address for Stack Group Biding
            Protocol.";
          reference
           "The Stack Group Biding Protocol (SGBP), United States 
            Patent 6073176";
          smiv2:max-access "read-only";
          smiv2:oid "1.3.6.1.4.1.9.10.24.1.2.2.1.14";
        }

        leaf cvpdnTunnelAttrRemoteIpAddress {
          type inet:ipv4-address;
          status deprecated;
          description
           "The remote IP address of the tunnel.  This IP address is
            that of the interface at the remote end of the tunnel.";
          smiv2:max-access "read-only";
          smiv2:oid "1.3.6.1.4.1.9.10.24.1.2.2.1.15";
        }

        leaf cvpdnTunnelAttrLocalInetAddressType {
          type inet-address:InetAddressType;
          description
           "Indicates the type of address contained in
            cvpdnTunnelAttrLocalInetAddress";
          smiv2:max-access "read-only";
          smiv2:oid "1.3.6.1.4.1.9.10.24.1.2.2.1.16";
        }

        leaf cvpdnTunnelAttrLocalInetAddress {
          type inet-address:InetAddress;
          description
           "The local IP address of the tunnel.  This IP address is
            that of the interface at the local end of the tunnel.
            The type of this address is determined by the value of 
            cvpdnTunnelAttrLocalInetAddressType.";
          smiv2:max-access "read-only";
          smiv2:oid "1.3.6.1.4.1.9.10.24.1.2.2.1.17";
        }

        leaf cvpdnTunnelAttrSourceInetAddressType {
          type inet-address:InetAddressType;
          description
           "Indicates the type of address contained in
            cvpdnTunnelAttrSourceInetAddress";
          smiv2:max-access "read-only";
          smiv2:oid "1.3.6.1.4.1.9.10.24.1.2.2.1.18";
        }

        leaf cvpdnTunnelAttrSourceInetAddress {
          type inet-address:InetAddress;
          description
           "The source IP address of the tunnel.  This IP address is
            the user configurable IP address for Stack Group Biding
            Protocol.  The type of this address is determined by the 
            value of cvpdnTunnelAttrSourceInetAddressType.";
          reference
           "The Stack Group Biding Protocol (SGBP), United States 
            Patent 6073176";
          smiv2:max-access "read-only";
          smiv2:oid "1.3.6.1.4.1.9.10.24.1.2.2.1.19";
        }

        leaf cvpdnTunnelAttrRemoteInetAddressType {
          type inet-address:InetAddressType;
          description
           "Indicates the type of address contained in
            cvpdnTunnelAttrRemoteInetAddress";
          smiv2:max-access "read-only";
          smiv2:oid "1.3.6.1.4.1.9.10.24.1.2.2.1.20";
        }

        leaf cvpdnTunnelAttrRemoteInetAddress {
          type inet-address:InetAddress;
          description
           "The remote IP address of the tunnel.  This IP address is
            that of the interface at the remote end of the tunnel.
            The type of this address is determined by the value of 
            cvpdnTunnelAttrRemoteInetAddressType.";
          smiv2:max-access "read-only";
          smiv2:oid "1.3.6.1.4.1.9.10.24.1.2.2.1.21";
        }
      }
    }

    container cvpdnTunnelSessionTable {
      status obsolete;
      description
       "Table of information about individual user sessions
        within the active tunnels.  Entry is added to the table
        when new user session is initiated and be removed from
        the table when the user session is terminated.";
      smiv2:oid "1.3.6.1.4.1.9.10.24.1.3.1";

      list cvpdnTunnelSessionEntry {
        key "cvpdnTunnelTunnelId cvpdnTunnelSessionId";
        status obsolete;
        description
         "An entry in the table, containing information about a
          single user session within the tunnel.";
        smiv2:oid "1.3.6.1.4.1.9.10.24.1.3.1.1";

        leaf cvpdnTunnelTunnelId {
          type leafref {
            path "/CISCO-VPDN-MGMT-MIB:CISCO-VPDN-MGMT-MIB/CISCO-VPDN-MGMT-MIB:cvpdnTunnelTable/CISCO-VPDN-MGMT-MIB:cvpdnTunnelEntry/CISCO-VPDN-MGMT-MIB:cvpdnTunnelTunnelId";
          }
          status obsolete;
        }

        leaf cvpdnTunnelSessionId {
          type uint32;
          status obsolete;
          description
           "The ID of an active VPDN tunnel user session.";
          smiv2:max-access "not-accessible";
          smiv2:oid "1.3.6.1.4.1.9.10.24.1.3.1.1.1";
        }

        leaf cvpdnTunnelSessionUserName {
          type snmpv2-tc:DisplayString {
            length "1..255";
          }
          status obsolete;
          description
           "The name of the user of the user session.";
          smiv2:max-access "read-only";
          smiv2:oid "1.3.6.1.4.1.9.10.24.1.3.1.1.2";
        }

        leaf cvpdnTunnelSessionState {
          type enumeration {
            enum "unknown" {
              value "1";
            }
            enum "opening" {
              value "2";
            }
            enum "open" {
              value "3";
            }
            enum "closing" {
              value "4";
            }
            enum "waitingForTunnel" {
              value "5";
            }
          }
          status obsolete;
          description
           "The current state of an active user session.  Each state
            code is explained below:
            
                unknown:          The current state of the tunnel's
                                  session is unknown.
            
                opening:          The user session has just been
                                  initiated through a tunnel and is
                                  pending for the remote end reply
                                  to complete the process.
            
                open:             The user session is active.
            
                closing:          The user session has just been
                                  closed and is pending for the
                                  remote end reply to complete the
                                  process.
            
                waitingForTunnel: The user session is in this state
                                  when the tunnel which this session
                                  is going through is still in
                                  CLOSED state.  It waits for the
                                  tunnel to become OPEN before the
                                  session is allow to be fully
                                  established.";
          smiv2:max-access "read-only";
          smiv2:oid "1.3.6.1.4.1.9.10.24.1.3.1.1.3";
        }

        leaf cvpdnTunnelSessionCallDuration {
          type yang:timeticks;
          status obsolete;
          description
           "This object specifies the call duration of the current
            active user session in value of system uptime.";
          smiv2:max-access "read-only";
          smiv2:oid "1.3.6.1.4.1.9.10.24.1.3.1.1.4";
        }

        leaf cvpdnTunnelSessionPacketsOut {
          type yang:counter32;
          units "packets";
          status obsolete;
          description
           "The total number of output packets through this active
            user session.";
          smiv2:max-access "read-only";
          smiv2:oid "1.3.6.1.4.1.9.10.24.1.3.1.1.5";
        }

        leaf cvpdnTunnelSessionBytesOut {
          type yang:counter32;
          units "bytes";
          status obsolete;
          description
           "The total number of output bytes through this active
            user session.";
          smiv2:max-access "read-only";
          smiv2:oid "1.3.6.1.4.1.9.10.24.1.3.1.1.6";
        }

        leaf cvpdnTunnelSessionPacketsIn {
          type yang:counter32;
          units "packets";
          status obsolete;
          description
           "The total number of input packets through this active
            user session.";
          smiv2:max-access "read-only";
          smiv2:oid "1.3.6.1.4.1.9.10.24.1.3.1.1.7";
        }

        leaf cvpdnTunnelSessionBytesIn {
          type yang:counter32;
          units "bytes";
          status obsolete;
          description
           "The total number of input bytes through this active
            user session.";
          smiv2:max-access "read-only";
          smiv2:oid "1.3.6.1.4.1.9.10.24.1.3.1.1.8";
        }

        leaf cvpdnTunnelSessionDeviceType {
          type enumeration {
            enum "other" {
              value "1";
            }
            enum "asyncInternalModem" {
              value "2";
            }
            enum "async" {
              value "3";
            }
            enum "bchan" {
              value "4";
            }
            enum "sync" {
              value "5";
            }
            enum "virtualAccess" {
              value "6";
            }
            enum "xdsl" {
              value "7";
            }
            enum "cable" {
              value "8";
            }
          }
          status obsolete;
          description
           "The type of physical devices that this user session
            is attached to for the local end of the tunnel.  The
            meaning of each device type is explained below:
            
                other:              Any device that has not been
                                    defined.
            
                asyncInternalModem: Modem Pool device of an access
                                    server.
            
                async:              A regular asynchronous serial
                                    interface.
            
                sync:               A regular synchronous serial
                                    interface.
            
                bchan:              An ISDN call.
            
                xdsl:               Future application with xDSL
                                    devices.
            
                cable:              Future application with Cable
                                    modem devices.";
          smiv2:max-access "read-only";
          smiv2:oid "1.3.6.1.4.1.9.10.24.1.3.1.1.9";
        }

        leaf cvpdnTunnelSessionDeviceCallerId {
          type snmpv2-tc:DisplayString;
          status obsolete;
          description
           "The incoming caller identification of the user.  It is
            the originating number that called into the device that
            initiates the user session.  This object can be empty
            since not all dial device can provide caller ID
            information.";
          smiv2:max-access "read-only";
          smiv2:oid "1.3.6.1.4.1.9.10.24.1.3.1.1.10";
        }

        leaf cvpdnTunnelSessionDevicePhyId {
          type if-mib:InterfaceIndexOrZero;
          status obsolete;
          description
           "The device ID of the physical interface for the user
            session.  The object is the the interface index which
            points to the ifTable.  For virtual interface that is
            not in the ifTable, it will have zero value.";
          smiv2:max-access "read-only";
          smiv2:oid "1.3.6.1.4.1.9.10.24.1.3.1.1.11";
        }

        leaf cvpdnTunnelSessionMultilink {
          type boolean;
          status obsolete;
          description
           "This object indicates whether the session is part of a
            multilink or not.";
          smiv2:max-access "read-only";
          smiv2:oid "1.3.6.1.4.1.9.10.24.1.3.1.1.12";
        }

        leaf cvpdnTunnelSessionModemSlotIndex {
          type uint32;
          status obsolete;
          description
           "The Modem Pool database slot index if it is associated
            with this user session.  Only a session with device of
            type asyncInternalModem will have a valid value for
            this object.";
          smiv2:max-access "read-only";
          smiv2:oid "1.3.6.1.4.1.9.10.24.1.3.1.1.13";
        }

        leaf cvpdnTunnelSessionModemPortIndex {
          type uint32;
          status obsolete;
          description
           "The Modem Pool database port index if it is associated
            with this user session.  Only a session with a device
            of type asyncInternalModem will have a valid value for
            this object.";
          smiv2:max-access "read-only";
          smiv2:oid "1.3.6.1.4.1.9.10.24.1.3.1.1.14";
        }

        leaf cvpdnTunnelSessionDS1SlotIndex {
          type uint32;
          status obsolete;
          description
           "The DS1 database slot index if it is associated with
            this user session.  Only a session with a device of
            type asyncInternalModem will have a valid value for
            this object.";
          smiv2:max-access "read-only";
          smiv2:oid "1.3.6.1.4.1.9.10.24.1.3.1.1.15";
        }

        leaf cvpdnTunnelSessionDS1PortIndex {
          type uint32;
          status obsolete;
          description
           "The DS1 database port index if it is associated with
            this user session.  Only a session with a device of
            type asyncInternalModem will have a a valid value for
            this object.";
          smiv2:max-access "read-only";
          smiv2:oid "1.3.6.1.4.1.9.10.24.1.3.1.1.16";
        }

        leaf cvpdnTunnelSessionDS1ChannelIndex {
          type uint32;
          status obsolete;
          description
           "The DS1 database channel index if it is associated with
            this user session.  Only a session over a device of
            type asyncInternalModem will have a valid value for
            this object.";
          smiv2:max-access "read-only";
          smiv2:oid "1.3.6.1.4.1.9.10.24.1.3.1.1.17";
        }

        leaf cvpdnTunnelSessionModemCallStartTime {
          type yang:timestamp;
          status obsolete;
          description
           "The start time of the current modem call.  Only a
            session with a  device of type asyncInternalModem will
            have a valid value for this object.";
          smiv2:max-access "read-only";
          smiv2:oid "1.3.6.1.4.1.9.10.24.1.3.1.1.18";
        }

        leaf cvpdnTunnelSessionModemCallStartIndex {
          type uint32;
          status obsolete;
          description
           "Arbitrary small integer to distinguish modem calls that
            occurred at the same time tick.  Only session over
            device asyncInternalModem will have a valid value for
            this object.";
          smiv2:max-access "read-only";
          smiv2:oid "1.3.6.1.4.1.9.10.24.1.3.1.1.19";
        }
      }
    }

    container cvpdnSessionAttrTable {
      description
       "Table of information about individual sessions within the
        active tunnels.  An entry is added to the table when a new
        session is initiated and removed from the table when the
        session is terminated.";
      smiv2:oid "1.3.6.1.4.1.9.10.24.1.3.2";

      list cvpdnSessionAttrEntry {
        key "cvpdnSystemTunnelType cvpdnTunnelAttrTunnelId cvpdnSessionAttrSessionId";
        description
         "An entry in the table, containing information about a
          single session within the tunnel.";
        smiv2:oid "1.3.6.1.4.1.9.10.24.1.3.2.1";

        leaf cvpdnSystemTunnelType {
          type leafref {
            path "/CISCO-VPDN-MGMT-MIB:CISCO-VPDN-MGMT-MIB/CISCO-VPDN-MGMT-MIB:cvpdnSystemTable/CISCO-VPDN-MGMT-MIB:cvpdnSystemEntry/CISCO-VPDN-MGMT-MIB:cvpdnSystemTunnelType";
          }
        }

        leaf cvpdnTunnelAttrTunnelId {
          type leafref {
            path "/CISCO-VPDN-MGMT-MIB:CISCO-VPDN-MGMT-MIB/CISCO-VPDN-MGMT-MIB:cvpdnTunnelAttrTable/CISCO-VPDN-MGMT-MIB:cvpdnTunnelAttrEntry/CISCO-VPDN-MGMT-MIB:cvpdnTunnelAttrTunnelId";
          }
        }

        leaf cvpdnSessionAttrSessionId {
          type int32 {
            range "0..65535";
          }
          description
           "The ID of an active VPDN session.";
          smiv2:max-access "not-accessible";
          smiv2:oid "1.3.6.1.4.1.9.10.24.1.3.2.1.1";
        }

        leaf cvpdnSessionAttrUserName {
          type snmpv2-tc:DisplayString {
            length "1..255";
          }
          description
           "The name of the user of the session.";
          smiv2:max-access "read-only";
          smiv2:oid "1.3.6.1.4.1.9.10.24.1.3.2.1.2";
        }

        leaf cvpdnSessionAttrState {
          type enumeration {
            enum "unknown" {
              value "1";
            }
            enum "l2fOpening" {
              value "2";
            }
            enum "l2fOpen" {
              value "3";
            }
            enum "l2fCloseWait" {
              value "4";
            }
            enum "l2fWaitingForTunnel" {
              value "5";
            }
            enum "l2tpIdle" {
              value "6";
            }
            enum "l2tpWaitingTunnel" {
              value "7";
            }
            enum "l2tpWaitReply" {
              value "8";
            }
            enum "l2tpWaitConnect" {
              value "9";
            }
            enum "l2tpEstablished" {
              value "10";
            }
            enum "l2tpShuttingDown" {
              value "11";
            }
            enum "pptpWaitVAccess" {
              value "12";
            }
            enum "pptpPacEstablished" {
              value "13";
            }
            enum "pptpWaitTunnel" {
              value "14";
            }
            enum "pptpWaitOCRP" {
              value "15";
            }
            enum "pptpPnsEstablished" {
              value "16";
            }
            enum "pptpWaitCallDisc" {
              value "17";
            }
            enum "pptpTerminal" {
              value "18";
            }
          }
          description
           "The current state of a tunnel session.
            L2F tunnel sessions will have states with the 'l2f' prefix.
            L2TP tunnel sessions will have states with the 'l2tp'
            prefix.
            
            Each state code is explained below:
            
                unknown:             The current state of the tunnel's
                                     session is unknown.
            
                l2fOpening:          The session has just been
                                     initiated through a tunnel and is
                                     pending for the remote end reply
                                     to complete the process.
            
                l2fOpen:             The session is active.
            
                l2fCloseWait:        The session has just been closed
                                     and is pending for the remote end
                                     reply to complete the process.
            
                l2fWaitingForTunnel: The session is in this state when
                                     the tunnel which this session is
                                     going through is still in CLOSED
                                     state.  It waits for the tunnel to
                                     become OPEN before the session is
                                     allowed to be fully established.
            
                l2tpIdle:            No session is initiated yet.
            
                l2tpWaitingTunnel:   The session is waiting for the
                                     tunnel to be established.
            
                l2tpWaitReply:       The session has been initiated and
                                     is pending for the remote end
                                     reply to complete the process.
            
                l2tpWaitConnect:     This end has acknowledged a
                                     connection request and is waiting
                                     for the remote end to connect.
            
                l2tpEstablished:     The session is active.
            
                l2tpShuttingDown:    The session is in progress of
                                     shutting down.
            
                pptpWaitVAccess:     The session is waiting for the
                                     creation of a virtual access
                                     interface.
            
                pptpPacEstablished:  The session is active.
            
                pptpWaitTunnel:      The session is waiting for the
                                     tunnel to be established.
            
                pptpWaitOCRP:        The session has been initiated and
                                     is pending for the remote end
                                     reply to complete the process.
            
                pptpPnsEstablished:  The session is active.
            
                pptpWaitCallDisc:    Session shutdown is in progress.";
          smiv2:max-access "read-only";
          smiv2:oid "1.3.6.1.4.1.9.10.24.1.3.2.1.3";
        }

        leaf cvpdnSessionAttrCallDuration {
          type yang:timeticks;
          description
           "This object specifies the call duration of the current
            active session.";
          smiv2:max-access "read-only";
          smiv2:oid "1.3.6.1.4.1.9.10.24.1.3.2.1.4";
        }

        leaf cvpdnSessionAttrPacketsOut {
          type yang:counter32;
          units "packets";
          description
           "The total number of output packets through this active
            session.";
          smiv2:max-access "read-only";
          smiv2:oid "1.3.6.1.4.1.9.10.24.1.3.2.1.5";
        }

        leaf cvpdnSessionAttrBytesOut {
          type yang:counter32;
          units "bytes";
          description
           "The total number of output bytes through this active
            session.";
          smiv2:max-access "read-only";
          smiv2:oid "1.3.6.1.4.1.9.10.24.1.3.2.1.6";
        }

        leaf cvpdnSessionAttrPacketsIn {
          type yang:counter32;
          units "packets";
          description
           "The total number of input packets through this active
            session.";
          smiv2:max-access "read-only";
          smiv2:oid "1.3.6.1.4.1.9.10.24.1.3.2.1.7";
        }

        leaf cvpdnSessionAttrBytesIn {
          type yang:counter32;
          units "bytes";
          description
           "The total number of input bytes through this active
            session.";
          smiv2:max-access "read-only";
          smiv2:oid "1.3.6.1.4.1.9.10.24.1.3.2.1.8";
        }

        leaf cvpdnSessionAttrDeviceType {
          type enumeration {
            enum "other" {
              value "1";
            }
            enum "asyncInternalModem" {
              value "2";
            }
            enum "async" {
              value "3";
            }
            enum "bchan" {
              value "4";
            }
            enum "sync" {
              value "5";
            }
            enum "virtualAccess" {
              value "6";
            }
            enum "xdsl" {
              value "7";
            }
            enum "cable" {
              value "8";
            }
          }
          description
           "The type of physical devices that this session is attached
            to for the local end of the tunnel.  The meaning of each
            device type is explained below:
            
                other:              Any device that has not been
                                    defined.
            
                asyncInternalModem: Modem Pool device of an access
                                    server.
            
                async:              A regular asynchronous serial
                                    interface.
            
                sync:               A regular synchronous serial
                                    interface.
            
                bchan:              An ISDN call.
            
                xdsl:               xDSL interface.
            
                cable:              cable modem interface.";
          smiv2:max-access "read-only";
          smiv2:oid "1.3.6.1.4.1.9.10.24.1.3.2.1.9";
        }

        leaf cvpdnSessionAttrDeviceCallerId {
          type snmpv2-tc:DisplayString;
          description
           "The incoming caller identification of the user.  It is the
            originating number that called into the device that
            initiates the session.  This object can be empty since not
            all dial devices can provide caller ID information.";
          smiv2:max-access "read-only";
          smiv2:oid "1.3.6.1.4.1.9.10.24.1.3.2.1.10";
        }

        leaf cvpdnSessionAttrDevicePhyId {
          type if-mib:InterfaceIndexOrZero;
          description
           "The device ID of the physical interface for the session.
            The object is the the interface index which points to the
            ifTable.  For virtual interfaces that are not in the
            ifTable, the value will be zero.";
          smiv2:max-access "read-only";
          smiv2:oid "1.3.6.1.4.1.9.10.24.1.3.2.1.11";
        }

        leaf cvpdnSessionAttrMultilink {
          type boolean;
          description
           "This object indicates whether the session is part of a
            multilink PPP bundle, even if there is only one link or
            session in the bundle.  If it is multilink PPP, the value
            is true.";
          smiv2:max-access "read-only";
          smiv2:oid "1.3.6.1.4.1.9.10.24.1.3.2.1.12";
        }

        leaf cvpdnSessionAttrModemSlotIndex {
          type uint32;
          description
           "The Modem Pool database slot index if it is associated with
            this session.  Only a session with device of type
            'asyncInternalModem' will have a valid value for this
            object; otherwise, it is not instantiated.";
          smiv2:max-access "read-only";
          smiv2:oid "1.3.6.1.4.1.9.10.24.1.3.2.1.13";
        }

        leaf cvpdnSessionAttrModemPortIndex {
          type uint32;
          description
           "The Modem Pool database port index if it is associated with
            this session.  Only a session with a device of type
            'asyncInternalModem' will have a valid value for this
            object; otherwise, it is not instantiated.";
          smiv2:max-access "read-only";
          smiv2:oid "1.3.6.1.4.1.9.10.24.1.3.2.1.14";
        }

        leaf cvpdnSessionAttrDS1SlotIndex {
          type uint32;
          description
           "The DS1 database slot index if it is associated with this
            session.  Only a session with a device of type
            'asyncInternalModem' will have a valid value for this
            object; otherwise it is not instantiated.";
          smiv2:max-access "read-only";
          smiv2:oid "1.3.6.1.4.1.9.10.24.1.3.2.1.15";
        }

        leaf cvpdnSessionAttrDS1PortIndex {
          type uint32;
          description
           "The DS1 database port index if it is associated with this
            session.  Only a session with a device of type
            'asyncInternalModem' will have a valid value for this
            object; otherwise it is not instantiated.";
          smiv2:max-access "read-only";
          smiv2:oid "1.3.6.1.4.1.9.10.24.1.3.2.1.16";
        }

        leaf cvpdnSessionAttrDS1ChannelIndex {
          type uint32;
          description
           "The DS1 database channel index if it is associated with
            this session.  Only a session over a device of type
            'asyncInternalModem' will have a valid value for this
            object; otherwise it is not instantiated.";
          smiv2:max-access "read-only";
          smiv2:oid "1.3.6.1.4.1.9.10.24.1.3.2.1.17";
        }

        leaf cvpdnSessionAttrModemCallStartTime {
          type yang:timestamp;
          description
           "The start time of the current modem call.  Only a session
            with a device of type 'asyncInternalModem' will have a
            valid value for this object; otherwise, it is not
            instantiated.";
          smiv2:max-access "read-only";
          smiv2:oid "1.3.6.1.4.1.9.10.24.1.3.2.1.18";
        }

        leaf cvpdnSessionAttrModemCallStartIndex {
          type uint32;
          description
           "Arbitrary small integer to distinguish modem calls that
            occurred at the same time tick.  Only session over device
            'asyncInternalModem' will have a valid value for this
            object; otherwise, it is not instantiated.";
          smiv2:max-access "read-only";
          smiv2:oid "1.3.6.1.4.1.9.10.24.1.3.2.1.19";
        }

        leaf cvpdnSessionAttrVirtualCircuitID {
          type uint32;
          description
           "The virtual circuit ID of an active Layer 2 VPN session.";
          smiv2:max-access "read-only";
          smiv2:oid "1.3.6.1.4.1.9.10.24.1.3.2.1.20";
        }

        leaf cvpdnSessionAttrSentPktsDropped {
          type yang:counter32;
          units "packets";
          description
           "The total number of dropped packets that could not be sent
            into this active session.";
          smiv2:max-access "read-only";
          smiv2:oid "1.3.6.1.4.1.9.10.24.1.3.2.1.21";
        }

        leaf cvpdnSessionAttrRecvPktsDropped {
          type yang:counter32;
          units "packets";
          description
           "The total number of dropped packets that were received from
            this active session.";
          smiv2:max-access "read-only";
          smiv2:oid "1.3.6.1.4.1.9.10.24.1.3.2.1.22";
        }

        leaf cvpdnSessionAttrMultilinkBundle {
          type snmp-framework:SnmpAdminString {
            length "0..255";
          }
          description
           "This object specifies the name of the multilink bundle to
            which this session belongs.  The value of this object is
            only valid when the value of cvpdnSessionAttrMultilink is
            'true'.  If the value of cvpdnSessionAttrMultilink is
            'false', then the value of this object will be the empty
            string.";
          smiv2:max-access "read-only";
          smiv2:oid "1.3.6.1.4.1.9.10.24.1.3.2.1.23";
        }

        leaf cvpdnSessionAttrMultilinkIfIndex {
          type if-mib:InterfaceIndexOrZero;
          description
           "This object specifies the ifIndex of the multilink bundle
            to which this session belongs.  The value of this object is
            only valid when the value of cvpdnSessionAttrMultilink is
            'true'.  If the value of cvpdnSessionAttrMultilink is
            'false', then the value of this object will be zero.";
          smiv2:max-access "read-only";
          smiv2:oid "1.3.6.1.4.1.9.10.24.1.3.2.1.24";
        }
      }
    }

    container cvpdnUserToFailHistInfoTable {
      description
       "Table of the record of failure objects which can be
        referenced by an user name.  Only a name that has a
        valid item in the Cisco IOS VPDN failure history table
        will yield a valid entry in this table.  The table has
        a maximum size of 50 entries.  Only the newest 50
        entries will be kept in the table.";
      smiv2:oid "1.3.6.1.4.1.9.10.24.1.4.1";

      list cvpdnUserToFailHistInfoEntry {
        key "cvpdnUnameToFailHistUname cvpdnUnameToFailHistTunnelId";
        description
         "An entry in the table, containing failure history
          relevant to an user name.";
        smiv2:oid "1.3.6.1.4.1.9.10.24.1.4.1.1";

        leaf cvpdnUnameToFailHistUname {
          type snmpv2-tc:DisplayString {
            length "1..255";
          }
          description
           "The user name for this failure entry.";
          smiv2:max-access "not-accessible";
          smiv2:oid "1.3.6.1.4.1.9.10.24.1.4.1.1.1";
        }

        leaf cvpdnUnameToFailHistTunnelId {
          type uint32;
          description
           "The Tunnel ID for this failure entry.  If it is the
            instigator of the tunnel, the ID is the TS tunnel ID,
            otherwise it is the NAS tunnel ID.";
          smiv2:max-access "not-accessible";
          smiv2:oid "1.3.6.1.4.1.9.10.24.1.4.1.1.2";
        }

        leaf cvpdnUnameToFailHistUserId {
          type uint32;
          description
           "The user ID of this failure entry.";
          smiv2:max-access "read-only";
          smiv2:oid "1.3.6.1.4.1.9.10.24.1.4.1.1.3";
        }

        leaf cvpdnUnameToFailHistLocalInitConn {
          type boolean;
          description
           "This object indicates whether the tunnel in which the
            failure occurred was generated locally or not.";
          smiv2:max-access "read-only";
          smiv2:oid "1.3.6.1.4.1.9.10.24.1.4.1.1.4";
        }

        leaf cvpdnUnameToFailHistLocalName {
          type snmpv2-tc:DisplayString;
          description
           "The local name of the VPDN tunnel in which the failure
            occurred.  It will be the NAS name of the tunnel if the
            system serves as the NAS, or the TS name of the tunnel
            if the system serves as the tunnel server.  The local
            name is the configured host name of the system.  This
            object can be empty if the failure occurred prior to
            successful tunnel projection, thus no source name will
            be available.";
          smiv2:max-access "read-only";
          smiv2:oid "1.3.6.1.4.1.9.10.24.1.4.1.1.5";
        }

        leaf cvpdnUnameToFailHistRemoteName {
          type snmpv2-tc:DisplayString;
          description
           "The remote name of the VPDN tunnel in which the failure
            occurred.  It will be the tunnel server name of the
            tunnel if the system is a NAS, or the NAS name of the
            tunnel if the system serves as the tunnel server.  This
            object can be empty if the failure occurred prior to
            successful tunnel projection, thus no source name will
            be available.";
          smiv2:max-access "read-only";
          smiv2:oid "1.3.6.1.4.1.9.10.24.1.4.1.1.6";
        }

        leaf cvpdnUnameToFailHistSourceIp {
          type inet:ipv4-address;
          status deprecated;
          description
           "The source IP address of the tunnel in which the
            failure occurred.  This IP address is that of the
            interface at the instigator end of the tunnel.";
          smiv2:max-access "read-only";
          smiv2:oid "1.3.6.1.4.1.9.10.24.1.4.1.1.7";
        }

        leaf cvpdnUnameToFailHistDestIp {
          type inet:ipv4-address;
          status deprecated;
          description
           "The destination IP address of the tunnel in which the
            failure occurred.  This IP address is that of the
            interface at the receiver end of the tunnel.";
          smiv2:max-access "read-only";
          smiv2:oid "1.3.6.1.4.1.9.10.24.1.4.1.1.8";
        }

        leaf cvpdnUnameToFailHistCount {
          type yang:counter32;
          units "failures";
          description
           "This object is incremented when multiple failures has
            been experienced by this user on this tunnel.  Seeing a
            delta of >1 is an indication that the current failure
            record is the latest of a series of failures that has
            been recorded.";
          smiv2:max-access "read-only";
          smiv2:oid "1.3.6.1.4.1.9.10.24.1.4.1.1.9";
        }

        leaf cvpdnUnameToFailHistFailTime {
          type yang:timestamp;
          description
           "This object specifies the time when the failure is
            occurred.";
          smiv2:max-access "read-only";
          smiv2:oid "1.3.6.1.4.1.9.10.24.1.4.1.1.10";
        }

        leaf cvpdnUnameToFailHistFailType {
          type snmpv2-tc:DisplayString {
            length "1..255";
          }
          description
           "The type of failure for the current failure record.  It
            comes in a form of a an ASCII string which describes
            the type of failure.";
          smiv2:max-access "read-only";
          smiv2:oid "1.3.6.1.4.1.9.10.24.1.4.1.1.11";
        }

        leaf cvpdnUnameToFailHistFailReason {
          type snmpv2-tc:DisplayString {
            length "1..255";
          }
          description
           "The reason of failure for the current failure record.";
          smiv2:max-access "read-only";
          smiv2:oid "1.3.6.1.4.1.9.10.24.1.4.1.1.12";
        }

        leaf cvpdnUnameToFailHistSourceInetType {
          type inet-address:InetAddressType;
          description
           "Indicates the type of address contained in
            cvpdnUnameToFailHistSourceInetAddr.";
          smiv2:max-access "read-only";
          smiv2:oid "1.3.6.1.4.1.9.10.24.1.4.1.1.13";
        }

        leaf cvpdnUnameToFailHistSourceInetAddr {
          type inet-address:InetAddress;
          description
           "The source IP address of the tunnel in which the
            failure occurred.  This IP address is that of the
            interface at the instigator end of the tunnel.  The
            instigator end is the peer which initiates the tunnel
            estalishment.  The type of this address is determined
            by the value of cvpdnUnameToFailHistSourceInetType.";
          smiv2:max-access "read-only";
          smiv2:oid "1.3.6.1.4.1.9.10.24.1.4.1.1.14";
        }

        leaf cvpdnUnameToFailHistDestInetType {
          type inet-address:InetAddressType;
          description
           "Indicates the type of address contained in
            cvpdnUnameToFailHistDestInetAddr.";
          smiv2:max-access "read-only";
          smiv2:oid "1.3.6.1.4.1.9.10.24.1.4.1.1.15";
        }

        leaf cvpdnUnameToFailHistDestInetAddr {
          type inet-address:InetAddress;
          description
           "The destination IP address of the tunnel in which the
            failure occurred.  This IP address is that of the
            interface at the receiver end of the tunnel.  The type 
            of this address is determined by the value of 
            cvpdnUnameToFailHistDestInetType.";
          smiv2:max-access "read-only";
          smiv2:oid "1.3.6.1.4.1.9.10.24.1.4.1.1.16";
        }
      }
    }

    container cvpdnTemplateTable {
      description
       "Table of information about the VPDN templates.  The
        VPDN template is a grouping mechanism that allows
        configuration settings to be shared among multiple VPDN
        groups.  One such setting is a limit on the number of
        active sessions across all VPDN groups associated with
        the template.  The template table allows customers to
        monitor template-wide information such as tracking the
        allocation of sessions across templates.";
      smiv2:oid "1.3.6.1.4.1.9.10.24.1.5.1";

      list cvpdnTemplateEntry {
        key "cvpdnTemplateName";
        smiv2:implied "cvpdnTemplateName";
        description
         "An entry in the table, containing information about a
          single VPDN template.";
        smiv2:oid "1.3.6.1.4.1.9.10.24.1.5.1.1";

        leaf cvpdnTemplateName {
          type snmp-framework:SnmpAdminString {
            length "1..255";
          }
          description
           "The name of the VPDN template.";
          smiv2:max-access "not-accessible";
          smiv2:oid "1.3.6.1.4.1.9.10.24.1.5.1.1.1";
        }

        leaf cvpdnTemplateActiveSessions {
          type yang:gauge32;
          units "sessions";
          description
           "The total number of active session in all groups
            associated with the template.";
          smiv2:max-access "read-only";
          smiv2:oid "1.3.6.1.4.1.9.10.24.1.5.1.1.2";
        }
      }
    }

    container cvpdnBundleTable {
      description
       "Table that describes the multilink PPP attributes of the
        active VPDN sessions.";
      smiv2:oid "1.3.6.1.4.1.9.10.24.1.6.4";

      list cvpdnBundleEntry {
        key "cvpdnBundleName";
        description
         "An entry in this table represents an active multilink PPP
          bundle that belongs to a VPDN tunnel.";
        smiv2:oid "1.3.6.1.4.1.9.10.24.1.6.4.1";

        leaf cvpdnBundleName {
          type snmp-framework:SnmpAdminString {
            length "1..64";
          }
          description
           "The name of the multilink PPP bundle associated with a VPDN
            tunnel.";
          smiv2:max-access "not-accessible";
          smiv2:oid "1.3.6.1.4.1.9.10.24.1.6.4.1.1";
        }

        leaf cvpdnBundleLinkCount {
          type yang:gauge32;
          units "links";
          description
           "The total number of active links in a multilink PPP bundle
            associated with a VPDN tunnel.";
          smiv2:max-access "read-only";
          smiv2:oid "1.3.6.1.4.1.9.10.24.1.6.4.1.2";
        }

        leaf cvpdnBundleEndpointType {
          type enumeration {
            enum "none" {
              value "1";
            }
            enum "hostname" {
              value "2";
            }
            enum "string" {
              value "3";
            }
            enum "macAddress" {
              value "4";
            }
            enum "ipV4Address" {
              value "5";
            }
            enum "ipV6Address" {
              value "6";
            }
            enum "phone" {
              value "7";
            }
            enum "magicNumber" {
              value "8";
            }
          }
          status deprecated;
          description
           "The multilink PPP bundle discriminator type associated with
            a VPDN tunnel.  The value of this object represents the type
            of discriminator used in cvpdnBundleEndpoint.
            
                none:        No endpoint discriminator was supplied, the
                             default value is being used.
            
                hostname:    The router's hostname is being used as
                             discriminator.
            
                string:      User specified string is being used as
                             discriminator.
            
                macAddress:  A MAC address as defined by the MacAddress
                             textual convention is being used as
                             discriminator.
            
                ipV4Address: An IP address as defined by the
                             InetAddressIPv4 textual convention is being
                             used as discriminator.
            
                ipV6Address: An IP address as defined by the
                             InetAddressIPv6 textual convention is being
                             used as discriminator.
            
                phone:       The PSTN phone number is being used as
                             discriminator.
            
                magicNumber: A magic number is being used as
                             discriminator.";
          smiv2:max-access "read-only";
          smiv2:oid "1.3.6.1.4.1.9.10.24.1.6.4.1.3";
        }

        leaf cvpdnBundleEndpoint {
          type binary {
            length "0..255";
          }
          description
           "Indicates the discriminator used in this bundle that is
            associated with a VPDN tunnel.";
          smiv2:max-access "read-only";
          smiv2:oid "1.3.6.1.4.1.9.10.24.1.6.4.1.4";
        }

        leaf cvpdnBundlePeerIpAddrType {
          type inet-address:InetAddressType;
          description
           "Indicates the type of address contained in
            cvpdnBundlePeerIpAddr.";
          smiv2:max-access "read-only";
          smiv2:oid "1.3.6.1.4.1.9.10.24.1.6.4.1.5";
        }

        leaf cvpdnBundlePeerIpAddr {
          type inet-address:InetAddress;
          description
           "The IP address of the multilink PPP peer in a VPDN tunnel.";
          smiv2:max-access "read-only";
          smiv2:oid "1.3.6.1.4.1.9.10.24.1.6.4.1.6";
        }

        leaf cvpdnBundleEndpointClass {
          type CISCO-VPDN-MGMT-MIB:EndpointClass;
          description
           "The multilink PPP bundle discriminator class associated
            with a VPDN tunnel.  The value of this object represents the
            type of discriminator used in cvpdnBundleEndpoint.";
          smiv2:max-access "read-only";
          smiv2:oid "1.3.6.1.4.1.9.10.24.1.6.4.1.7";
        }
      }
    }

    container cvpdnBundleChildTable {
      description
       "A table that exposes the containment relationship between a
        multilink PPP bundle and a VPDN tunnel.";
      smiv2:oid "1.3.6.1.4.1.9.10.24.1.6.6";

      list cvpdnBundleChildEntry {
        key "cvpdnBundleName cvpdnBundleChildTunnelType cvpdnBundleChildTunnelId cvpdnBundleChildSessionId";
        description
         "An entry in this table represents a session that belongs to
          a VPDN tunnel and to a multilink PPP bundle.";
        smiv2:oid "1.3.6.1.4.1.9.10.24.1.6.6.1";

        leaf cvpdnBundleName {
          type leafref {
            path "/CISCO-VPDN-MGMT-MIB:CISCO-VPDN-MGMT-MIB/CISCO-VPDN-MGMT-MIB:cvpdnBundleTable/CISCO-VPDN-MGMT-MIB:cvpdnBundleEntry/CISCO-VPDN-MGMT-MIB:cvpdnBundleName";
          }
        }

        leaf cvpdnBundleChildTunnelType {
          type CISCO-VPDN-MGMT-MIB:TunnelType;
          description
           "The tunnel type.  This is the tunnel protocol of an active
            VPDN session that is associated with a multilink PPP
            bundle.";
          smiv2:max-access "not-accessible";
          smiv2:oid "1.3.6.1.4.1.9.10.24.1.6.6.1.1";
        }

        leaf cvpdnBundleChildTunnelId {
          type uint32;
          description
           "The Tunnel ID of an active VPDN session that is associated
            with a multilink PPP bundle.";
          smiv2:max-access "not-accessible";
          smiv2:oid "1.3.6.1.4.1.9.10.24.1.6.6.1.2";
        }

        leaf cvpdnBundleChildSessionId {
          type uint32;
          description
           "The ID of an active VPDN session that is associated with a
            multilink PPP bundle.";
          smiv2:max-access "read-only";
          smiv2:oid "1.3.6.1.4.1.9.10.24.1.6.6.1.3";
        }
      }
    }
  }

  notification cvpdnNotifSession {
    description
     "Conveys an event regarding the L2X session with the
      indicated session ID and Xconnect VCID.";
    smiv2:oid "1.3.6.1.4.1.9.10.24.0.3";

    container object-1 {

      leaf cvpdnNotifSessionID {
        type leafref {
          path "/CISCO-VPDN-MGMT-MIB:CISCO-VPDN-MGMT-MIB/CISCO-VPDN-MGMT-MIB:ciscoVpdnMgmtMIBNotifs/CISCO-VPDN-MGMT-MIB:cvpdnNotifSessionID";
        }
      }
    }

    container object-2 {

      leaf cvpdnNotifSessionEvent {
        type leafref {
          path "/CISCO-VPDN-MGMT-MIB:CISCO-VPDN-MGMT-MIB/CISCO-VPDN-MGMT-MIB:ciscoVpdnMgmtMIBNotifs/CISCO-VPDN-MGMT-MIB:cvpdnNotifSessionEvent";
        }
      }
    }

    container object-3 {

      leaf cvpdnSystemTunnelType {
        type leafref {
          path "/CISCO-VPDN-MGMT-MIB:CISCO-VPDN-MGMT-MIB/CISCO-VPDN-MGMT-MIB:cvpdnSystemTable/CISCO-VPDN-MGMT-MIB:cvpdnSystemEntry/CISCO-VPDN-MGMT-MIB:cvpdnSystemTunnelType";
        }
      }

      leaf cvpdnTunnelAttrTunnelId {
        type leafref {
          path "/CISCO-VPDN-MGMT-MIB:CISCO-VPDN-MGMT-MIB/CISCO-VPDN-MGMT-MIB:cvpdnTunnelAttrTable/CISCO-VPDN-MGMT-MIB:cvpdnTunnelAttrEntry/CISCO-VPDN-MGMT-MIB:cvpdnTunnelAttrTunnelId";
        }
      }

      leaf cvpdnSessionAttrSessionId {
        type leafref {
          path "/CISCO-VPDN-MGMT-MIB:CISCO-VPDN-MGMT-MIB/CISCO-VPDN-MGMT-MIB:cvpdnSessionAttrTable/CISCO-VPDN-MGMT-MIB:cvpdnSessionAttrEntry/CISCO-VPDN-MGMT-MIB:cvpdnSessionAttrSessionId";
        }
      }

      leaf cvpdnSessionAttrDevicePhyId {
        type leafref {
          path "/CISCO-VPDN-MGMT-MIB:CISCO-VPDN-MGMT-MIB/CISCO-VPDN-MGMT-MIB:cvpdnSessionAttrTable/CISCO-VPDN-MGMT-MIB:cvpdnSessionAttrEntry/CISCO-VPDN-MGMT-MIB:cvpdnSessionAttrDevicePhyId";
        }
      }
    }

    container object-4 {

      leaf cvpdnSystemTunnelType {
        type leafref {
          path "/CISCO-VPDN-MGMT-MIB:CISCO-VPDN-MGMT-MIB/CISCO-VPDN-MGMT-MIB:cvpdnSystemTable/CISCO-VPDN-MGMT-MIB:cvpdnSystemEntry/CISCO-VPDN-MGMT-MIB:cvpdnSystemTunnelType";
        }
      }

      leaf cvpdnTunnelAttrTunnelId {
        type leafref {
          path "/CISCO-VPDN-MGMT-MIB:CISCO-VPDN-MGMT-MIB/CISCO-VPDN-MGMT-MIB:cvpdnTunnelAttrTable/CISCO-VPDN-MGMT-MIB:cvpdnTunnelAttrEntry/CISCO-VPDN-MGMT-MIB:cvpdnTunnelAttrTunnelId";
        }
      }

      leaf cvpdnSessionAttrSessionId {
        type leafref {
          path "/CISCO-VPDN-MGMT-MIB:CISCO-VPDN-MGMT-MIB/CISCO-VPDN-MGMT-MIB:cvpdnSessionAttrTable/CISCO-VPDN-MGMT-MIB:cvpdnSessionAttrEntry/CISCO-VPDN-MGMT-MIB:cvpdnSessionAttrSessionId";
        }
      }

      leaf cvpdnSessionAttrVirtualCircuitID {
        type leafref {
          path "/CISCO-VPDN-MGMT-MIB:CISCO-VPDN-MGMT-MIB/CISCO-VPDN-MGMT-MIB:cvpdnSessionAttrTable/CISCO-VPDN-MGMT-MIB:cvpdnSessionAttrEntry/CISCO-VPDN-MGMT-MIB:cvpdnSessionAttrVirtualCircuitID";
        }
      }
    }
  }

  smiv2:alias "ciscoVpdnMgmtMIB" {
    smiv2:oid "1.3.6.1.4.1.9.10.24";
  }

  smiv2:alias "ciscoVpdnMgmtMIBNotifs" {
    smiv2:oid "1.3.6.1.4.1.9.10.24.0";
  }

  smiv2:alias "ciscoVpdnMgmtMIBObjects" {
    smiv2:oid "1.3.6.1.4.1.9.10.24.1";
  }

  smiv2:alias "cvpdnSystemInfo" {
    smiv2:oid "1.3.6.1.4.1.9.10.24.1.1";
  }

  smiv2:alias "cvpdnTunnelInfo" {
    smiv2:oid "1.3.6.1.4.1.9.10.24.1.2";
  }

  smiv2:alias "cvpdnTunnelSessionInfo" {
    smiv2:oid "1.3.6.1.4.1.9.10.24.1.3";
  }

  smiv2:alias "cvpdnUserToFailHistInfo" {
    smiv2:oid "1.3.6.1.4.1.9.10.24.1.4";
  }

  smiv2:alias "cvpdnTemplateInfo" {
    smiv2:oid "1.3.6.1.4.1.9.10.24.1.5";
  }

  smiv2:alias "cvpdnMultilinkInfo" {
    smiv2:oid "1.3.6.1.4.1.9.10.24.1.6";
  }

  smiv2:alias "ciscoVpdnMgmtMIBConformance" {
    smiv2:oid "1.3.6.1.4.1.9.10.24.3";
  }

  smiv2:alias "ciscoVpdnMgmtMIBCompliances" {
    smiv2:oid "1.3.6.1.4.1.9.10.24.3.1";
  }

  smiv2:alias "ciscoVpdnMgmtMIBGroups" {
    smiv2:oid "1.3.6.1.4.1.9.10.24.3.2";
  }

}
