/*
 * Generated by confdc --mib2yang-std
 * Source: mgmt/dmi/model/mib/src/TCP-MIB.mib
 */
/*
 * This YANG module has been generated by smidump 0.5.0:
 *
 *      smidump -f yang TCP-MIB
 *
 * Do not edit. Edit the source file instead!
 */

module TCP-MIB {

  namespace "urn:ietf:params:xml:ns:yang:smiv2:TCP-MIB";
  prefix TCP-MIB;

  import INET-ADDRESS-MIB {
    prefix "inet-address";
  }

  import ietf-inet-types {
    prefix "inet";
  }

  import ietf-yang-smiv2 {
    prefix "smiv2";
  }

  import ietf-yang-types {
    prefix "yang";
  }

  organization
   "IETF IPv6 MIB Revision Team
    http://www.ietf.org/html.charters/ipv6-charter.html";

  contact
   "Rajiv Raghunarayan (editor)
    
    Cisco Systems Inc.
    170 West Tasman Drive
    San Jose, CA 95134
    
    Phone: +1 408 853 9612
    Email: <raraghun@cisco.com>
    
    Send comments to <ipv6@ietf.org>";

  description
   "The MIB module for managing TCP implementations.
    
    Copyright (C) The Internet Society (2005). This version
    of this MIB module is a part of RFC 4022; see the RFC
    itself for full legal notices.";

  revision 2005-02-18 {
    description
     "IP version neutral revision, published as RFC 4022.";
  }

  revision 1994-11-01 {
    description
     "Initial SMIv2 version, published as RFC 2012.";
  }

  revision 1991-03-31 {
    description
     "The initial revision of this MIB module was part of
      MIB-II.";
  }


  container TCP-MIB {
    config false;

    container tcp {
      smiv2:oid "1.3.6.1.2.1.6";

      leaf tcpRtoAlgorithm {
        type enumeration {
          enum "other" {
            value "1";
          }
          enum "constant" {
            value "2";
          }
          enum "rsre" {
            value "3";
          }
          enum "vanj" {
            value "4";
          }
          enum "rfc2988" {
            value "5";
          }
        }
        description
         "The algorithm used to determine the timeout value used for
          retransmitting unacknowledged octets.";
        smiv2:max-access "read-only";
        smiv2:oid "1.3.6.1.2.1.6.1";
      }

      leaf tcpRtoMin {
        type int32 {
          range "0..2147483647";
        }
        units "milliseconds";
        description
         "The minimum value permitted by a TCP implementation for
          the retransmission timeout, measured in milliseconds.
          More refined semantics for objects of this type depend
          on the algorithm used to determine the retransmission
          timeout; in particular, the IETF standard algorithm
          rfc2988(5) provides a minimum value.";
        smiv2:max-access "read-only";
        smiv2:oid "1.3.6.1.2.1.6.2";
      }

      leaf tcpRtoMax {
        type int32 {
          range "0..2147483647";
        }
        units "milliseconds";
        description
         "The maximum value permitted by a TCP implementation for
          the retransmission timeout, measured in milliseconds.
          More refined semantics for objects of this type depend
          on the algorithm used to determine the retransmission
          timeout; in particular, the IETF standard algorithm
          rfc2988(5) provides an upper bound (as part of an
          adaptive backoff algorithm).";
        smiv2:max-access "read-only";
        smiv2:oid "1.3.6.1.2.1.6.3";
      }

      leaf tcpMaxConn {
        type int32 {
          range "-1..2147483647";
        }
        description
         "The limit on the total number of TCP connections the entity
          can support.  In entities where the maximum number of
          connections is dynamic, this object should contain the
          value -1.";
        smiv2:max-access "read-only";
        smiv2:oid "1.3.6.1.2.1.6.4";
      }

      leaf tcpActiveOpens {
        type yang:counter32;
        description
         "The number of times that TCP connections have made a direct
          transition to the SYN-SENT state from the CLOSED state.
          
          Discontinuities in the value of this counter are
          indicated via discontinuities in the value of sysUpTime.";
        smiv2:max-access "read-only";
        smiv2:oid "1.3.6.1.2.1.6.5";
      }

      leaf tcpPassiveOpens {
        type yang:counter32;
        description
         "The number of times TCP connections have made a direct
          transition to the SYN-RCVD state from the LISTEN state.
          
          Discontinuities in the value of this counter are
          indicated via discontinuities in the value of sysUpTime.";
        smiv2:max-access "read-only";
        smiv2:oid "1.3.6.1.2.1.6.6";
      }

      leaf tcpAttemptFails {
        type yang:counter32;
        description
         "The number of times that TCP connections have made a direct
          transition to the CLOSED state from either the SYN-SENT
          state or the SYN-RCVD state, plus the number of times that
          TCP connections have made a direct transition to the
          LISTEN state from the SYN-RCVD state.
          
          Discontinuities in the value of this counter are
          indicated via discontinuities in the value of sysUpTime.";
        smiv2:max-access "read-only";
        smiv2:oid "1.3.6.1.2.1.6.7";
      }

      leaf tcpEstabResets {
        type yang:counter32;
        description
         "The number of times that TCP connections have made a direct
          transition to the CLOSED state from either the ESTABLISHED
          state or the CLOSE-WAIT state.
          
          Discontinuities in the value of this counter are
          indicated via discontinuities in the value of sysUpTime.";
        smiv2:max-access "read-only";
        smiv2:oid "1.3.6.1.2.1.6.8";
      }

      leaf tcpCurrEstab {
        type yang:gauge32;
        description
         "The number of TCP connections for which the current state
          is either ESTABLISHED or CLOSE-WAIT.";
        smiv2:max-access "read-only";
        smiv2:oid "1.3.6.1.2.1.6.9";
      }

      leaf tcpInSegs {
        type yang:counter32;
        description
         "The total number of segments received, including those
          received in error.  This count includes segments received
          on currently established connections.
          
          Discontinuities in the value of this counter are
          indicated via discontinuities in the value of sysUpTime.";
        smiv2:max-access "read-only";
        smiv2:oid "1.3.6.1.2.1.6.10";
      }

      leaf tcpOutSegs {
        type yang:counter32;
        description
         "The total number of segments sent, including those on
          current connections but excluding those containing only
          retransmitted octets.
          
          Discontinuities in the value of this counter are
          indicated via discontinuities in the value of sysUpTime.";
        smiv2:max-access "read-only";
        smiv2:oid "1.3.6.1.2.1.6.11";
      }

      leaf tcpRetransSegs {
        type yang:counter32;
        description
         "The total number of segments retransmitted; that is, the
          number of TCP segments transmitted containing one or more
          previously transmitted octets.
          
          Discontinuities in the value of this counter are
          indicated via discontinuities in the value of sysUpTime.";
        smiv2:max-access "read-only";
        smiv2:oid "1.3.6.1.2.1.6.12";
      }

      leaf tcpInErrs {
        type yang:counter32;
        description
         "The total number of segments received in error (e.g., bad
          TCP checksums).
          
          Discontinuities in the value of this counter are
          indicated via discontinuities in the value of sysUpTime.";
        smiv2:max-access "read-only";
        smiv2:oid "1.3.6.1.2.1.6.14";
      }

      leaf tcpOutRsts {
        type yang:counter32;
        description
         "The number of TCP segments sent containing the RST flag.
          
          Discontinuities in the value of this counter are
          indicated via discontinuities in the value of sysUpTime.";
        smiv2:max-access "read-only";
        smiv2:oid "1.3.6.1.2.1.6.15";
      }

      leaf tcpHCInSegs {
        type yang:counter64;
        description
         "The total number of segments received, including those
          received in error.  This count includes segments received
          
          on currently established connections.  This object is
          the 64-bit equivalent of tcpInSegs.
          
          Discontinuities in the value of this counter are
          indicated via discontinuities in the value of sysUpTime.";
        smiv2:max-access "read-only";
        smiv2:oid "1.3.6.1.2.1.6.17";
      }

      leaf tcpHCOutSegs {
        type yang:counter64;
        description
         "The total number of segments sent, including those on
          current connections but excluding those containing only
          retransmitted octets.  This object is the 64-bit
          equivalent of tcpOutSegs.
          
          Discontinuities in the value of this counter are
          indicated via discontinuities in the value of sysUpTime.";
        smiv2:max-access "read-only";
        smiv2:oid "1.3.6.1.2.1.6.18";
      }
    }

    container tcpConnTable {
      status deprecated;
      description
       "A table containing information about existing IPv4-specific
        TCP connections or listeners.  This table has been
        deprecated in favor of the version neutral
        tcpConnectionTable.";
      smiv2:oid "1.3.6.1.2.1.6.13";

      list tcpConnEntry {
        key "tcpConnLocalAddress tcpConnLocalPort tcpConnRemAddress tcpConnRemPort";
        status deprecated;
        description
         "A conceptual row of the tcpConnTable containing information
          about a particular current IPv4 TCP connection.  Each row
          of this table is transient in that it ceases to exist when
          (or soon after) the connection makes the transition to the
          CLOSED state.";
        smiv2:oid "1.3.6.1.2.1.6.13.1";

        leaf tcpConnState {
          type enumeration {
            enum "closed" {
              value "1";
            }
            enum "listen" {
              value "2";
            }
            enum "synSent" {
              value "3";
            }
            enum "synReceived" {
              value "4";
            }
            enum "established" {
              value "5";
            }
            enum "finWait1" {
              value "6";
            }
            enum "finWait2" {
              value "7";
            }
            enum "closeWait" {
              value "8";
            }
            enum "lastAck" {
              value "9";
            }
            enum "closing" {
              value "10";
            }
            enum "timeWait" {
              value "11";
            }
            enum "deleteTCB" {
              value "12";
            }
          }
          status deprecated;
          description
           "The state of this TCP connection.
            
            The only value that may be set by a management station is
            deleteTCB(12).  Accordingly, it is appropriate for an agent
            to return a `badValue' response if a management station
            attempts to set this object to any other value.
            
            If a management station sets this object to the value
            deleteTCB(12), then the TCB (as defined in [RFC793]) of
            the corresponding connection on the managed node is
            deleted, resulting in immediate termination of the
            connection.
            
            As an implementation-specific option, a RST segment may be
            sent from the managed node to the other TCP endpoint (note,
            however, that RST segments are not sent reliably).";
          smiv2:max-access "read-write";
          smiv2:oid "1.3.6.1.2.1.6.13.1.1";
        }

        leaf tcpConnLocalAddress {
          type inet:ipv4-address;
          status deprecated;
          description
           "The local IP address for this TCP connection.  In the case
            of a connection in the listen state willing to
            accept connections for any IP interface associated with the
            node, the value 0.0.0.0 is used.";
          smiv2:max-access "read-only";
          smiv2:oid "1.3.6.1.2.1.6.13.1.2";
        }

        leaf tcpConnLocalPort {
          type int32 {
            range "0..65535";
          }
          status deprecated;
          description
           "The local port number for this TCP connection.";
          smiv2:max-access "read-only";
          smiv2:oid "1.3.6.1.2.1.6.13.1.3";
        }

        leaf tcpConnRemAddress {
          type inet:ipv4-address;
          status deprecated;
          description
           "The remote IP address for this TCP connection.";
          smiv2:max-access "read-only";
          smiv2:oid "1.3.6.1.2.1.6.13.1.4";
        }

        leaf tcpConnRemPort {
          type int32 {
            range "0..65535";
          }
          status deprecated;
          description
           "The remote port number for this TCP connection.";
          smiv2:max-access "read-only";
          smiv2:oid "1.3.6.1.2.1.6.13.1.5";
        }
      }
    }

    container tcpConnectionTable {
      description
       "A table containing information about existing TCP
        connections.  Note that unlike earlier TCP MIBs, there
        is a separate table for connections in the LISTEN state.";
      smiv2:oid "1.3.6.1.2.1.6.19";

      list tcpConnectionEntry {
        key "tcpConnectionLocalAddressType tcpConnectionLocalAddress tcpConnectionLocalPort tcpConnectionRemAddressType tcpConnectionRemAddress tcpConnectionRemPort";
        description
         "A conceptual row of the tcpConnectionTable containing
          information about a particular current TCP connection.
          Each row of this table is transient in that it ceases to
          exist when (or soon after) the connection makes the
          transition to the CLOSED state.";
        smiv2:oid "1.3.6.1.2.1.6.19.1";

        leaf tcpConnectionLocalAddressType {
          type inet-address:InetAddressType;
          description
           "The address type of tcpConnectionLocalAddress.";
          smiv2:max-access "not-accessible";
          smiv2:oid "1.3.6.1.2.1.6.19.1.1";
        }

        leaf tcpConnectionLocalAddress {
          type inet-address:InetAddress;
          description
           "The local IP address for this TCP connection.  The type
            of this address is determined by the value of
            tcpConnectionLocalAddressType.
            
            As this object is used in the index for the
            tcpConnectionTable, implementors should be
            careful not to create entries that would result in OIDs
            with more than 128 subidentifiers; otherwise the information
            cannot be accessed by using SNMPv1, SNMPv2c, or SNMPv3.";
          smiv2:max-access "not-accessible";
          smiv2:oid "1.3.6.1.2.1.6.19.1.2";
        }

        leaf tcpConnectionLocalPort {
          type inet:port-number;
          description
           "The local port number for this TCP connection.";
          smiv2:max-access "not-accessible";
          smiv2:oid "1.3.6.1.2.1.6.19.1.3";
        }

        leaf tcpConnectionRemAddressType {
          type inet-address:InetAddressType;
          description
           "The address type of tcpConnectionRemAddress.";
          smiv2:max-access "not-accessible";
          smiv2:oid "1.3.6.1.2.1.6.19.1.4";
        }

        leaf tcpConnectionRemAddress {
          type inet-address:InetAddress;
          description
           "The remote IP address for this TCP connection.  The type
            of this address is determined by the value of
            tcpConnectionRemAddressType.
            
            As this object is used in the index for the
            tcpConnectionTable, implementors should be
            careful not to create entries that would result in OIDs
            with more than 128 subidentifiers; otherwise the information
            cannot be accessed by using SNMPv1, SNMPv2c, or SNMPv3.";
          smiv2:max-access "not-accessible";
          smiv2:oid "1.3.6.1.2.1.6.19.1.5";
        }

        leaf tcpConnectionRemPort {
          type inet:port-number;
          description
           "The remote port number for this TCP connection.";
          smiv2:max-access "not-accessible";
          smiv2:oid "1.3.6.1.2.1.6.19.1.6";
        }

        leaf tcpConnectionState {
          type enumeration {
            enum "closed" {
              value "1";
            }
            enum "listen" {
              value "2";
            }
            enum "synSent" {
              value "3";
            }
            enum "synReceived" {
              value "4";
            }
            enum "established" {
              value "5";
            }
            enum "finWait1" {
              value "6";
            }
            enum "finWait2" {
              value "7";
            }
            enum "closeWait" {
              value "8";
            }
            enum "lastAck" {
              value "9";
            }
            enum "closing" {
              value "10";
            }
            enum "timeWait" {
              value "11";
            }
            enum "deleteTCB" {
              value "12";
            }
          }
          description
           "The state of this TCP connection.
            
            The value listen(2) is included only for parallelism to the
            old tcpConnTable and should not be used.  A connection in
            LISTEN state should be present in the tcpListenerTable.
            
            The only value that may be set by a management station is
            deleteTCB(12).  Accordingly, it is appropriate for an agent
            to return a `badValue' response if a management station
            attempts to set this object to any other value.
            
            If a management station sets this object to the value
            deleteTCB(12), then the TCB (as defined in [RFC793]) of
            the corresponding connection on the managed node is
            deleted, resulting in immediate termination of the
            connection.
            
            As an implementation-specific option, a RST segment may be
            sent from the managed node to the other TCP endpoint (note,
            however, that RST segments are not sent reliably).";
          smiv2:max-access "read-write";
          smiv2:oid "1.3.6.1.2.1.6.19.1.7";
        }

        leaf tcpConnectionProcess {
          type uint32;
          description
           "The system's process ID for the process associated with
            this connection, or zero if there is no such process.  This
            value is expected to be the same as HOST-RESOURCES-MIB::
            hrSWRunIndex or SYSAPPL-MIB::sysApplElmtRunIndex for some
            row in the appropriate tables.";
          smiv2:max-access "read-only";
          smiv2:oid "1.3.6.1.2.1.6.19.1.8";
        }
      }
    }

    container tcpListenerTable {
      description
       "A table containing information about TCP listeners.  A
        listening application can be represented in three
        possible ways:
        
        1. An application that is willing to accept both IPv4 and
           IPv6 datagrams is represented by
        
           a tcpListenerLocalAddressType of unknown (0) and
           a tcpListenerLocalAddress of ''h (a zero-length
           octet-string).
        
        2. An application that is willing to accept only IPv4 or
           IPv6 datagrams is represented by a
           tcpListenerLocalAddressType of the appropriate address
           type and a tcpListenerLocalAddress of '0.0.0.0' or '::'
           respectively.
        
        3. An application that is listening for data destined
           only to a specific IP address, but from any remote
           system, is represented by a tcpListenerLocalAddressType
           of an appropriate address type, with
           tcpListenerLocalAddress as the specific local address.
        
        NOTE: The address type in this table represents the
        address type used for the communication, irrespective
        of the higher-layer abstraction.  For example, an
        application using IPv6 'sockets' to communicate via
        IPv4 between ::ffff:10.0.0.1 and ::ffff:10.0.0.2 would
        use InetAddressType ipv4(1)).";
      smiv2:oid "1.3.6.1.2.1.6.20";

      list tcpListenerEntry {
        key "tcpListenerLocalAddressType tcpListenerLocalAddress tcpListenerLocalPort";
        description
         "A conceptual row of the tcpListenerTable containing
          information about a particular TCP listener.";
        smiv2:oid "1.3.6.1.2.1.6.20.1";

        leaf tcpListenerLocalAddressType {
          type inet-address:InetAddressType;
          description
           "The address type of tcpListenerLocalAddress.  The value
            should be unknown (0) if connection initiations to all
            local IP addresses are accepted.";
          smiv2:max-access "not-accessible";
          smiv2:oid "1.3.6.1.2.1.6.20.1.1";
        }

        leaf tcpListenerLocalAddress {
          type inet-address:InetAddress;
          description
           "The local IP address for this TCP connection.
            
            The value of this object can be represented in three
            possible ways, depending on the characteristics of the
            listening application:
            
            1. For an application willing to accept both IPv4 and
               IPv6 datagrams, the value of this object must be
               ''h (a zero-length octet-string), with the value
               of the corresponding tcpListenerLocalAddressType
               object being unknown (0).
            
            2. For an application willing to accept only IPv4 or
               IPv6 datagrams, the value of this object must be
               '0.0.0.0' or '::' respectively, with
               tcpListenerLocalAddressType representing the
               appropriate address type.
            
            3. For an application which is listening for data
               destined only to a specific IP address, the value
               of this object is the specific local address, with
               tcpListenerLocalAddressType representing the
               appropriate address type.
            
            As this object is used in the index for the
            tcpListenerTable, implementors should be
            careful not to create entries that would result in OIDs
            with more than 128 subidentifiers; otherwise the information
            cannot be accessed, using SNMPv1, SNMPv2c, or SNMPv3.";
          smiv2:max-access "not-accessible";
          smiv2:oid "1.3.6.1.2.1.6.20.1.2";
        }

        leaf tcpListenerLocalPort {
          type inet:port-number;
          description
           "The local port number for this TCP connection.";
          smiv2:max-access "not-accessible";
          smiv2:oid "1.3.6.1.2.1.6.20.1.3";
        }

        leaf tcpListenerProcess {
          type uint32;
          description
           "The system's process ID for the process associated with
            this listener, or zero if there is no such process.  This
            value is expected to be the same as HOST-RESOURCES-MIB::
            hrSWRunIndex or SYSAPPL-MIB::sysApplElmtRunIndex for some
            row in the appropriate tables.";
          smiv2:max-access "read-only";
          smiv2:oid "1.3.6.1.2.1.6.20.1.4";
        }
      }
    }
  }

  smiv2:alias "tcp" {
    smiv2:oid "1.3.6.1.2.1.6";
  }

  smiv2:alias "tcpMIB" {
    smiv2:oid "1.3.6.1.2.1.49";
  }

  smiv2:alias "tcpMIBConformance" {
    smiv2:oid "1.3.6.1.2.1.49.2";
  }

  smiv2:alias "tcpMIBCompliances" {
    smiv2:oid "1.3.6.1.2.1.49.2.1";
  }

  smiv2:alias "tcpMIBGroups" {
    smiv2:oid "1.3.6.1.2.1.49.2.2";
  }

}
