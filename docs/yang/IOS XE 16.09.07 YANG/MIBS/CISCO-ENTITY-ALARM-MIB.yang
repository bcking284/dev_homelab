/*
 * Generated by confdc --mib2yang-std
 * Source: mgmt/dmi/model/mib/src/CISCO-ENTITY-ALARM-MIB.mib
 */
/*
 * This YANG module has been generated by smidump 0.5.0:
 *
 *      smidump -f yang CISCO-ENTITY-ALARM-MIB
 *
 * Do not edit. Edit the source file instead!
 */

module CISCO-ENTITY-ALARM-MIB {

  namespace "urn:ietf:params:xml:ns:yang:smiv2:CISCO-ENTITY-ALARM-MIB";
  prefix CISCO-ENTITY-ALARM-MIB;

  import ENTITY-MIB {
    prefix "entity-mib";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA 95134
    
    Tel: +1 800 553-NETS
    
    E-mail: cs-dslam@cisco.com";

  description
   "This MIB module defines the managed objects that support the
    monitoring of alarms generated by physical entities contained
    by the system, including chassis, slots, modules, ports, power
    supplies, and fans.  In order to monitor alarms generated by a
    physical entity, it must be represented by a row in the
    entPhysicalTable (see ENTITY-MIB).";

  revision 1999-07-06 {
    description
     "[Revision added by libsmi due to a LAST-UPDATED clause.]";
  }

  typedef AlarmType {
    type int32 {
      range "0..255";
    }
    description
     "An arbitrary integer value that uniquely identifies an event
      relative to a physical entity contained by a system.";
  }

  typedef AlarmSeverity {
    type enumeration {
      enum "critical" {
        value "1";
      }
      enum "major" {
        value "2";
      }
      enum "minor" {
        value "3";
      }
      enum "info" {
        value "4";
      }
    }
    description
     "Each alarm type defined by a vendor type employed by the
      system has an associated severity.  Bellcore TR-NWT-000474
      defines these severities as follows:
      
      'critical'  An alarm used to indicate a severe, service-
                  affecting condition has occurred and that immediate
                  corrective action is imperative, regardless of the
                  time of day or day of the week.
      
      'major'     An alarm used for hardware or software conditions
                  that indicate a serious disruption of service or the
                  malfunctioning or failure of important hardware.
                  These troubles require the immediate attention and
                  response of a technician to restore or maintain
                  system capability.  The urgency is less than in
                  critical situations because of a lesser immediate
                  or impending effect on service or system
                  performance.
      
      'minor'     An alarm used for troubles that do not have a
                  serious effect on service to customers or for
                  troubles in hardware that are not essential to
                  the operation of the system.
      
      'info'      An indication used to raise attention to a condition
                  that could possibly be an impending problem or to 
                  notify the customer of an event that improves
                  operation.";
    reference
     "Bellcore Technical Reference TR-NWT-000474 Issue 4, December
      1993, OTGR Section 4.  Network Maintenance: Alarm and Control -
      Network Element.";
  }

  typedef AlarmSeverityOrZero {
    type int32 {
      range "0..4";
    }
    description
     "A value of either '0' or a valid alarm severity.";
  }

  typedef AlarmList {
    type binary {
      length "0..32";
    }
    description
     "For each unique type of physical entity (i.e., for each set
      of physical entities sharing a unique entPhysicalVendorType
      OID), there an exists unique alarm space.  Observe that it
      is not necessary that all the alarms within a space be defined.
      
      An OCTET STRING represents an alarm list, in which each
      bit represents an alarm type.  The bits in the first octet
      represent alarm types identified by the integer values 1
      through 8, inclusive, The bits in the second octet represent
      alarm types identified by the integer values 9 through 16,
      inclusive, and so forth.  The least significant bit of an
      octet represents the alarm type identified by the lowest
      integer value, and the most significant bit represents the
      alarm type identified by the highest integer value.  The
      figure shown below illustrates the format of an alarm list.
      
       Octet 1             Octet 32
      
       7 6 5 4 3 2 1 0     7 6 5 4 3 2 1 0
      +-+-+-+-+-+-+-+-+   +-+-+-+-+-+-+-+-+
      |               |...|               |
      +-+-+-+-+-+-+-+-+   +-+-+-+-+-+-+-+-+
       | | | | | | | |     | | | | | | | |
       | | | | | | | |     | | | | | | | +- Alarm 248
       | | | | | | | |     | | | | | | +--- Alarm 249
       | | | | | | | |     | | | | | +----- Alarm 250
       | | | | | | | |     | | | | +------- Alarm 251
       | | | | | | | |     | | | +--------- Alarm 252
       | | | | | | | |     | | +----------- Alarm 253
       | | | | | | | |     | +------------- Alarm 254
       | | | | | | | |     +--------------- Alarm 255
       | | | | | | | |                          :
       | | | | | | | |                          :
       | | | | | | | +--------------------- Alarm 0
       | | | | | | +----------------------- Alarm 1
       | | | | | +------------------------- Alarm 2
       | | | | +--------------------------- Alarm 3
       | | | +----------------------------- Alarm 4
       | | +------------------------------- Alarm 5
       | +--------------------------------- Alarm 6
       +----------------------------------- Alarm 7
      
      An alarm list of length N, where N < 32, represents an alarm
      list for which alarms N*8 through 255 have the value of '0'.
      A special case is an alarm list having a length of '0', which
      represents an alarm list of all zeros.";
  }

  typedef AlarmFilterProfileType {
    type uint32;
    description
     "An integer value that uniquely identifies an alarm filter
      profile.";
  }


  container CISCO-ENTITY-ALARM-MIB {
    config false;

    container ceAlarmMonitoring {
      smiv2:oid "1.3.6.1.4.1.9.9.138.1.2";

      leaf ceAlarmCriticalCount {
        type yang:gauge32;
        description
         "The value of this object specifies the number of alarms
          currently asserted with a severity of 'critical'.";
        smiv2:max-access "read-only";
        smiv2:oid "1.3.6.1.4.1.9.9.138.1.2.1";
      }

      leaf ceAlarmMajorCount {
        type yang:gauge32;
        description
         "The value of this object specifies the number of alarms
          currently asserted with a severity of 'major'.";
        smiv2:max-access "read-only";
        smiv2:oid "1.3.6.1.4.1.9.9.138.1.2.2";
      }

      leaf ceAlarmMinorCount {
        type yang:gauge32;
        description
         "The value of this object specifies the number of alarms
          currently asserted with a severity of 'minor'.";
        smiv2:max-access "read-only";
        smiv2:oid "1.3.6.1.4.1.9.9.138.1.2.3";
      }

      leaf ceAlarmCutOff {
        type boolean;
        description
         "If the management client writes a value of 'true' to this
          object, the agent stops signalling all external audible alarms
          under the control of the agent.  Reading this object should
          always result in a value of 'false'.
          
          Observe that alarm cutoff does not have an effect on monitoring,
          history logging, generation of notifications, or syslog message
          generation.  It also does not prevent the agent from signalling
          external audible alarms for alarms asserted after alarm-cutoff.
          
          This object emulates the 'alarm cut-off' mechanism typically
          installed in a central office (e.g., a big red button).  Observe
          this object should neither affect external visual alarms under
          the control of the agent, nor should it affect the current state
          of alarms being asserted by the system.";
        smiv2:max-access "read-write";
        smiv2:oid "1.3.6.1.4.1.9.9.138.1.2.4";
      }
    }

    container ceAlarmHistory {
      smiv2:oid "1.3.6.1.4.1.9.9.138.1.3";

      leaf ceAlarmHistTableSize {
        type int32 {
          range "0..500";
        }
        description
         "This object specifies the number of entries that the 
          ceAlarmHistTable can contain.  When a physical entity
          generates an unfiltered alarm, and the capacity of the
          ceAlarmHistTable has reached the value specified by
          this object, then the agent deletes the oldest entity in
          order to accommodate the new entry. A value of '0' prevents
          any history from being retained.  ";
        smiv2:max-access "read-write";
        smiv2:oid "1.3.6.1.4.1.9.9.138.1.3.1";
      }

      leaf ceAlarmHistLastIndex {
        type uint32;
        description
         "This object specifies the value of the ceAlarmHistIndex
          object corresponding to the last entry added to the table by the
          agent.
          
          If the management client uses the notifications defined by this
          module, then it can poll this object to determine whether it has
          missed a notification sent by the agent.";
        smiv2:max-access "read-only";
        smiv2:oid "1.3.6.1.4.1.9.9.138.1.3.2";
      }
    }

    container ceAlarmFiltering {
      smiv2:oid "1.3.6.1.4.1.9.9.138.1.4";

      leaf ceAlarmNotifiesEnable {
        type CISCO-ENTITY-ALARM-MIB:AlarmSeverityOrZero;
        description
         "This object specifies a severity threshold governing the
          generation of ceAlarmAsserted and ceAlarmCleared
          notifications.  For example, if the value of this object is
          set to 'major', then the agent generates these notifications
          if and only if the severity of the alarm being indicated is
          'major' or 'critical'.  The value of '0' disables the 
          generation of notifications.
          
          Observe that this setting overrides the value of the 
          ceAlarmFilterNotifiesEnabled object.
          
          This object affects notification generation only; that is, it
          does not affect monitoring, history logging, and syslog message
          generation.";
        smiv2:max-access "read-write";
        smiv2:oid "1.3.6.1.4.1.9.9.138.1.4.1";
      }

      leaf ceAlarmSyslogEnable {
        type CISCO-ENTITY-ALARM-MIB:AlarmSeverityOrZero;
        description
         "This object specifies a severity threshold governing the
          generation of syslog messages corresponding to alarms.  For
          example, if the value of this object is set to 'major', then
          the agent generates these a syslog message if and only if the
          severity of the alarm being indicated is 'major' or 'critical'.
          The value of '0' disables the generation of syslog messages
          corresponding to alarms.
          
          Observe that this setting overrides the value of the 
          ceAlarmFilterSyslogEnabled object.
          
          This object affects syslog message generation only; that is, it
          does not have an effect on monitoring, history logging, and
          generation of notifications.";
        smiv2:max-access "read-write";
        smiv2:oid "1.3.6.1.4.1.9.9.138.1.4.2";
      }

      leaf ceAlarmFilterProfileIndexNext {
        type CISCO-ENTITY-ALARM-MIB:AlarmFilterProfileType;
        description
         "This object contains an appropriate value to be used
          for ceAlarmFilterIndex when creating entries in the
          ceAlarmFilterProfileTable.  The value '0' indicates
          that no unassigned entries are available.  To obtain
          a ceAlarmFilterIndex, the management client issues
          a get request.  The agent has the responsibility of 
          modifying the value of this object following each 
          successful get request.";
        smiv2:max-access "read-only";
        smiv2:oid "1.3.6.1.4.1.9.9.138.1.4.3";
      }
    }

    container ceAlarmDescrMapTable {
      description
       "For each type of entity (represented entPhysicalVendorType
        OID), this table contains a mapping between a unique 
        ceAlarmDescrIndex and entPhysicalvendorType OID.";
      smiv2:oid "1.3.6.1.4.1.9.9.138.1.1.1";

      list ceAlarmDescrMapEntry {
        key "ceAlarmDescrIndex";
        description
         "A mapping between an alarm description and a vendor type.";
        smiv2:oid "1.3.6.1.4.1.9.9.138.1.1.1.1";

        leaf ceAlarmDescrIndex {
          type uint32;
          description
           "This object uniquely identifies an alarm description.";
          smiv2:max-access "not-accessible";
          smiv2:oid "1.3.6.1.4.1.9.9.138.1.1.1.1.1";
        }

        leaf ceAlarmDescrVendorType {
          type snmpv2-tc:AutonomousType;
          description
           "This object specifies an object identifier (typically an
            enterprise-specific OID) that uniquely identifies the vendor
            type of those physical entities that this alarm description
            applies to.";
          smiv2:max-access "read-only";
          smiv2:oid "1.3.6.1.4.1.9.9.138.1.1.1.1.2";
        }
      }
    }

    container ceAlarmDescrTable {
      description
       "This table contains a description for each alarm type
        defined by each vendor type employed by the system.
        Observe that this table is sparse in nature, as it is
        rarely the case that a physical entity type needs to 
        define every alarm in its alarm space.";
      smiv2:oid "1.3.6.1.4.1.9.9.138.1.1.2";

      list ceAlarmDescrEntry {
        key "ceAlarmDescrIndex ceAlarmDescrAlarmType";
        description
         "A collection of attributes that describe an alarm type.";
        smiv2:oid "1.3.6.1.4.1.9.9.138.1.1.2.1";

        leaf ceAlarmDescrIndex {
          type leafref {
            path "/CISCO-ENTITY-ALARM-MIB:CISCO-ENTITY-ALARM-MIB/CISCO-ENTITY-ALARM-MIB:ceAlarmDescrMapTable/CISCO-ENTITY-ALARM-MIB:ceAlarmDescrMapEntry/CISCO-ENTITY-ALARM-MIB:ceAlarmDescrIndex";
          }
        }

        leaf ceAlarmDescrAlarmType {
          type CISCO-ENTITY-ALARM-MIB:AlarmType;
          description
           "This object specifies the alarm type being described.";
          smiv2:max-access "not-accessible";
          smiv2:oid "1.3.6.1.4.1.9.9.138.1.1.2.1.1";
        }

        leaf ceAlarmDescrSeverity {
          type CISCO-ENTITY-ALARM-MIB:AlarmSeverityOrZero;
          description
           "This object specifies the severity associated with the
            alarm type.
            
            An implementation may chose to not allow dynamic severity
            assignment, in which case it would restrict access to this
            object to be read-only.
            
            If an implementation allows dynamic severity assignment, then
            a management client can revert to the default severity by
            writing the value '0' to this object.
            
            There exists a class of systems that should implement dynamic
            severity assignment.  For example, consider a DSLAM (Digital
            Subscriber Loop Access Multiplexor) designed for both the
            central office and pedestal environments.  A 'pedestal' is
            typically a dark-green metal box mounted on a concrete or stone
            foundation in which carrier-class companies house equipment.
            The central office typically controls the temperature and
            humidity of the environment, reducing reliance on a system's
            fans.  Thus, the customer probably has a desire to reduce the 
            severity of alarms indicating the failure of a fan.  However, a
            pedestal environment has a much greater reliance on a system's
            fans.  Thus, the customer probably has a desire to increase the
            severity of alarms indicating the failure of a fan.";
          smiv2:max-access "read-write";
          smiv2:oid "1.3.6.1.4.1.9.9.138.1.1.2.1.2";
        }

        leaf ceAlarmDescrText {
          type snmp-framework:SnmpAdminString;
          description
           "This object specifies a human-readable message describing
            the alarm.";
          smiv2:max-access "read-only";
          smiv2:oid "1.3.6.1.4.1.9.9.138.1.1.2.1.3";
        }
      }
    }

    container ceAlarmTable {
      description
       "This table specifies alarm control and status information
        related to each physical entity contained by the system,
        including the alarms currently being asserted by each physical
        entity capable of generating alarms.";
      smiv2:oid "1.3.6.1.4.1.9.9.138.1.2.5";

      list ceAlarmEntry {
        key "entPhysicalIndex";
        description
         "Alarm control and status information related to the 
          corresponding physical entity, including a list of those
          alarms currently being asserted by that physical entity.";
        smiv2:oid "1.3.6.1.4.1.9.9.138.1.2.5.1";

        leaf entPhysicalIndex {
          type leafref {
            path "/entity-mib:ENTITY-MIB/entity-mib:entPhysicalTable/entity-mib:entPhysicalEntry/entity-mib:entPhysicalIndex";
          }
        }

        leaf ceAlarmFilterProfile {
          type CISCO-ENTITY-ALARM-MIB:AlarmFilterProfileType;
          description
           "This object specifies the alarm filter profile associated
            with the corresponding physical entity.  An alarm filter
            profile controls which alarm types the agent will monitor
            and signal for the corresponding physical entity.
            
            If the value of this object is '0', then the agent monitors
            and signals all alarms associated with the corresponding
            physical entity.";
          smiv2:max-access "read-write";
          smiv2:oid "1.3.6.1.4.1.9.9.138.1.2.5.1.1";
        }

        leaf ceAlarmSeverity {
          type CISCO-ENTITY-ALARM-MIB:AlarmSeverityOrZero;
          description
           "This object specifies the highest severity alarm currently
            being asserted by the corresponding physical entity.  A value
            of '0' indicates that there the corresponding physical entity
            currently is not asserting any alarms.";
          smiv2:max-access "read-only";
          smiv2:oid "1.3.6.1.4.1.9.9.138.1.2.5.1.2";
        }

        leaf ceAlarmList {
          type CISCO-ENTITY-ALARM-MIB:AlarmList;
          description
           "This object specifies those alarms currently being asserted
            by the corresponding physical entity.  Note, an alarm indicates
            a condition, not an event.  An alarm has two states:
            
                'asserted'  Indicates that the condition described by the
                            alarm exists.
            
                'cleared'   Indicates that the condition described by the
                            alarm does not exist.
            
            For example, a slot in a chassis may define an alarm that
            specifies whether the slot contains a module.  At the time of
            module insertion, the physical entity corresponding to the slot
            asserts this alarm, and the alarm remains asserted until the 
            slot becomes empty.
            
            If an alarm is being asserted by the physical entity, then the
            corresponding bit in the alarm list is set to a one. Observe
            that if the physical entity is not currently asserting any
            alarms, then the list will have a length of zero.";
          smiv2:max-access "read-only";
          smiv2:oid "1.3.6.1.4.1.9.9.138.1.2.5.1.3";
        }
      }
    }

    container ceAlarmHistTable {
      description
       "This table contains a history of ceAlarmIndicate and
        ceAlarmClear traps generated by the agent.";
      smiv2:oid "1.3.6.1.4.1.9.9.138.1.3.3";

      list ceAlarmHistEntry {
        key "ceAlarmHistIndex";
        description
         "The information conveyed by a ceAlarmIndicate or
          ceAlarmClear trap.";
        smiv2:oid "1.3.6.1.4.1.9.9.138.1.3.3.1";

        leaf ceAlarmHistIndex {
          type uint32;
          description
           "An integer value uniquely identifying the entry in the table.
            The value of this object starts at '1' and monotonically
            increases for each alarm condition transition monitored by the
            agent.  If the value of this object is '4294967295', the agent
            will reset it to '1' upon monitoring the next alarm condition
            transition.";
          smiv2:max-access "not-accessible";
          smiv2:oid "1.3.6.1.4.1.9.9.138.1.3.3.1.1";
        }

        leaf ceAlarmHistType {
          type enumeration {
            enum "asserted" {
              value "1";
            }
            enum "cleared" {
              value "2";
            }
          }
          description
           "This object specifies whether the agent created the entry as
            the result of an alarm being asserted or cleared.";
          smiv2:max-access "read-only";
          smiv2:oid "1.3.6.1.4.1.9.9.138.1.3.3.1.2";
        }

        leaf ceAlarmHistEntPhysicalIndex {
          type entity-mib:PhysicalIndex;
          description
           "This object specifies the physical entity that generated
            the alarm.";
          smiv2:max-access "read-only";
          smiv2:oid "1.3.6.1.4.1.9.9.138.1.3.3.1.3";
        }

        leaf ceAlarmHistAlarmType {
          type CISCO-ENTITY-ALARM-MIB:AlarmType;
          description
           "This object specifies the type of alarm generated.";
          smiv2:max-access "read-only";
          smiv2:oid "1.3.6.1.4.1.9.9.138.1.3.3.1.4";
        }

        leaf ceAlarmHistSeverity {
          type CISCO-ENTITY-ALARM-MIB:AlarmSeverity;
          description
           "This object specifies the severity of the alarm generated.";
          smiv2:max-access "read-only";
          smiv2:oid "1.3.6.1.4.1.9.9.138.1.3.3.1.5";
        }

        leaf ceAlarmHistTimeStamp {
          type yang:timestamp;
          description
           "This object specifies the value of the sysUpTime object at
            the time the alarm was generated.";
          smiv2:max-access "read-only";
          smiv2:oid "1.3.6.1.4.1.9.9.138.1.3.3.1.6";
        }
      }
    }

    container ceAlarmFilterProfileTable {
      description
       "This table contains a list of alarm filter profiles.";
      smiv2:oid "1.3.6.1.4.1.9.9.138.1.4.4";

      list ceAlarmFilterProfileEntry {
        key "ceAlarmFilterIndex";
        description
         "When a physical entity asserts/clears an alarm AND the
          ceAlarmFilterProfile object is not '0', the agent applies
          the specified alarm filter profile in processing the alarm.
          The agent uses the following procedure in processing the
          transition of an alarm condition of a given type:
          
          1)  If the alarm list specified by the alarm filter profile's
              ceAlarmFilterAlarmsEnabled object specifies that the alarm
              type is disabled, then the agent performs no further
              processing.
          
          2)  The agent creates an entry in the ceAlarmHistTable.
          
          3)  If the alarm list specified by the alarm filter profile's 
              ceAlarmFilterNotifiesEnabled object specifies that the alarm
              type is enabled, then the agent generates the appropriate
              notification.
          
          4)  If the alarm list specified by the alarm filter profile's
              ceAlarmFilterSyslogEnabled object specifies that the alarm
              type is enabled, then the agent generates the appropriate
              syslog message.";
        smiv2:oid "1.3.6.1.4.1.9.9.138.1.4.4.1";

        leaf ceAlarmFilterIndex {
          type CISCO-ENTITY-ALARM-MIB:AlarmFilterProfileType;
          description
           "This object uniquely identifies the alarm filter profile.";
          smiv2:max-access "not-accessible";
          smiv2:oid "1.3.6.1.4.1.9.9.138.1.4.4.1.1";
        }

        leaf ceAlarmFilterStatus {
          type snmpv2-tc:RowStatus;
          description
           "This object facilitates the creation, modification, or 
            deletion of a conceptual row in this table.
            
            A management client can create a conceptual row in this
            table by setting this object to 'createAndWait' or 
            'createAndGo'.  If a request to create a conceptual row
            in this table fails, then the system is not capable of
            supporting any more alarm filters.
            
            Before modifying a conceptual row in this table, the 
            management client must set this object to 'notInService'.
            After modifying a conceptual row in this table, the 
            management client must set this object to 'active'.
            This operation causes the modifications made to an
            alarm filter profile to take effect.
            
            An implementation should not allow a conceptual row in
            this table to be deleted if one or more physical entities
            reference it.";
          smiv2:max-access "read-write";
          smiv2:oid "1.3.6.1.4.1.9.9.138.1.4.4.1.2";
        }

        leaf ceAlarmFilterAlias {
          type snmpv2-tc:DisplayString;
          description
           "This object specifies an arbitrary name associated with the
            alarm filter profile by the management client, and provides
            a non-volatile 'handle' for the alarm filter profile.
            
            On the first instantiation of an alarm filter profile, the
            value of this object is a zero-length string.  However, an
            agent may choose to set the value to a locally unique default
            value.
            
            If an implementation supports write access to this object,
            then the agent is responsible for ensuring the retention
            of any value written to this object until a management client
            deletes it.  The level of retention must span reboots and 
            reinitializations of the network management system, including
            those that result in different assignments to the value of
            the entPhysicalIndex associated with the physical entity.";
          smiv2:max-access "read-write";
          smiv2:oid "1.3.6.1.4.1.9.9.138.1.4.4.1.3";
        }

        leaf ceAlarmFilterAlarmsEnabled {
          type CISCO-ENTITY-ALARM-MIB:AlarmList;
          description
           "This object specifies a list of alarms that are enabled.";
          smiv2:max-access "read-write";
          smiv2:oid "1.3.6.1.4.1.9.9.138.1.4.4.1.4";
        }

        leaf ceAlarmFilterNotifiesEnabled {
          type CISCO-ENTITY-ALARM-MIB:AlarmList;
          description
           "This object specifies a list of alarms for which notification
            generation is enabled.";
          smiv2:max-access "read-write";
          smiv2:oid "1.3.6.1.4.1.9.9.138.1.4.4.1.5";
        }

        leaf ceAlarmFilterSyslogEnabled {
          type CISCO-ENTITY-ALARM-MIB:AlarmList;
          description
           "This object specifies a list of alarms for which syslog
            message generation is enabled.";
          smiv2:max-access "read-write";
          smiv2:oid "1.3.6.1.4.1.9.9.138.1.4.4.1.6";
        }
      }
    }
  }

  notification ceAlarmAsserted {
    description
     "The agent generates this trap when a physical entity
      asserts an alarm.";
    smiv2:oid "1.3.6.1.4.1.9.9.138.2.0.1";

    container object-1 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistEntPhysicalIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistEntPhysicalIndex";
        }
      }
    }

    container object-2 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistAlarmType {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistAlarmType";
        }
      }
    }

    container object-3 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistSeverity {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistSeverity";
        }
      }
    }

    container object-4 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistTimeStamp {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistTimeStamp";
        }
      }
    }
  }

  notification ceAlarmCleared {
    description
     "The agent generates this trap when a physical entity
      clears a previously asserted alarm.";
    smiv2:oid "1.3.6.1.4.1.9.9.138.2.0.2";

    container object-1 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistEntPhysicalIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistEntPhysicalIndex";
        }
      }
    }

    container object-2 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistAlarmType {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistAlarmType";
        }
      }
    }

    container object-3 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistSeverity {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistSeverity";
        }
      }
    }

    container object-4 {

      leaf ceAlarmHistIndex {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistIndex";
        }
      }

      leaf ceAlarmHistTimeStamp {
        type leafref {
          path "/CISCO-ENTITY-ALARM-MIB:CISCO-ENTITY-ALARM-MIB/CISCO-ENTITY-ALARM-MIB:ceAlarmHistTable/CISCO-ENTITY-ALARM-MIB:ceAlarmHistEntry/CISCO-ENTITY-ALARM-MIB:ceAlarmHistTimeStamp";
        }
      }
    }
  }

  smiv2:alias "ciscoEntityAlarmMIB" {
    smiv2:oid "1.3.6.1.4.1.9.9.138";
  }

  smiv2:alias "ciscoEntityAlarmMIBObjects" {
    smiv2:oid "1.3.6.1.4.1.9.9.138.1";
  }

  smiv2:alias "ceAlarmDescription" {
    smiv2:oid "1.3.6.1.4.1.9.9.138.1.1";
  }

  smiv2:alias "ceAlarmMonitoring" {
    smiv2:oid "1.3.6.1.4.1.9.9.138.1.2";
  }

  smiv2:alias "ceAlarmHistory" {
    smiv2:oid "1.3.6.1.4.1.9.9.138.1.3";
  }

  smiv2:alias "ceAlarmFiltering" {
    smiv2:oid "1.3.6.1.4.1.9.9.138.1.4";
  }

  smiv2:alias "ciscoEntityAlarmMIBNotificationsPrefix" {
    smiv2:oid "1.3.6.1.4.1.9.9.138.2";
  }

  smiv2:alias "ciscoEntityAlarmMIBNotifications" {
    smiv2:oid "1.3.6.1.4.1.9.9.138.2.0";
  }

  smiv2:alias "ciscoEntityAlarmMIBConformance" {
    smiv2:oid "1.3.6.1.4.1.9.9.138.3";
  }

  smiv2:alias "ciscoEntityAlarmMIBCompliances" {
    smiv2:oid "1.3.6.1.4.1.9.9.138.3.1";
  }

  smiv2:alias "ciscoEntityAlarmMIBGroups" {
    smiv2:oid "1.3.6.1.4.1.9.9.138.3.2";
  }

}
