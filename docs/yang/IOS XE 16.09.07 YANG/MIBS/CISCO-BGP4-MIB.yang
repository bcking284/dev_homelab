/*
 * Generated by confdc --mib2yang-std
 * Source: mgmt/dmi/model/mib/src/CISCO-BGP4-MIB.mib
 */
/*
 * This YANG module has been generated by smidump 0.5.0:
 *
 *      smidump -f yang CISCO-BGP4-MIB
 *
 * Do not edit. Edit the source file instead!
 */

module CISCO-BGP4-MIB {

  namespace "urn:ietf:params:xml:ns:yang:smiv2:CISCO-BGP4-MIB";
  prefix CISCO-BGP4-MIB;

  import BGP4-MIB {
    prefix "bgp4-mib";
  }

  import INET-ADDRESS-MIB {
    prefix "inet-address";
  }

  import SNMP-FRAMEWORK-MIB {
    prefix "snmp-framework";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-iprouting-bgp@cisco.com";

  description
   "An extension to the IETF BGP4 MIB module defined in
    RFC 1657.
    
    Following is the terminology associated with Border
    Gateway Protocol(BGP).
    
    UPDATE message
        UPDATE messages are used to transfer routing 
        information between BGP peers. An UPDATE message 
        is used to advertise a single feasible route to a
        peer, or to withdraw multiple unfeasible routes 
        from service.                 
    
    Adj-RIBs-In 
       The Adj-RIBs-In store routing information that has
       been learned from inbound UPDATE messages. Their 
       contents represent routes that are available as an 
       input to the Decision Process.
    
    Loc-RIB(BGP table) 
       The Loc-RIB contains the local routing information
       that the BGP speaker has selected by applying its 
       local policies to the routing information contained 
       in its Adj-RIBs-In.
    
    Adj-RIBs-Out 
       The Adj-RIBs-Out store the information that the
       local BGP speaker has selected for advertisement to 
       its peers. The routing information stored in the 
       Adj-RIBs-Out will be carried in the local BGP 
       speaker's UPDATE messages and advertised to its
       peers.
    
    Path Attributes
       A variable length sequence of path attributes is 
       present in every UPDATE. Each path attribute is a 
       triple <attribute type, attribute length, 
       attribute value> of variable length. 
    
    Network Layer Reachability Information(NLRI)
       A variable length field present in UPDATE messages
       which contains a list of Network Layer address 
       prefixes. 
    
    Address Family Identifier(AFI) 
       Primary identifier to indicate the type of the 
       Network Layer Reachability Information(NLRI) being 
       carried.
    
    Subsequent Address Family Identifier(SAFI) 
       Secondary identifier to indicate the type of the 
       Network Layer Reachability Information(NLRI) being 
       carried.";

  revision 2010-09-30 {
    description
     "+Added cbgpNotifsEnable and cbgpLocalAs
      +Modified CbgpNetworkAddress TC
      +Added cbgpPeer2Table
      +Added cbgpPeer2CapsTable
      +Added cbgpPeer2AddrFamilyTable
      +Added cbgpPeer2AddrFamilyPrefixTable
      +Added notification cbgpPeer2EstablishedNotification
      +Added notification cbgpPeer2BackwardTransNotification
      +Added notification cbgpPeer2FsmStateChange
      +Added notification cbgpPeer2BackwardTransition
      +Added notification cbgpPeer2PrefixThresholdExceeded
      +Added notification cbgpPeer2PrefixThresholdClear";
  }

  revision 2003-02-24 {
    description
     "+Added cbgpPeerCapsTable
      +Added cbgpPeerAddrFamilyTable
      +Added cbgpPeerAddrFamilyPrefixTable
      +Added notification event cbgpBackwardTransition
      +Added notification event cbgpPrefixThresholdExceeded
      +Added notification event cbgpPrefixThresholdClear";
  }

  revision 2002-12-19 {
    description
     "+Added cbgpPeerPrefixTable
      +Added notification event cbgpFsmStateChange";
  }

  revision 2001-08-13 {
    description
     "Initial version of the MIB module.";
  }

  typedef CbgpSafi {
    type enumeration {
      enum "unicast" {
        value "1";
      }
      enum "multicast" {
        value "2";
      }
      enum "unicastAndMulticast" {
        value "3";
      }
      enum "vpn" {
        value "128";
      }
    }
    description
     "Subsequent Address Family Identifier(SAFI) is used
      by BGP speaker to indicate the type of the the Network
      Layer Reachability Information(NLRI) being carried. 
      RFC-2858 has defined the following values for SAFI.
      1 - Network Layer Reachability Information used for 
          unicast forwarding
      2 - Network Layer Reachability Information used for 
          multicast forwarding
      3 - Network Layer Reachability Information used for 
          both unicast and multicast forwarding. 
      SAFI values 128 through 255 are for private use.";
    reference
     "RFC-2858: Multiprotocol Extensions for BGP-4,
      RFC-2547: BGP/MPLS VPNs";
  }

  typedef CbgpNetworkAddress {
    type binary {
      length "0..255";
    }
    description
     "Represents the Network Address prefix carried in the
      BGP UPDATE messages.  In the following table, column 
      'Type' gives the kind of Network Layer address which 
      will be stored in the object of this type based on the
      values of Address Family Identifier(AFI) and SAFI.
      
       AFI          SAFI                   Type
      
      ipv4(1)      unicast(1)            IPv4 address 
      ipv4(1)      multicast(2)          IPv4 address
      ipv4(1)      vpn(128)              VPN-IPv4 address
      ipv6(2)      unicast(1)            IPv6 address
      ipv6(2)      multicast(2)          IPv6 address
      ipv6(2)      vpn(128)              VPN-IPv6 address
      
      A VPN-IPv4 address is a 12-byte quantity, beginning 
      with an 8-byte 'Route Distinguisher (RD)' and ending 
      with a 4-byte IPv4 address.
      
      A VPN-IPv6 address is a 24-byte quantity, beginning 
      with an 8-byte 'Route Distinguisher (RD)' and ending 
      with a 16-byte IPv6 address.";
    reference
     "RFC 2858, Multiprotocol Extensions for BGP-4.
      RFC 2547, Section 4.1, BGP/MPLS VPNs.";
  }


  container CISCO-BGP4-MIB {
    config false;

    container cbgpGlobal {
      smiv2:oid "1.3.6.1.4.1.9.9.187.1.3";

      leaf cbgpNotifsEnable {
        type bits {
          bit notifsEnable {
            position "0";
          }
          bit notifsPeer2Enable {
            position "1";
          }
        }
        description
         "Indicates whether the specific notifications are
          enabled. 
          If notifsEnable(0) bit is set to 1,
          then the notifications defined in
          ciscoBgp4NotificationsGroup1 are enabled; 
          If notifsPeer2Enable(1) bit is set to 1,
          then the notifications defined in
          ciscoBgp4Peer2NotificationsGroup are enabled.";
        smiv2:max-access "read-write";
        smiv2:oid "1.3.6.1.4.1.9.9.187.1.3.1";
      }

      leaf cbgpLocalAs {
        type inet:as-number;
        description
         "The local autonomous system (AS) number.";
        reference
         "RFC 4271, Section 4.2, 'My Autonomous System'.
          RFC 4893, BGP Support for Four-octet AS
          Number Space.";
        smiv2:max-access "read-only";
        smiv2:oid "1.3.6.1.4.1.9.9.187.1.3.2";
      }
    }

    container cbgpRouteTable {
      description
       "This table contains information about routes to
        destination networks from all BGP4 peers.  Since 
        BGP4 can carry routes for multiple Network Layer 
        protocols, this table has the Address Family 
        Identifier(AFI) of the Network Layer protocol as the 
        first index. Further for a given AFI, routes carried
        by BGP4 are distinguished based on Subsequent Address 
        Family Identifiers(SAFI).  Hence that is used as the
        second index.  Conceptually there is a separate Loc-RIB
        maintained by the BGP speaker for each combination of 
        AFI and SAFI supported by it.";
      reference
       "RFC-1771: A Border Gateway Protocol 4 (BGP-4),
        RFC-2858: Multiprotocol Extensions for BGP-4,
        RFC-2547: BGP/MPLS VPNs";
      smiv2:oid "1.3.6.1.4.1.9.9.187.1.1.1";

      list cbgpRouteEntry {
        key "cbgpRouteAfi cbgpRouteSafi cbgpRoutePeerType cbgpRoutePeer cbgpRouteAddrPrefix cbgpRouteAddrPrefixLen";
        description
         "Information about a path to a network received from
          a peer.";
        smiv2:oid "1.3.6.1.4.1.9.9.187.1.1.1.1";

        leaf cbgpRouteAfi {
          type inet-address:InetAddressType;
          description
           "Represents Address Family Identifier(AFI) of the
            Network Layer protocol associated with the route.
            An implementation is only required to support IPv4
            unicast and VPNv4 (Value - 1) address families.";
          smiv2:max-access "not-accessible";
          smiv2:oid "1.3.6.1.4.1.9.9.187.1.1.1.1.1";
        }

        leaf cbgpRouteSafi {
          type CISCO-BGP4-MIB:CbgpSafi;
          description
           "Represents Subsequent Address Family Identifier(SAFI)
            of the route. It gives additional information about
            the type of the route. An implementation is only 
            required to support IPv4 unicast(Value - 1) and VPNv4(
            Value - 128) address families.";
          smiv2:max-access "not-accessible";
          smiv2:oid "1.3.6.1.4.1.9.9.187.1.1.1.1.2";
        }

        leaf cbgpRoutePeerType {
          type inet-address:InetAddressType;
          description
           "Represents the type of Network Layer address stored
            in cbgpRoutePeer. An implementation is only required
            to support IPv4 address type(Value - 1).";
          smiv2:max-access "not-accessible";
          smiv2:oid "1.3.6.1.4.1.9.9.187.1.1.1.1.3";
        }

        leaf cbgpRoutePeer {
          type inet-address:InetAddress;
          description
           "The Network Layer address of the peer where the route
            information was learned. An implementation is only 
            required to support an IPv4 peer.";
          smiv2:max-access "not-accessible";
          smiv2:oid "1.3.6.1.4.1.9.9.187.1.1.1.1.4";
        }

        leaf cbgpRouteAddrPrefix {
          type CISCO-BGP4-MIB:CbgpNetworkAddress;
          description
           "A Network Address prefix in the Network Layer
            Reachability Information field of BGP UPDATE message.
            This object is a Network Address containing the prefix
            with length specified by cbgpRouteAddrPrefixLen. Any
            bits beyond the length specified by
            cbgpRouteAddrPrefixLen are zeroed.";
          smiv2:max-access "not-accessible";
          smiv2:oid "1.3.6.1.4.1.9.9.187.1.1.1.1.5";
        }

        leaf cbgpRouteAddrPrefixLen {
          type uint32 {
            range "0..2040";
          }
          description
           "Length in bits of the Network Address prefix in the
            Network Layer Reachability Information field.";
          smiv2:max-access "not-accessible";
          smiv2:oid "1.3.6.1.4.1.9.9.187.1.1.1.1.6";
        }

        leaf cbgpRouteOrigin {
          type enumeration {
            enum "igp" {
              value "1";
            }
            enum "egp" {
              value "2";
            }
            enum "incomplete" {
              value "3";
            }
          }
          description
           "The ultimate origin of the route information.";
          smiv2:max-access "read-only";
          smiv2:oid "1.3.6.1.4.1.9.9.187.1.1.1.1.7";
        }

        leaf cbgpRouteASPathSegment {
          type binary {
            length "0..255";
          }
          description
           "The sequence of AS path segments.  Each AS
            path segment is represented by a triple
            <type, length, value>.
            
            The type is a 1-octet field which has two
            possible values:
            1  AS_SET: unordered set of ASs a route in the 
                      UPDATE message has traversed
            2  AS_SEQUENCE: ordered set of ASs a route in the
                           UPDATE message has traversed.
            
            The length is a 1-octet field containing the
            number of ASs in the value field.
            
            The value field contains one or more AS
            numbers, each AS is represented in the octet
            string as a pair of octets according to the
            following algorithm:
            
            first-byte-of-pair = ASNumber / 256;
            second-byte-of-pair = ASNumber & 255;";
          smiv2:max-access "read-only";
          smiv2:oid "1.3.6.1.4.1.9.9.187.1.1.1.1.8";
        }

        leaf cbgpRouteNextHop {
          type CISCO-BGP4-MIB:CbgpNetworkAddress;
          description
           "The Network Layer address of the border router
            that should be used for the destination network.";
          smiv2:max-access "read-only";
          smiv2:oid "1.3.6.1.4.1.9.9.187.1.1.1.1.9";
        }

        leaf cbgpRouteMedPresent {
          type boolean;
          description
           "Indicates the presence/absence of MULTI_EXIT_DISC
            attribute for the route.";
          smiv2:max-access "read-only";
          smiv2:oid "1.3.6.1.4.1.9.9.187.1.1.1.1.10";
        }

        leaf cbgpRouteMultiExitDisc {
          type uint32 {
            range "0..4294967295";
          }
          description
           "This metric is used to discriminate between multiple
            exit points to an adjacent autonomous system.  The
            value of this object is irrelevant if the value of
            of cbgpRouteMedPresent is false(2).";
          smiv2:max-access "read-only";
          smiv2:oid "1.3.6.1.4.1.9.9.187.1.1.1.1.11";
        }

        leaf cbgpRouteLocalPrefPresent {
          type boolean;
          description
           "Indicates the presence/absence of LOCAL_PREF
            attribute for the route.";
          smiv2:max-access "read-only";
          smiv2:oid "1.3.6.1.4.1.9.9.187.1.1.1.1.12";
        }

        leaf cbgpRouteLocalPref {
          type uint32 {
            range "0..4294967295";
          }
          description
           "The degree of preference calculated by the local BGP4
            speaker for the route. The value of this object is 
            irrelevant if the value of cbgpRouteLocalPrefPresent 
            is false(2).";
          smiv2:max-access "read-only";
          smiv2:oid "1.3.6.1.4.1.9.9.187.1.1.1.1.13";
        }

        leaf cbgpRouteAtomicAggregate {
          type enumeration {
            enum "lessSpecificRouteNotSelected" {
              value "1";
            }
            enum "lessSpecificRouteSelected" {
              value "2";
            }
          }
          description
           "Whether or not the local system has selected a less
            specific route without selecting a more specific
            route.";
          smiv2:max-access "read-only";
          smiv2:oid "1.3.6.1.4.1.9.9.187.1.1.1.1.14";
        }

        leaf cbgpRouteAggregatorAS {
          type uint32 {
            range "0..65535";
          }
          description
           "The AS number of the last BGP4 speaker that performed
            route aggregation.  A value of zero (0) indicates the 
            absence of this attribute.";
          smiv2:max-access "read-only";
          smiv2:oid "1.3.6.1.4.1.9.9.187.1.1.1.1.15";
        }

        leaf cbgpRouteAggregatorAddrType {
          type inet-address:InetAddressType;
          description
           "Represents the type of Network Layer address stored
            in cbgpRouteAggregatorAddr.";
          smiv2:max-access "read-only";
          smiv2:oid "1.3.6.1.4.1.9.9.187.1.1.1.1.16";
        }

        leaf cbgpRouteAggregatorAddr {
          type inet-address:InetAddress;
          description
           "The Network Layer address of the last BGP4 speaker
            that performed route aggregation.  A value of all zeros
            indicates the absence of this attribute.";
          smiv2:max-access "read-only";
          smiv2:oid "1.3.6.1.4.1.9.9.187.1.1.1.1.17";
        }

        leaf cbgpRouteBest {
          type boolean;
          description
           "An indication of whether or not this route was chosen
            as the best BGP4 route.";
          smiv2:max-access "read-only";
          smiv2:oid "1.3.6.1.4.1.9.9.187.1.1.1.1.18";
        }

        leaf cbgpRouteUnknownAttr {
          type binary {
            length "0..255";
          }
          description
           "One or more path attributes not understood by this
            BGP4 speaker.  Size zero (0) indicates the absence of
            such attribute(s).  Octets beyond the maximum size, if
            any, are not recorded by this object.  
            
            Each path attribute is a triple <attribute type,
            attribute length, attribute value> of variable length.
            Attribute Type is a two-octet field that consists of
            the Attribute Flags octet followed by the Attribute
            Type Code octet.  If the Extended Length bit of the 
            Attribute Flags octet is set to 0, the third octet of 
            the Path Attribute contains the length of the
            attribute data in octets.  If the Extended Length bit 
            of the Attribute Flags octet is set to 1, then the
            third and the fourth octets of the path attribute 
            contain the length of the attribute data in octets.
            The remaining octets of the Path Attribute represent 
            the attribute value and are interpreted according to 
            the Attribute Flags and the Attribute Type Code.";
          reference
           "RFC-1771: A Border Gateway Protocol 4 (BGP-4), 
            section 4.3";
          smiv2:max-access "read-only";
          smiv2:oid "1.3.6.1.4.1.9.9.187.1.1.1.1.19";
        }
      }
    }

    container cbgpPeerCapsTable {
      description
       "This table contains the capabilities that are
        supported by a peer. Capabilities of a peer are 
        received during BGP connection establishment.
        Values corresponding to each received capability
        are stored in this table. When a new capability 
        is received, this table is updated with a new 
        entry. When an existing capability is not received 
        during the latest connection establishment, the 
        corresponding entry is deleted from the table.";
      reference
       "RFC 2842, Capabilities Advertisement with
        BGP-4.
        
        RFC2818, Route Refresh Capability for BGP-4.
        
        RFC2858, Multiprotocol Extensions for BGP-4.
        
        draft-ietf-idr-restart-05.txt, Graceful Restart
        Mechanism for BGP";
      smiv2:oid "1.3.6.1.4.1.9.9.187.1.2.2";

      list cbgpPeerCapsEntry {
        key "bgpPeerRemoteAddr cbgpPeerCapCode cbgpPeerCapIndex";
        description
         "Each entry represents a capability received from a
          peer with a particular code and an index. When a 
          capability is received multiple times with different
          values during a BGP connection establishment, 
          corresponding entries are differentiated with indices.";
        smiv2:oid "1.3.6.1.4.1.9.9.187.1.2.2.1";

        leaf bgpPeerRemoteAddr {
          type leafref {
            path "/bgp4-mib:BGP4-MIB/bgp4-mib:bgpPeerTable/bgp4-mib:bgpPeerEntry/bgp4-mib:bgpPeerRemoteAddr";
          }
        }

        leaf cbgpPeerCapCode {
          type enumeration {
            enum "multiProtocol" {
              value "1";
            }
            enum "routeRefresh" {
              value "2";
            }
            enum "gracefulRestart" {
              value "64";
            }
            enum "routeRefreshOld" {
              value "128";
            }
          }
          description
           "The BGP Capability Advertisement Capability Code.";
          reference
           "RFC 2842, Capabilities Advertisement with
            BGP-4.
            
            RFC2818, Route Refresh Capability for BGP-4.
            
            RFC2858, Multiprotocol Extensions for BGP-4.
            
            draft-ietf-idr-restart-05.txt, Graceful Restart
            Mechanism for BGP";
          smiv2:max-access "not-accessible";
          smiv2:oid "1.3.6.1.4.1.9.9.187.1.2.2.1.1";
        }

        leaf cbgpPeerCapIndex {
          type uint32 {
            range "1..128";
          }
          description
           "Multiple instances of a given capability may be
            sent by a BGP speaker.  This variable is used
            to index them.";
          smiv2:max-access "not-accessible";
          smiv2:oid "1.3.6.1.4.1.9.9.187.1.2.2.1.2";
        }

        leaf cbgpPeerCapValue {
          type binary {
            length "0..255";
          }
          description
           "The value of the announced capability. This
            MIB object value is organized as given below,
                Capability : Route Refresh Capability
                             Null string
                Capability : Multiprotocol Extensions
                  +----------------------------------+
                  | AFI(16 bits)                     |
                  +----------------------------------+
                  | SAFI (8 bits)                    |
                  +----------------------------------+
                Capability : Graceful Restart
                  +----------------------------------+
                  | Restart Flags (4 bits)           |
                  +----------------------------------+
                  | Restart Time in seconds (12 bits)|
                  +----------------------------------+
                  | AFI(16 bits)                     |
                  +----------------------------------+
                  | SAFI (8 bits)                    |
                  +----------------------------------+
                  | Flags for Address Family (8 bits)|
                  +----------------------------------+
                  | ...                              |
                  +----------------------------------+
                  | AFI(16 bits)                     |
                  +----------------------------------+
                  | SAFI (8 bits)                    |
                  +----------------------------------+
                  | Flags for Address Family (8 bits)|
                  +----------------------------------+";
          reference
           "RFC 2842, Capabilities Advertisement with
            BGP-4.
            
            RFC2818, Route Refresh Capability for BGP-4.
            
            RFC2858, Multiprotocol Extensions for BGP-4.
            
            draft-ietf-idr-restart-05.txt, Graceful Restart
            Mechanism for BGP";
          smiv2:max-access "read-only";
          smiv2:oid "1.3.6.1.4.1.9.9.187.1.2.2.1.3";
        }
      }
    }

    container cbgpPeerAddrFamilyTable {
      description
       "This table contains information related to
        address families supported by a peer. Supported
        address families of a peer are known during BGP 
        connection establishment. When a new supported 
        address family is known, this table is updated 
        with a new entry. When an address family is not 
        supported any more, corresponding entry is deleted 
        from the table.";
      smiv2:oid "1.3.6.1.4.1.9.9.187.1.2.3";

      list cbgpPeerAddrFamilyEntry {
        key "bgpPeerRemoteAddr cbgpPeerAddrFamilyAfi cbgpPeerAddrFamilySafi";
        description
         "An entry is identified by an AFI/SAFI pair and
          peer address. It contains names associated with
          an address family.";
        smiv2:oid "1.3.6.1.4.1.9.9.187.1.2.3.1";

        leaf bgpPeerRemoteAddr {
          type leafref {
            path "/bgp4-mib:BGP4-MIB/bgp4-mib:bgpPeerTable/bgp4-mib:bgpPeerEntry/bgp4-mib:bgpPeerRemoteAddr";
          }
        }

        leaf cbgpPeerAddrFamilyAfi {
          type inet-address:InetAddressType;
          description
           "The AFI index of the entry. An implementation
            is only required to support IPv4 unicast and 
            VPNv4 (Value - 1) address families.";
          smiv2:max-access "not-accessible";
          smiv2:oid "1.3.6.1.4.1.9.9.187.1.2.3.1.1";
        }

        leaf cbgpPeerAddrFamilySafi {
          type CISCO-BGP4-MIB:CbgpSafi;
          description
           "The SAFI index of the entry. An implementation
            is only required to support IPv4 unicast(Value 
            - 1) and VPNv4( Value - 128) address families.";
          reference
           "RFC-2858: Multiprotocol Extensions for BGP-4,
            RFC-2547: BGP/MPLS VPNs";
          smiv2:max-access "not-accessible";
          smiv2:oid "1.3.6.1.4.1.9.9.187.1.2.3.1.2";
        }

        leaf cbgpPeerAddrFamilyName {
          type snmp-framework:SnmpAdminString;
          description
           "Implementation specific Address Family name.";
          smiv2:max-access "read-only";
          smiv2:oid "1.3.6.1.4.1.9.9.187.1.2.3.1.3";
        }
      }
    }

    container cbgpPeerAddrFamilyPrefixTable {
      description
       "This table contains prefix related information
        related to address families supported by a peer. 
        Supported address families of a peer are known 
        during BGP connection establishment. When a new 
        supported address family is known, this table 
        is updated with a new entry. When an address 
        family is not supported any more, corresponding 
        entry is deleted from the table.";
      smiv2:oid "1.3.6.1.4.1.9.9.187.1.2.4";

      list cbgpPeerAddrFamilyPrefixEntry {
        key "bgpPeerRemoteAddr cbgpPeerAddrFamilyAfi cbgpPeerAddrFamilySafi";
        description
         "An entry is identified by an AFI/SAFI pair and
          peer address. It contains information associated 
          with route prefixes belonging to an address family.";
        smiv2:oid "1.3.6.1.4.1.9.9.187.1.2.4.1";

        leaf bgpPeerRemoteAddr {
          type leafref {
            path "/bgp4-mib:BGP4-MIB/bgp4-mib:bgpPeerTable/bgp4-mib:bgpPeerEntry/bgp4-mib:bgpPeerRemoteAddr";
          }
        }

        leaf cbgpPeerAddrFamilyAfi {
          type leafref {
            path "/CISCO-BGP4-MIB:CISCO-BGP4-MIB/CISCO-BGP4-MIB:cbgpPeerAddrFamilyTable/CISCO-BGP4-MIB:cbgpPeerAddrFamilyEntry/CISCO-BGP4-MIB:cbgpPeerAddrFamilyAfi";
          }
        }

        leaf cbgpPeerAddrFamilySafi {
          type leafref {
            path "/CISCO-BGP4-MIB:CISCO-BGP4-MIB/CISCO-BGP4-MIB:cbgpPeerAddrFamilyTable/CISCO-BGP4-MIB:cbgpPeerAddrFamilyEntry/CISCO-BGP4-MIB:cbgpPeerAddrFamilySafi";
          }
        }

        leaf cbgpPeerAcceptedPrefixes {
          type yang:counter32;
          description
           "Number of accepted route prefixes on this connection,
            which belong to an address family.";
          smiv2:max-access "read-only";
          smiv2:oid "1.3.6.1.4.1.9.9.187.1.2.4.1.1";
        }

        leaf cbgpPeerDeniedPrefixes {
          type yang:gauge32;
          description
           "This counter is incremented when a route prefix, which
            belongs to an address family, received on this 
            connection is denied. It is initialized to zero when 
            the connection is undergone a hard reset.";
          smiv2:max-access "read-only";
          smiv2:oid "1.3.6.1.4.1.9.9.187.1.2.4.1.2";
        }

        leaf cbgpPeerPrefixAdminLimit {
          type uint32 {
            range "1..4294967295";
          }
          description
           "Max number of route prefixes accepted for an address
            family on this connection.";
          smiv2:max-access "read-write";
          smiv2:oid "1.3.6.1.4.1.9.9.187.1.2.4.1.3";
        }

        leaf cbgpPeerPrefixThreshold {
          type uint32 {
            range "1..100";
          }
          description
           "Prefix threshold value (%) for an address family
            on this connection at which warning message stating
            the prefix count is crossed the threshold or 
            corresponding SNMP notification is generated.";
          smiv2:max-access "read-write";
          smiv2:oid "1.3.6.1.4.1.9.9.187.1.2.4.1.4";
        }

        leaf cbgpPeerPrefixClearThreshold {
          type uint32 {
            range "1..100";
          }
          description
           "Prefix threshold value (%) for an address family
            on this connection at which SNMP clear notification
            is generated if prefix threshold notification is
            already generated.";
          smiv2:max-access "read-only";
          smiv2:oid "1.3.6.1.4.1.9.9.187.1.2.4.1.5";
        }

        leaf cbgpPeerAdvertisedPrefixes {
          type yang:gauge32;
          description
           "This counter is incremented when a route prefix,
            which belongs to an address family is advertised
            on this connection. It is initialized to zero when 
            the connection is undergone a hard reset.";
          smiv2:max-access "read-only";
          smiv2:oid "1.3.6.1.4.1.9.9.187.1.2.4.1.6";
        }

        leaf cbgpPeerSuppressedPrefixes {
          type yang:gauge32;
          description
           "This counter is incremented when a route prefix,
            which belongs to an address family is suppressed
            from being sent on this connection. It is 
            initialized to zero when the connection is undergone
            a hard reset.";
          smiv2:max-access "read-only";
          smiv2:oid "1.3.6.1.4.1.9.9.187.1.2.4.1.7";
        }

        leaf cbgpPeerWithdrawnPrefixes {
          type yang:gauge32;
          description
           "This counter is incremented when a route prefix,
            which belongs to an address family, is withdrawn on
            this connection. It is initialized to zero when the
            connection is undergone a hard reset.";
          smiv2:max-access "read-only";
          smiv2:oid "1.3.6.1.4.1.9.9.187.1.2.4.1.8";
        }
      }
    }

    container cbgpPeer2Table {
      description
       "BGP peer table.  This table contains,
        one entry per BGP peer, information about
        the connections with BGP peers.";
      smiv2:oid "1.3.6.1.4.1.9.9.187.1.2.5";

      list cbgpPeer2Entry {
        key "cbgpPeer2Type cbgpPeer2RemoteAddr";
        description
         "Entry containing information about the
          connection with a BGP peer.";
        smiv2:oid "1.3.6.1.4.1.9.9.187.1.2.5.1";

        leaf cbgpPeer2Type {
          type inet-address:InetAddressType;
          description
           "Represents the type of Peer address stored
            in cbgpPeer2Entry.";
          smiv2:max-access "not-accessible";
          smiv2:oid "1.3.6.1.4.1.9.9.187.1.2.5.1.1";
        }

        leaf cbgpPeer2RemoteAddr {
          type inet-address:InetAddress;
          description
           "The remote IP address of this entry's BGP
            peer.";
          smiv2:max-access "not-accessible";
          smiv2:oid "1.3.6.1.4.1.9.9.187.1.2.5.1.2";
        }

        leaf cbgpPeer2State {
          type enumeration {
            enum "idle" {
              value "1";
            }
            enum "connect" {
              value "2";
            }
            enum "active" {
              value "3";
            }
            enum "opensent" {
              value "4";
            }
            enum "openconfirm" {
              value "5";
            }
            enum "established" {
              value "6";
            }
          }
          description
           "The BGP peer connection state.";
          reference
           "RFC 4271, Section 8.2.2.";
          smiv2:max-access "read-only";
          smiv2:oid "1.3.6.1.4.1.9.9.187.1.2.5.1.3";
        }

        leaf cbgpPeer2AdminStatus {
          type enumeration {
            enum "stop" {
              value "1";
            }
            enum "start" {
              value "2";
            }
          }
          description
           "The desired state of the BGP connection.
            A transition from 'stop' to 'start' will cause
            the BGP Manual Start Event to be generated.
            A transition from 'start' to 'stop' will cause
            the BGP Manual Stop Event to be generated.
            This parameter can be used to restart BGP peer
            connections.  Care should be used in providing
            write access to this object without adequate
            authentication.";
          reference
           "RFC 4271, Section 8.1.2.";
          smiv2:max-access "read-write";
          smiv2:oid "1.3.6.1.4.1.9.9.187.1.2.5.1.4";
        }

        leaf cbgpPeer2NegotiatedVersion {
          type int32;
          description
           "The negotiated version of BGP running between
            the two peers.
            
            This entry MUST be zero (0) unless the
            cbgpPeer2State is in the openconfirm or the
            established state.
            
            Note that legal values for this object are
            between 0 and 255.";
          reference
           "RFC 4271, Section 4.2.
            RFC 4271, Section 7.";
          smiv2:max-access "read-only";
          smiv2:oid "1.3.6.1.4.1.9.9.187.1.2.5.1.5";
        }

        leaf cbgpPeer2LocalAddr {
          type inet-address:InetAddress;
          description
           "The local IP address of this entry's BGP
            connection.";
          smiv2:max-access "read-only";
          smiv2:oid "1.3.6.1.4.1.9.9.187.1.2.5.1.6";
        }

        leaf cbgpPeer2LocalPort {
          type inet:port-number;
          description
           "The local port for the TCP connection between
            the BGP peers.";
          smiv2:max-access "read-only";
          smiv2:oid "1.3.6.1.4.1.9.9.187.1.2.5.1.7";
        }

        leaf cbgpPeer2LocalAs {
          type inet:as-number;
          description
           "The local AS number for this session.";
          smiv2:max-access "read-only";
          smiv2:oid "1.3.6.1.4.1.9.9.187.1.2.5.1.8";
        }

        leaf cbgpPeer2LocalIdentifier {
          type inet:ipv4-address;
          description
           "The BGP Identifier of this entry's BGP peer.";
          smiv2:max-access "read-only";
          smiv2:oid "1.3.6.1.4.1.9.9.187.1.2.5.1.9";
        }

        leaf cbgpPeer2RemotePort {
          type inet:port-number;
          description
           "The remote port for the TCP connection
            between the BGP peers.  Note that the
            objects cbgpPeer2LocalAddr,
            cbgpPeer2LocalPort, cbgpPeer2RemoteAddr, and
            cbgpPeer2RemotePort provide the appropriate
            reference to the standard MIB TCP
            connection table.";
          smiv2:max-access "read-only";
          smiv2:oid "1.3.6.1.4.1.9.9.187.1.2.5.1.10";
        }

        leaf cbgpPeer2RemoteAs {
          type inet:as-number;
          description
           "The remote autonomous system number received in
            the BGP OPEN message.";
          reference
           "RFC 4271, Section 4.2.";
          smiv2:max-access "read-only";
          smiv2:oid "1.3.6.1.4.1.9.9.187.1.2.5.1.11";
        }

        leaf cbgpPeer2RemoteIdentifier {
          type inet:ipv4-address;
          description
           "The BGP Identifier of this entry's BGP peer.
            This entry MUST be 0.0.0.0 unless the
            cbgpPeer2State is in the openconfirm or the
            established state.";
          reference
           "RFC 4271, Section 4.2, 'BGP Identifier'.";
          smiv2:max-access "read-only";
          smiv2:oid "1.3.6.1.4.1.9.9.187.1.2.5.1.12";
        }

        leaf cbgpPeer2InUpdates {
          type yang:counter32;
          description
           "The number of BGP UPDATE messages
            received on this connection.";
          reference
           "RFC 4271, Section 4.3.";
          smiv2:max-access "read-only";
          smiv2:oid "1.3.6.1.4.1.9.9.187.1.2.5.1.13";
        }

        leaf cbgpPeer2OutUpdates {
          type yang:counter32;
          description
           "The number of BGP UPDATE messages
            transmitted on this connection.";
          reference
           "RFC 4271, Section 4.3.";
          smiv2:max-access "read-only";
          smiv2:oid "1.3.6.1.4.1.9.9.187.1.2.5.1.14";
        }

        leaf cbgpPeer2InTotalMessages {
          type yang:counter32;
          description
           "The total number of messages received
            from the remote peer on this connection.";
          reference
           "RFC 4271, Section 4.";
          smiv2:max-access "read-only";
          smiv2:oid "1.3.6.1.4.1.9.9.187.1.2.5.1.15";
        }

        leaf cbgpPeer2OutTotalMessages {
          type yang:counter32;
          description
           "The total number of messages transmitted to
            the remote peer on this connection.";
          reference
           "RFC 4271, Section 4.";
          smiv2:max-access "read-only";
          smiv2:oid "1.3.6.1.4.1.9.9.187.1.2.5.1.16";
        }

        leaf cbgpPeer2LastError {
          type binary {
            length "2";
          }
          description
           "The last error code and subcode seen by this
            peer on this connection.  If no error has
            occurred, this field is zero.  Otherwise, the
            first byte of this two byte OCTET STRING
            contains the error code, and the second byte
            contains the subcode.";
          reference
           "RFC 4271, Section 4.5.";
          smiv2:max-access "read-only";
          smiv2:oid "1.3.6.1.4.1.9.9.187.1.2.5.1.17";
        }

        leaf cbgpPeer2FsmEstablishedTransitions {
          type yang:counter32;
          description
           "The total number of times the BGP FSM
            transitioned into the established state
            for this peer.";
          reference
           "RFC 4271, Section 8.";
          smiv2:max-access "read-only";
          smiv2:oid "1.3.6.1.4.1.9.9.187.1.2.5.1.18";
        }

        leaf cbgpPeer2FsmEstablishedTime {
          type yang:gauge32;
          units "seconds";
          description
           "This timer indicates how long (in
            seconds) this peer has been in the
            established state or how long
            since this peer was last in the
            established state.  It is set to zero when
            a new peer is configured or when the router is
            booted.";
          reference
           "RFC 4271, Section 8.";
          smiv2:max-access "read-only";
          smiv2:oid "1.3.6.1.4.1.9.9.187.1.2.5.1.19";
        }

        leaf cbgpPeer2ConnectRetryInterval {
          type int32 {
            range "1..65535";
          }
          units "seconds";
          description
           "Time interval (in seconds) for the
            ConnectRetry timer.  The suggested value
            for this timer is 120 seconds.";
          reference
           "RFC 4271, Section 8.2.2.  This is the value used
            to initialize the 'ConnectRetryTimer'.";
          smiv2:max-access "read-write";
          smiv2:oid "1.3.6.1.4.1.9.9.187.1.2.5.1.20";
        }

        leaf cbgpPeer2HoldTime {
          type int32 {
            range "0|3..65535";
          }
          units "seconds";
          description
           "Time interval (in seconds) for the Hold
            Timer established with the peer.  The
            value of this object is calculated by this
            BGP speaker, using the smaller of the
            values in cbgpPeer2HoldTimeConfigured and the
            Hold Time received in the OPEN message.
            
            This value must be at least three seconds
            if it is not zero (0).
            
            If the Hold Timer has not been established
            with the peer this object MUST have a value
            of zero (0).
            
            If the cbgpPeer2HoldTimeConfigured object has
            a value of (0), then this object MUST have a
            value of (0).";
          reference
           "RFC 4271, Section 4.2.";
          smiv2:max-access "read-only";
          smiv2:oid "1.3.6.1.4.1.9.9.187.1.2.5.1.21";
        }

        leaf cbgpPeer2KeepAlive {
          type int32 {
            range "0..21845";
          }
          units "seconds";
          description
           "Time interval (in seconds) for the KeepAlive
            timer established with the peer.  The value
            of this object is calculated by this BGP
            speaker such that, when compared with
            cbgpPeer2HoldTime, it has the same proportion
            that cbgpPeer2KeepAliveConfigured has,
            compared with cbgpPeer2HoldTimeConfigured.
            
            If the KeepAlive timer has not been established
            with the peer, this object MUST have a value
            of zero (0).
            
            If the of cbgpPeer2KeepAliveConfigured object
            has a value of (0), then this object MUST have
            a value of (0).";
          reference
           "RFC 4271, Section 4.4.";
          smiv2:max-access "read-only";
          smiv2:oid "1.3.6.1.4.1.9.9.187.1.2.5.1.22";
        }

        leaf cbgpPeer2HoldTimeConfigured {
          type int32 {
            range "0|3..65535";
          }
          units "seconds";
          description
           "Time interval (in seconds) for the Hold Time
            configured for this BGP speaker with this
            peer.  This value is placed in an OPEN
            message sent to this peer by this BGP
            speaker, and is compared with the Hold
            Time field in an OPEN message received
            from the peer when determining the Hold
            Time (cbgpPeer2HoldTime) with the peer.
            This value must not be less than three
            seconds if it is not zero (0).  If it is
            zero (0), the Hold Time is NOT to be
            established with the peer.  The suggested
            value for this timer is 90 seconds.";
          reference
           "RFC 4271, Section 4.2.
            RFC 4271, Section 10.";
          smiv2:max-access "read-write";
          smiv2:oid "1.3.6.1.4.1.9.9.187.1.2.5.1.23";
        }

        leaf cbgpPeer2KeepAliveConfigured {
          type int32 {
            range "0..21845";
          }
          units "seconds";
          description
           "Time interval (in seconds) for the
            KeepAlive timer configured for this BGP
            speaker with this peer.  The value of this
            object will only determine the
            KEEPALIVE messages' frequency relative to
            the value specified in
            cbgpPeer2HoldTimeConfigured; the actual
            time interval for the KEEPALIVE messages is
            indicated by cbgpPeer2KeepAlive.  A
            reasonable maximum value for this timer
            would be one third of that of
            cbgpPeer2HoldTimeConfigured.
            If the value of this object is zero (0),
            no periodical KEEPALIVE messages are sent
            to the peer after the BGP connection has
            been established.  The suggested value for
            this timer is 30 seconds.";
          reference
           "RFC 4271, Section 4.4.
            RFC 4271, Section 10.";
          smiv2:max-access "read-write";
          smiv2:oid "1.3.6.1.4.1.9.9.187.1.2.5.1.24";
        }

        leaf cbgpPeer2MinASOriginationInterval {
          type int32 {
            range "1..65535";
          }
          units "seconds";
          description
           "Time interval (in seconds) for the
            MinASOriginationInterval timer.
            The suggested value for this timer is 15
            seconds.";
          reference
           "RFC 4271, Section 9.2.1.2.
            RFC 4271, Section 10.";
          smiv2:max-access "read-write";
          smiv2:oid "1.3.6.1.4.1.9.9.187.1.2.5.1.25";
        }

        leaf cbgpPeer2MinRouteAdvertisementInterval {
          type int32 {
            range "1..65535";
          }
          units "seconds";
          description
           "Time interval (in seconds) for the
            MinRouteAdvertisementInterval timer.
            The suggested value for this timer is 30
            seconds for EBGP connections and 5
            seconds for IBGP connections.";
          reference
           "RFC 4271, Section 9.2.1.1.
            RFC 4271, Section 10.";
          smiv2:max-access "read-write";
          smiv2:oid "1.3.6.1.4.1.9.9.187.1.2.5.1.26";
        }

        leaf cbgpPeer2InUpdateElapsedTime {
          type yang:gauge32;
          units "seconds";
          description
           "Elapsed time (in seconds) since the last BGP
            UPDATE message was received from the peer.
            Each time cbgpPeer2InUpdates is incremented,
            the value of this object is set to zero (0).";
          reference
           "RFC 4271, Section 4.3.
            RFC 4271, Section 8.2.2, Established state.";
          smiv2:max-access "read-only";
          smiv2:oid "1.3.6.1.4.1.9.9.187.1.2.5.1.27";
        }

        leaf cbgpPeer2LastErrorTxt {
          type snmp-framework:SnmpAdminString;
          description
           "Implementation specific error description for
            bgpPeerLastErrorReceived.";
          smiv2:max-access "read-only";
          smiv2:oid "1.3.6.1.4.1.9.9.187.1.2.5.1.28";
        }

        leaf cbgpPeer2PrevState {
          type enumeration {
            enum "none" {
              value "0";
            }
            enum "idle" {
              value "1";
            }
            enum "connect" {
              value "2";
            }
            enum "active" {
              value "3";
            }
            enum "opensent" {
              value "4";
            }
            enum "openconfirm" {
              value "5";
            }
            enum "established" {
              value "6";
            }
          }
          description
           "The BGP peer connection previous state.";
          reference
           "RFC 1771, Section 8, A Border Gateway Protocol 4
            (BGP-4).";
          smiv2:max-access "read-only";
          smiv2:oid "1.3.6.1.4.1.9.9.187.1.2.5.1.29";
        }
      }
    }

    container cbgpPeer2CapsTable {
      description
       "This table contains the capabilities that are
        supported by a peer. Capabilities of a peer are
        received during BGP connection establishment.
        Values corresponding to each received capability
        are stored in this table. When a new capability
        is received, this table is updated with a new
        entry. When an existing capability is not received
        during the latest connection establishment, the
        corresponding entry is deleted from the table.";
      reference
       "RFC 2842, Capabilities Advertisement with
        BGP-4.
        RFC 2818, Route Refresh Capability for BGP-4.
        RFC 2858, Multiprotocol Extensions for BGP-4.
        RFC 4724, Graceful Restart Mechanism for BGP.
        RFC 4893, BGP Support for Four-octet AS
        Number Space.
        draft-ietf-idr-add-paths-04.txt, Advertisement
        of Multiple Paths in BGP.";
      smiv2:oid "1.3.6.1.4.1.9.9.187.1.2.6";

      list cbgpPeer2CapsEntry {
        key "cbgpPeer2Type cbgpPeer2RemoteAddr cbgpPeer2CapCode cbgpPeer2CapIndex";
        description
         "Each entry represents a capability received from a
          peer with a particular code and an index. When a
          capability is received multiple times with different
          values during a BGP connection establishment,
          corresponding entries are differentiated with indices.";
        smiv2:oid "1.3.6.1.4.1.9.9.187.1.2.6.1";

        leaf cbgpPeer2Type {
          type leafref {
            path "/CISCO-BGP4-MIB:CISCO-BGP4-MIB/CISCO-BGP4-MIB:cbgpPeer2Table/CISCO-BGP4-MIB:cbgpPeer2Entry/CISCO-BGP4-MIB:cbgpPeer2Type";
          }
        }

        leaf cbgpPeer2RemoteAddr {
          type leafref {
            path "/CISCO-BGP4-MIB:CISCO-BGP4-MIB/CISCO-BGP4-MIB:cbgpPeer2Table/CISCO-BGP4-MIB:cbgpPeer2Entry/CISCO-BGP4-MIB:cbgpPeer2RemoteAddr";
          }
        }

        leaf cbgpPeer2CapCode {
          type enumeration {
            enum "multiProtocol" {
              value "1";
            }
            enum "routeRefresh" {
              value "2";
            }
            enum "gracefulRestart" {
              value "64";
            }
            enum "fourByteAs" {
              value "65";
            }
            enum "addPath" {
              value "69";
            }
            enum "routeRefreshOld" {
              value "128";
            }
          }
          description
           "The BGP Capability Advertisement Capability Code.";
          reference
           "RFC 2842, Capabilities Advertisement with
            BGP-4.
            RFC 2818, Route Refresh Capability for BGP-4.
            RFC 2858, Multiprotocol Extensions for BGP-4.
            RFC 4724, Graceful Restart Mechanism for BGP.
            RFC 4893, BGP Support for Four-octet AS
            Number Space.
            draft-ietf-idr-add-paths-04.txt, Advertisement
            of Multiple Paths in BGP.";
          smiv2:max-access "not-accessible";
          smiv2:oid "1.3.6.1.4.1.9.9.187.1.2.6.1.1";
        }

        leaf cbgpPeer2CapIndex {
          type uint32 {
            range "1..128";
          }
          description
           "Multiple instances of a given capability may be
            sent by a BGP speaker.  This variable is used
            to index them.";
          smiv2:max-access "not-accessible";
          smiv2:oid "1.3.6.1.4.1.9.9.187.1.2.6.1.2";
        }

        leaf cbgpPeer2CapValue {
          type binary {
            length "0..255";
          }
          description
           "The value of the announced capability. This
            MIB object value is organized as given below,
                Capability : Route Refresh Capability
                             4-Byte AS Capability
                             Null string
                Capability : Multiprotocol Extensions
                  +----------------------------------+
                  | AFI(16 bits)                     |
                  +----------------------------------+
                  | SAFI (8 bits)                    |
                  +----------------------------------+
                Capability : Graceful Restart
                  +----------------------------------+
                  | Restart Flags (4 bits)           |
                  +----------------------------------+
                  | Restart Time in seconds (12 bits)|
                  +----------------------------------+
                  | AFI(16 bits)                     |
                  +----------------------------------+
                  | SAFI (8 bits)                    |
                  +----------------------------------+
                  | Flags for Address Family (8 bits)|
                  +----------------------------------+
                  | ...                              |
                  +----------------------------------+
                  | AFI(16 bits)                     |
                  +----------------------------------+
                  | SAFI (8 bits)                    |
                  +----------------------------------+
                  | Flags for Address Family (8 bits)|
                  +----------------------------------+
                Capability : Additional Paths
                  +----------------------------------+
                  | AFI(16 bits)                     |
                  +----------------------------------+
                  | SAFI (8 bits)                    |
                  +----------------------------------+
                  | Send/Receive (8 bits)            |
                  +----------------------------------+";
          reference
           "RFC 2842, Capabilities Advertisement with
            BGP-4.
            RFC 2818, Route Refresh Capability for BGP-4.
            RFC 2858, Multiprotocol Extensions for BGP-4.
            RFC 4724, Graceful Restart Mechanism for BGP.
            RFC 4893, BGP Support for Four-octet AS
            Number Space.
            draft-ietf-idr-add-paths-04.txt, Advertisement
            of Multiple Paths in BGP.";
          smiv2:max-access "read-only";
          smiv2:oid "1.3.6.1.4.1.9.9.187.1.2.6.1.3";
        }
      }
    }

    container cbgpPeer2AddrFamilyTable {
      description
       "This table contains information related to
        address families supported by a peer. Supported
        address families of a peer are known during BGP
        connection establishment. When a new supported
        address family is known, this table is updated
        with a new entry. When an address family is not
        supported any more, corresponding entry is deleted
        from the table.";
      smiv2:oid "1.3.6.1.4.1.9.9.187.1.2.7";

      list cbgpPeer2AddrFamilyEntry {
        key "cbgpPeer2Type cbgpPeer2RemoteAddr cbgpPeer2AddrFamilyAfi cbgpPeer2AddrFamilySafi";
        description
         "An entry is identified by an AFI/SAFI pair and
          peer address. It contains names associated with
          an address family.";
        smiv2:oid "1.3.6.1.4.1.9.9.187.1.2.7.1";

        leaf cbgpPeer2Type {
          type leafref {
            path "/CISCO-BGP4-MIB:CISCO-BGP4-MIB/CISCO-BGP4-MIB:cbgpPeer2Table/CISCO-BGP4-MIB:cbgpPeer2Entry/CISCO-BGP4-MIB:cbgpPeer2Type";
          }
        }

        leaf cbgpPeer2RemoteAddr {
          type leafref {
            path "/CISCO-BGP4-MIB:CISCO-BGP4-MIB/CISCO-BGP4-MIB:cbgpPeer2Table/CISCO-BGP4-MIB:cbgpPeer2Entry/CISCO-BGP4-MIB:cbgpPeer2RemoteAddr";
          }
        }

        leaf cbgpPeer2AddrFamilyAfi {
          type inet-address:InetAddressType;
          description
           "The AFI index of the entry. An implementation
            is only required to support IPv4 unicast and
            VPNv4 (Value - 1) address families.";
          smiv2:max-access "not-accessible";
          smiv2:oid "1.3.6.1.4.1.9.9.187.1.2.7.1.1";
        }

        leaf cbgpPeer2AddrFamilySafi {
          type CISCO-BGP4-MIB:CbgpSafi;
          description
           "The SAFI index of the entry. An implementation
            is only required to support IPv4 unicast(Value
            - 1) and VPNv4( Value - 128) address families.";
          reference
           "RFC 2858, Multiprotocol Extensions for BGP-4.
            RFC 2547, BGP/MPLS VPNs.";
          smiv2:max-access "not-accessible";
          smiv2:oid "1.3.6.1.4.1.9.9.187.1.2.7.1.2";
        }

        leaf cbgpPeer2AddrFamilyName {
          type snmp-framework:SnmpAdminString;
          description
           "Implementation specific Address Family name.";
          smiv2:max-access "read-only";
          smiv2:oid "1.3.6.1.4.1.9.9.187.1.2.7.1.3";
        }
      }
    }

    container cbgpPeer2AddrFamilyPrefixTable {
      description
       "This table contains prefix related information
        related to address families supported by a peer.
        Supported address families of a peer are known
        during BGP connection establishment. When a new
        supported address family is known, this table
        is updated with a new entry. When an address
        family is not supported any more, corresponding
        entry is deleted from the table.";
      smiv2:oid "1.3.6.1.4.1.9.9.187.1.2.8";

      list cbgpPeer2AddrFamilyPrefixEntry {
        key "cbgpPeer2Type cbgpPeer2RemoteAddr cbgpPeer2AddrFamilyAfi cbgpPeer2AddrFamilySafi";
        description
         "An entry is identified by an AFI/SAFI pair and
          peer address. It contains information associated
          with route prefixes belonging to an address family.";
        smiv2:oid "1.3.6.1.4.1.9.9.187.1.2.8.1";

        leaf cbgpPeer2Type {
          type leafref {
            path "/CISCO-BGP4-MIB:CISCO-BGP4-MIB/CISCO-BGP4-MIB:cbgpPeer2Table/CISCO-BGP4-MIB:cbgpPeer2Entry/CISCO-BGP4-MIB:cbgpPeer2Type";
          }
        }

        leaf cbgpPeer2RemoteAddr {
          type leafref {
            path "/CISCO-BGP4-MIB:CISCO-BGP4-MIB/CISCO-BGP4-MIB:cbgpPeer2Table/CISCO-BGP4-MIB:cbgpPeer2Entry/CISCO-BGP4-MIB:cbgpPeer2RemoteAddr";
          }
        }

        leaf cbgpPeer2AddrFamilyAfi {
          type leafref {
            path "/CISCO-BGP4-MIB:CISCO-BGP4-MIB/CISCO-BGP4-MIB:cbgpPeer2AddrFamilyTable/CISCO-BGP4-MIB:cbgpPeer2AddrFamilyEntry/CISCO-BGP4-MIB:cbgpPeer2AddrFamilyAfi";
          }
        }

        leaf cbgpPeer2AddrFamilySafi {
          type leafref {
            path "/CISCO-BGP4-MIB:CISCO-BGP4-MIB/CISCO-BGP4-MIB:cbgpPeer2AddrFamilyTable/CISCO-BGP4-MIB:cbgpPeer2AddrFamilyEntry/CISCO-BGP4-MIB:cbgpPeer2AddrFamilySafi";
          }
        }

        leaf cbgpPeer2AcceptedPrefixes {
          type yang:counter32;
          description
           "Number of accepted route prefixes on this connection,
            which belong to an address family.";
          smiv2:max-access "read-only";
          smiv2:oid "1.3.6.1.4.1.9.9.187.1.2.8.1.1";
        }

        leaf cbgpPeer2DeniedPrefixes {
          type yang:gauge32;
          description
           "This counter is incremented when a route prefix, which
            belongs to an address family, received on this
            connection is denied. It is initialized to zero when
            the connection is undergone a hard reset.";
          smiv2:max-access "read-only";
          smiv2:oid "1.3.6.1.4.1.9.9.187.1.2.8.1.2";
        }

        leaf cbgpPeer2PrefixAdminLimit {
          type uint32 {
            range "1..4294967295";
          }
          description
           "Max number of route prefixes accepted for an address
            family on this connection.";
          smiv2:max-access "read-write";
          smiv2:oid "1.3.6.1.4.1.9.9.187.1.2.8.1.3";
        }

        leaf cbgpPeer2PrefixThreshold {
          type uint32 {
            range "1..100";
          }
          units "percent";
          description
           "Prefix threshold value (%) for an address family
            on this connection at which warning message stating
            the prefix count is crossed the threshold or
            corresponding SNMP notification is generated.";
          smiv2:max-access "read-write";
          smiv2:oid "1.3.6.1.4.1.9.9.187.1.2.8.1.4";
        }

        leaf cbgpPeer2PrefixClearThreshold {
          type uint32 {
            range "1..100";
          }
          units "percent";
          description
           "Prefix threshold value (%) for an address family
            on this connection at which SNMP clear notification
            is generated if prefix threshold notification is
            already generated.";
          smiv2:max-access "read-only";
          smiv2:oid "1.3.6.1.4.1.9.9.187.1.2.8.1.5";
        }

        leaf cbgpPeer2AdvertisedPrefixes {
          type yang:gauge32;
          description
           "This counter is incremented when a route prefix,
            which belongs to an address family is advertised
            on this connection. It is initialized to zero when
            the connection is undergone a hard reset.";
          smiv2:max-access "read-only";
          smiv2:oid "1.3.6.1.4.1.9.9.187.1.2.8.1.6";
        }

        leaf cbgpPeer2SuppressedPrefixes {
          type yang:gauge32;
          description
           "This counter is incremented when a route prefix,
            which belongs to an address family is suppressed
            from being sent on this connection. It is
            initialized to zero when the connection is undergone
            a hard reset.";
          smiv2:max-access "read-only";
          smiv2:oid "1.3.6.1.4.1.9.9.187.1.2.8.1.7";
        }

        leaf cbgpPeer2WithdrawnPrefixes {
          type yang:gauge32;
          description
           "This counter is incremented when a route prefix,
            which belongs to an address family, is withdrawn on
            this connection. It is initialized to zero when the
            connection is undergone a hard reset.";
          smiv2:max-access "read-only";
          smiv2:oid "1.3.6.1.4.1.9.9.187.1.2.8.1.8";
        }
      }
    }
  }

  smiv2:alias "cbgpPeerTable" {
    description
     "BGP peer table.  This table contains,
      one entry per BGP peer, information about
      the connections with BGP peers.";
    smiv2:oid "1.3.6.1.4.1.9.9.187.1.2.1";
  }

  smiv2:alias "cbgpPeerEntry" {
    description
     "Entry containing information about the
      connection with a BGP peer.";
    smiv2:oid "1.3.6.1.4.1.9.9.187.1.2.1.1";
  }

  augment "/bgp4-mib:BGP4-MIB/bgp4-mib:bgpPeerTable/bgp4-mib:bgpPeerEntry" {
    description
     "Entry containing information about the
      connection with a BGP peer.";
    smiv2:oid "1.3.6.1.4.1.9.9.187.1.2.1.1";

    leaf cbgpPeerPrefixAccepted {
      type yang:counter32;
      status deprecated;
      description
       "Number of Route prefixes received on this connnection,
        which are accepted after applying filters. Possible
        filters are route maps, prefix lists, distributed
        lists, etc.";
      smiv2:max-access "read-only";
      smiv2:oid "1.3.6.1.4.1.9.9.187.1.2.1.1.1";
    }

    leaf cbgpPeerPrefixDenied {
      type yang:counter32;
      status deprecated;
      description
       "Counter which gets incremented when a route prefix
        received on this connection is denied  or when a route
        prefix is denied during soft reset of this connection
        if 'soft-reconfiguration' is on . This object is 
        initialized to zero when the peer is  configured or
        the router is rebooted";
      smiv2:max-access "read-only";
      smiv2:oid "1.3.6.1.4.1.9.9.187.1.2.1.1.2";
    }

    leaf cbgpPeerPrefixLimit {
      type uint32 {
        range "1..4294967295";
      }
      status deprecated;
      description
       "Max number of route prefixes accepted on this
        connection";
      smiv2:max-access "read-write";
      smiv2:oid "1.3.6.1.4.1.9.9.187.1.2.1.1.3";
    }

    leaf cbgpPeerPrefixAdvertised {
      type yang:counter32;
      status deprecated;
      description
       "Counter which gets incremented when a route prefix
        is advertised on this connection. This object is
        initialized to zero when the peer is configured or 
        the router is rebooted";
      smiv2:max-access "read-only";
      smiv2:oid "1.3.6.1.4.1.9.9.187.1.2.1.1.4";
    }

    leaf cbgpPeerPrefixSuppressed {
      type yang:counter32;
      status deprecated;
      description
       "Counter which gets incremented when a route prefix
        is suppressed from being sent on this connection. This 
        object is initialized to zero when the peer is 
        configured or the router is rebooted";
      smiv2:max-access "read-only";
      smiv2:oid "1.3.6.1.4.1.9.9.187.1.2.1.1.5";
    }

    leaf cbgpPeerPrefixWithdrawn {
      type yang:counter32;
      status deprecated;
      description
       "Counter which gets incremented when a route prefix
        is withdrawn on this connection. This object is
        initialized to zero when the peer is configured or
        the router is rebooted";
      smiv2:max-access "read-only";
      smiv2:oid "1.3.6.1.4.1.9.9.187.1.2.1.1.6";
    }

    leaf cbgpPeerLastErrorTxt {
      type snmp-framework:SnmpAdminString;
      description
       "Implementation specific error description for
        bgpPeerLastErrorReceived.";
      smiv2:max-access "read-only";
      smiv2:oid "1.3.6.1.4.1.9.9.187.1.2.1.1.7";
    }

    leaf cbgpPeerPrevState {
      type enumeration {
        enum "none" {
          value "0";
        }
        enum "idle" {
          value "1";
        }
        enum "connect" {
          value "2";
        }
        enum "active" {
          value "3";
        }
        enum "opensent" {
          value "4";
        }
        enum "openconfirm" {
          value "5";
        }
        enum "established" {
          value "6";
        }
      }
      description
       "The BGP peer connection previous state.";
      reference
       "Section 8, RFC 1771, A Border Gateway Protocol 4 
        (BGP-4).";
      smiv2:max-access "read-only";
      smiv2:oid "1.3.6.1.4.1.9.9.187.1.2.1.1.8";
    }
  }

  notification cbgpFsmStateChange {
    description
     "The BGP cbgpFsmStateChange notification is generated
      for every BGP FSM state change. The bgpPeerRemoteAddr
      value is attached to the notification object ID.";
    smiv2:oid "1.3.6.1.4.1.9.9.187.0.1";

    container object-1 {

      leaf bgpPeerRemoteAddr {
        type leafref {
          path "/bgp4-mib:BGP4-MIB/bgp4-mib:bgpPeerTable/bgp4-mib:bgpPeerEntry/bgp4-mib:bgpPeerRemoteAddr";
        }
      }

      leaf bgpPeerLastError {
        type leafref {
          path "/bgp4-mib:BGP4-MIB/bgp4-mib:bgpPeerTable/bgp4-mib:bgpPeerEntry/bgp4-mib:bgpPeerLastError";
        }
      }
    }

    container object-2 {

      leaf bgpPeerRemoteAddr {
        type leafref {
          path "/bgp4-mib:BGP4-MIB/bgp4-mib:bgpPeerTable/bgp4-mib:bgpPeerEntry/bgp4-mib:bgpPeerRemoteAddr";
        }
      }

      leaf bgpPeerState {
        type leafref {
          path "/bgp4-mib:BGP4-MIB/bgp4-mib:bgpPeerTable/bgp4-mib:bgpPeerEntry/bgp4-mib:bgpPeerState";
        }
      }
    }

    container object-3 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerLastErrorTxt {
        type leafref {
          path "/bgp4-mib:BGP4-MIB/bgp4-mib:bgpPeerTable/bgp4-mib:bgpPeerEntry/CISCO-BGP4-MIB:cbgpPeerLastErrorTxt";
        }
      }
    }

    container object-4 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerPrevState {
        type leafref {
          path "/bgp4-mib:BGP4-MIB/bgp4-mib:bgpPeerTable/bgp4-mib:bgpPeerEntry/CISCO-BGP4-MIB:cbgpPeerPrevState";
        }
      }
    }
  }

  notification cbgpBackwardTransition {
    description
     "The cbgpBackwardTransition Event is generated when the
      BGP FSM moves from a higher numbered state to a lower
      numbered state. The bgpPeerRemoteAddr value is attached
      to the notification object ID.";
    smiv2:oid "1.3.6.1.4.1.9.9.187.0.2";

    container object-1 {

      leaf bgpPeerRemoteAddr {
        type leafref {
          path "/bgp4-mib:BGP4-MIB/bgp4-mib:bgpPeerTable/bgp4-mib:bgpPeerEntry/bgp4-mib:bgpPeerRemoteAddr";
        }
      }

      leaf bgpPeerLastError {
        type leafref {
          path "/bgp4-mib:BGP4-MIB/bgp4-mib:bgpPeerTable/bgp4-mib:bgpPeerEntry/bgp4-mib:bgpPeerLastError";
        }
      }
    }

    container object-2 {

      leaf bgpPeerRemoteAddr {
        type leafref {
          path "/bgp4-mib:BGP4-MIB/bgp4-mib:bgpPeerTable/bgp4-mib:bgpPeerEntry/bgp4-mib:bgpPeerRemoteAddr";
        }
      }

      leaf bgpPeerState {
        type leafref {
          path "/bgp4-mib:BGP4-MIB/bgp4-mib:bgpPeerTable/bgp4-mib:bgpPeerEntry/bgp4-mib:bgpPeerState";
        }
      }
    }

    container object-3 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerLastErrorTxt {
        type leafref {
          path "/bgp4-mib:BGP4-MIB/bgp4-mib:bgpPeerTable/bgp4-mib:bgpPeerEntry/CISCO-BGP4-MIB:cbgpPeerLastErrorTxt";
        }
      }
    }

    container object-4 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerPrevState {
        type leafref {
          path "/bgp4-mib:BGP4-MIB/bgp4-mib:bgpPeerTable/bgp4-mib:bgpPeerEntry/CISCO-BGP4-MIB:cbgpPeerPrevState";
        }
      }
    }
  }

  notification cbgpPrefixThresholdExceeded {
    description
     "The cbgpPrefixThresholdExceeded notification is
      generated when prefix count exceeds the configured
      warning threshold on a session for an address
      family. The bgpPeerRemoteAddr, cbgpPeerAddrFamilyAfi
      and cbgpPeerAddrFamilySafi values are attached to the
      notification object ID.";
    smiv2:oid "1.3.6.1.4.1.9.9.187.0.3";

    container object-1 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerAddrFamilyAfi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilyAfi";
        }
      }

      leaf cbgpPeerAddrFamilySafi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilySafi";
        }
      }

      leaf cbgpPeerPrefixAdminLimit {
        type leafref {
          path "/CISCO-BGP4-MIB:CISCO-BGP4-MIB/CISCO-BGP4-MIB:cbgpPeerAddrFamilyPrefixTable/CISCO-BGP4-MIB:cbgpPeerAddrFamilyPrefixEntry/CISCO-BGP4-MIB:cbgpPeerPrefixAdminLimit";
        }
      }
    }

    container object-2 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerAddrFamilyAfi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilyAfi";
        }
      }

      leaf cbgpPeerAddrFamilySafi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilySafi";
        }
      }

      leaf cbgpPeerPrefixThreshold {
        type leafref {
          path "/CISCO-BGP4-MIB:CISCO-BGP4-MIB/CISCO-BGP4-MIB:cbgpPeerAddrFamilyPrefixTable/CISCO-BGP4-MIB:cbgpPeerAddrFamilyPrefixEntry/CISCO-BGP4-MIB:cbgpPeerPrefixThreshold";
        }
      }
    }
  }

  notification cbgpPrefixThresholdClear {
    description
     "The cbgpPrefixThresholdClear notification is
      generated when prefix count drops below the configured
      clear threshold on a session for an address family once
      cbgpPrefixThresholdExceeded is generated. This won't
      be generated if the peer session goes down after the
      generation of cbgpPrefixThresholdExceeded.
      The bgpPeerRemoteAddr, cbgpPeerAddrFamilyAfi and
      cbgpPeerAddrFamilySafi values are attached to the
      notification object ID.";
    smiv2:oid "1.3.6.1.4.1.9.9.187.0.4";

    container object-1 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerAddrFamilyAfi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilyAfi";
        }
      }

      leaf cbgpPeerAddrFamilySafi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilySafi";
        }
      }

      leaf cbgpPeerPrefixAdminLimit {
        type leafref {
          path "/CISCO-BGP4-MIB:CISCO-BGP4-MIB/CISCO-BGP4-MIB:cbgpPeerAddrFamilyPrefixTable/CISCO-BGP4-MIB:cbgpPeerAddrFamilyPrefixEntry/CISCO-BGP4-MIB:cbgpPeerPrefixAdminLimit";
        }
      }
    }

    container object-2 {

      leaf bgpPeerRemoteAddr {
        type leafref {
          path "/bgp4-mib:BGP4-MIB/bgp4-mib:bgpPeerTable/bgp4-mib:bgpPeerEntry/bgp4-mib:bgpPeerRemoteAddr";
        }
      }

      leaf cbgpPeerAddrFamilyAfi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilyAfi";
        }
      }

      leaf cbgpPeerAddrFamilySafi {
        type leafref {
          path "/CISCO-BGP4-MIB:CISCO-BGP4-MIB/CISCO-BGP4-MIB:cbgpPeerAddrFamilyTable/CISCO-BGP4-MIB:cbgpPeerAddrFamilyEntry/CISCO-BGP4-MIB:cbgpPeerAddrFamilySafi";
        }
      }

      leaf cbgpPeerPrefixClearThreshold {
        type leafref {
          path "/CISCO-BGP4-MIB:CISCO-BGP4-MIB/CISCO-BGP4-MIB:cbgpPeerAddrFamilyPrefixTable/CISCO-BGP4-MIB:cbgpPeerAddrFamilyPrefixEntry/CISCO-BGP4-MIB:cbgpPeerPrefixClearThreshold";
        }
      }
    }
  }

  notification cbgpPeer2EstablishedNotification {
    description
     "The cbgpPeer2EstablishedNotification notification
      is generated when the BGP FSM enters the established
      state.";
    smiv2:oid "1.3.6.1.4.1.9.9.187.0.5";

    container object-1 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2LastError {
        type leafref {
          path "/CISCO-BGP4-MIB:CISCO-BGP4-MIB/CISCO-BGP4-MIB:cbgpPeer2Table/CISCO-BGP4-MIB:cbgpPeer2Entry/CISCO-BGP4-MIB:cbgpPeer2LastError";
        }
      }
    }

    container object-2 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2State {
        type leafref {
          path "/CISCO-BGP4-MIB:CISCO-BGP4-MIB/CISCO-BGP4-MIB:cbgpPeer2Table/CISCO-BGP4-MIB:cbgpPeer2Entry/CISCO-BGP4-MIB:cbgpPeer2State";
        }
      }
    }
  }

  notification cbgpPeer2BackwardTransNotification {
    description
     "The cbgpPeer2BackwardTransNotification notification
      is generated when the BGP FSM moves from a higher
      numbered state to a lower numbered state.";
    smiv2:oid "1.3.6.1.4.1.9.9.187.0.6";

    container object-1 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2LastError {
        type leafref {
          path "/CISCO-BGP4-MIB:CISCO-BGP4-MIB/CISCO-BGP4-MIB:cbgpPeer2Table/CISCO-BGP4-MIB:cbgpPeer2Entry/CISCO-BGP4-MIB:cbgpPeer2LastError";
        }
      }
    }

    container object-2 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2State {
        type leafref {
          path "/CISCO-BGP4-MIB:CISCO-BGP4-MIB/CISCO-BGP4-MIB:cbgpPeer2Table/CISCO-BGP4-MIB:cbgpPeer2Entry/CISCO-BGP4-MIB:cbgpPeer2State";
        }
      }
    }
  }

  notification cbgpPeer2FsmStateChange {
    description
     "The cbgpPeer2FsmStateChange notification is generated
      for every BGP FSM state change.";
    smiv2:oid "1.3.6.1.4.1.9.9.187.0.7";

    container object-1 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2LastError {
        type leafref {
          path "/CISCO-BGP4-MIB:CISCO-BGP4-MIB/CISCO-BGP4-MIB:cbgpPeer2Table/CISCO-BGP4-MIB:cbgpPeer2Entry/CISCO-BGP4-MIB:cbgpPeer2LastError";
        }
      }
    }

    container object-2 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2State {
        type leafref {
          path "/CISCO-BGP4-MIB:CISCO-BGP4-MIB/CISCO-BGP4-MIB:cbgpPeer2Table/CISCO-BGP4-MIB:cbgpPeer2Entry/CISCO-BGP4-MIB:cbgpPeer2State";
        }
      }
    }

    container object-3 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2LastErrorTxt {
        type leafref {
          path "/CISCO-BGP4-MIB:CISCO-BGP4-MIB/CISCO-BGP4-MIB:cbgpPeer2Table/CISCO-BGP4-MIB:cbgpPeer2Entry/CISCO-BGP4-MIB:cbgpPeer2LastErrorTxt";
        }
      }
    }

    container object-4 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2PrevState {
        type leafref {
          path "/CISCO-BGP4-MIB:CISCO-BGP4-MIB/CISCO-BGP4-MIB:cbgpPeer2Table/CISCO-BGP4-MIB:cbgpPeer2Entry/CISCO-BGP4-MIB:cbgpPeer2PrevState";
        }
      }
    }
  }

  notification cbgpPeer2BackwardTransition {
    description
     "The cbgpPeer2BackwardTransition notification is
      generated when the BGP FSM moves from a higher numbered
      state to a lower numbered state.";
    smiv2:oid "1.3.6.1.4.1.9.9.187.0.8";

    container object-1 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2LastError {
        type leafref {
          path "/CISCO-BGP4-MIB:CISCO-BGP4-MIB/CISCO-BGP4-MIB:cbgpPeer2Table/CISCO-BGP4-MIB:cbgpPeer2Entry/CISCO-BGP4-MIB:cbgpPeer2LastError";
        }
      }
    }

    container object-2 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2State {
        type leafref {
          path "/CISCO-BGP4-MIB:CISCO-BGP4-MIB/CISCO-BGP4-MIB:cbgpPeer2Table/CISCO-BGP4-MIB:cbgpPeer2Entry/CISCO-BGP4-MIB:cbgpPeer2State";
        }
      }
    }

    container object-3 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2LastErrorTxt {
        type leafref {
          path "/CISCO-BGP4-MIB:CISCO-BGP4-MIB/CISCO-BGP4-MIB:cbgpPeer2Table/CISCO-BGP4-MIB:cbgpPeer2Entry/CISCO-BGP4-MIB:cbgpPeer2LastErrorTxt";
        }
      }
    }

    container object-4 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2PrevState {
        type leafref {
          path "/CISCO-BGP4-MIB:CISCO-BGP4-MIB/CISCO-BGP4-MIB:cbgpPeer2Table/CISCO-BGP4-MIB:cbgpPeer2Entry/CISCO-BGP4-MIB:cbgpPeer2PrevState";
        }
      }
    }
  }

  notification cbgpPeer2PrefixThresholdExceeded {
    description
     "The cbgpPeer2PrefixThresholdExceeded notification is
      generated when prefix count exceeds the configured
      warning threshold on a session for an address
      family.";
    smiv2:oid "1.3.6.1.4.1.9.9.187.0.9";

    container object-1 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2AddrFamilyAfi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilyAfi";
        }
      }

      leaf cbgpPeer2AddrFamilySafi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilySafi";
        }
      }

      leaf cbgpPeer2PrefixAdminLimit {
        type leafref {
          path "/CISCO-BGP4-MIB:CISCO-BGP4-MIB/CISCO-BGP4-MIB:cbgpPeer2AddrFamilyPrefixTable/CISCO-BGP4-MIB:cbgpPeer2AddrFamilyPrefixEntry/CISCO-BGP4-MIB:cbgpPeer2PrefixAdminLimit";
        }
      }
    }

    container object-2 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2AddrFamilyAfi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilyAfi";
        }
      }

      leaf cbgpPeer2AddrFamilySafi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilySafi";
        }
      }

      leaf cbgpPeer2PrefixThreshold {
        type leafref {
          path "/CISCO-BGP4-MIB:CISCO-BGP4-MIB/CISCO-BGP4-MIB:cbgpPeer2AddrFamilyPrefixTable/CISCO-BGP4-MIB:cbgpPeer2AddrFamilyPrefixEntry/CISCO-BGP4-MIB:cbgpPeer2PrefixThreshold";
        }
      }
    }
  }

  notification cbgpPeer2PrefixThresholdClear {
    description
     "The cbgpPeer2PrefixThresholdClear notification is
      generated when prefix count drops below the configured
      clear threshold on a session for an address family once
      cbgpPeer2PrefixThresholdExceeded is generated.
      This will not be generated if the peer session goes down
      after the generation of cbgpPrefixThresholdExceeded.";
    smiv2:oid "1.3.6.1.4.1.9.9.187.0.10";

    container object-1 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2AddrFamilyAfi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilyAfi";
        }
      }

      leaf cbgpPeer2AddrFamilySafi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilySafi";
        }
      }

      leaf cbgpPeer2PrefixAdminLimit {
        type leafref {
          path "/CISCO-BGP4-MIB:CISCO-BGP4-MIB/CISCO-BGP4-MIB:cbgpPeer2AddrFamilyPrefixTable/CISCO-BGP4-MIB:cbgpPeer2AddrFamilyPrefixEntry/CISCO-BGP4-MIB:cbgpPeer2PrefixAdminLimit";
        }
      }
    }

    container object-2 {

      leaf cbgpPeer2Type {
        type leafref {
          path "/CISCO-BGP4-MIB:CISCO-BGP4-MIB/CISCO-BGP4-MIB:cbgpPeer2Table/CISCO-BGP4-MIB:cbgpPeer2Entry/CISCO-BGP4-MIB:cbgpPeer2Type";
        }
      }

      leaf cbgpPeer2RemoteAddr {
        type leafref {
          path "/CISCO-BGP4-MIB:CISCO-BGP4-MIB/CISCO-BGP4-MIB:cbgpPeer2Table/CISCO-BGP4-MIB:cbgpPeer2Entry/CISCO-BGP4-MIB:cbgpPeer2RemoteAddr";
        }
      }

      leaf cbgpPeer2AddrFamilyAfi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilyAfi";
        }
      }

      leaf cbgpPeer2AddrFamilySafi {
        type leafref {
          path "/CISCO-BGP4-MIB:CISCO-BGP4-MIB/CISCO-BGP4-MIB:cbgpPeer2AddrFamilyTable/CISCO-BGP4-MIB:cbgpPeer2AddrFamilyEntry/CISCO-BGP4-MIB:cbgpPeer2AddrFamilySafi";
        }
      }

      leaf cbgpPeer2PrefixClearThreshold {
        type leafref {
          path "/CISCO-BGP4-MIB:CISCO-BGP4-MIB/CISCO-BGP4-MIB:cbgpPeer2AddrFamilyPrefixTable/CISCO-BGP4-MIB:cbgpPeer2AddrFamilyPrefixEntry/CISCO-BGP4-MIB:cbgpPeer2PrefixClearThreshold";
        }
      }
    }
  }

  smiv2:alias "ciscoBgp4MIB" {
    smiv2:oid "1.3.6.1.4.1.9.9.187";
  }

  smiv2:alias "ciscoBgp4NotifyPrefix" {
    smiv2:oid "1.3.6.1.4.1.9.9.187.0";
  }

  smiv2:alias "ciscoBgp4MIBObjects" {
    smiv2:oid "1.3.6.1.4.1.9.9.187.1";
  }

  smiv2:alias "cbgpRoute" {
    smiv2:oid "1.3.6.1.4.1.9.9.187.1.1";
  }

  smiv2:alias "cbgpPeer" {
    smiv2:oid "1.3.6.1.4.1.9.9.187.1.2";
  }

  smiv2:alias "cbgpGlobal" {
    smiv2:oid "1.3.6.1.4.1.9.9.187.1.3";
  }

  smiv2:alias "ciscoBgp4NotificationPrefix" {
    smiv2:oid "1.3.6.1.4.1.9.9.187.2";
  }

  smiv2:alias "ciscoBgp4MIBConformance" {
    smiv2:oid "1.3.6.1.4.1.9.9.187.3";
  }

  smiv2:alias "ciscoBgp4MIBCompliances" {
    smiv2:oid "1.3.6.1.4.1.9.9.187.3.1";
  }

  smiv2:alias "ciscoBgp4MIBGroups" {
    smiv2:oid "1.3.6.1.4.1.9.9.187.3.2";
  }

}
