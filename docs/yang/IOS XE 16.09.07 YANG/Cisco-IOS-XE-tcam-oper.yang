module Cisco-IOS-XE-tcam-oper {
  yang-version 1;
  namespace "http://cisco.com/ns/yang/Cisco-IOS-XE-tcam-oper";
  prefix tcam-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for ASIC TCAM Memory Utilization Statistics.
     Copyright (c) 2016-2017 by Cisco Systems, Inc.
     All rights reserved.";

  revision 2017-06-06 {
    description
      "Initial revision";
    reference "1.0.0";
  }

  grouping tcam-oper-key {
    description
      "Key Asic Number and Protocol Entry Name";
    leaf asic-no {
      type uint8 {
        range "0 .. 8";
      }
      description
        "Asic Number of Switch";
    }
    leaf name {
      type string;
      description
        "Protocol Name";
    }
  }

  grouping tcam-utils {
    description
      "FED ASIC TCAM Utilization Statistics";
    leaf hash-entries-max {
      type uint32;
      description
        "Maximum Hash Entries";
    }
    leaf tcam-entries-max {
      type uint32;
      description
        "Maximum Tcam Entries";
    }
    leaf hash-entries-used {
      type uint32;
      description
        "Hash Entries Used";
    }
    leaf tcam-entries-used {
      type uint32;
      description
        "Tcam Entries Used";
    }
  }

  container tcam-details {
    config false;
    description
      "ASIC TCAM Memory Statistics";
    list tcam-detail {
      key "asic-no name";
      description
        "FED ASIC TCAM Utilization";
      uses tcam-ios-xe-oper:tcam-oper-key;
      uses tcam-ios-xe-oper:tcam-utils;
    }
  }
}
