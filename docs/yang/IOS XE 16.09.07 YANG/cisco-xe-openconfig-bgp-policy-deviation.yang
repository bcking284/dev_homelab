module cisco-xe-openconfig-bgp-policy-deviation {
  // namespace
  namespace "http://cisco.com/ns/yang/cisco-xe-bgp-policy-deviation";

  prefix cisco-oc-bgp-pol-dev;

  import openconfig-routing-policy {
    prefix oc-rpol;
  }
  import openconfig-bgp-policy {
    prefix oc-bgp-pol;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-bgp-policy module.
     Copyright (c) 2017 by Cisco Systems, Inc.
     All rights reserved.";

  revision 2017-07-24 {
    description
      "Initial Revision";

    reference
      "RFC 6020: YANG - A Data Modeling Language for the
       Network Configuration Protocol (NETCONF)";
  }



 deviation "/oc-rpol:routing-policy/oc-rpol:policy-definitions/oc-rpol:policy-definition/oc-rpol:statements/oc-rpol:statement/oc-rpol:actions/oc-bgp-pol:bgp-actions/oc-bgp-pol:set-community/oc-bgp-pol:reference" {
        deviate not-supported;
        description  "Not supported on IOS-XE.";
      }

 deviation "/oc-rpol:routing-policy/oc-rpol:policy-definitions/oc-rpol:policy-definition/oc-rpol:statements/oc-rpol:statement/oc-rpol:actions/oc-bgp-pol:bgp-actions/oc-bgp-pol:set-ext-community/oc-bgp-pol:reference" {
        deviate not-supported;
        description  "Not supported on IOS-XE.";
      }


 deviation "/oc-rpol:routing-policy/oc-rpol:policy-definitions/oc-rpol:policy-definition/oc-rpol:statements/oc-rpol:statement/oc-rpol:actions/oc-bgp-pol:bgp-actions/oc-bgp-pol:state/oc-bgp-pol:set-local-pref" {
        deviate not-supported;
        description  "Not supported on IOS-XE 16.7.1.";
      }

 deviation "/oc-rpol:routing-policy/oc-rpol:policy-definitions/oc-rpol:policy-definition/oc-rpol:statements/oc-rpol:statement/oc-rpol:actions/oc-bgp-pol:bgp-actions/oc-bgp-pol:state/oc-bgp-pol:set-med" {
        deviate not-supported;
        description  "Not supported on IOS-XE 16.7.1.";
      }

 deviation "/oc-rpol:routing-policy/oc-rpol:policy-definitions/oc-rpol:policy-definition/oc-rpol:statements/oc-rpol:statement/oc-rpol:actions/oc-bgp-pol:bgp-actions/oc-bgp-pol:state/oc-bgp-pol:set-next-hop" {
        deviate not-supported;
        description  "Not supported on IOS-XE 16.7.1.";
      }


 deviation "/oc-rpol:routing-policy/oc-rpol:policy-definitions/oc-rpol:policy-definition/oc-rpol:statements/oc-rpol:statement/oc-rpol:actions/oc-bgp-pol:bgp-actions/oc-bgp-pol:state/oc-bgp-pol:set-route-origin" {
        deviate not-supported;
        description  "Not supported on IOS-XE 16.7.1.";
      }



  deviation "/oc-rpol:routing-policy/oc-rpol:policy-definitions/oc-rpol:policy-definition/oc-rpol:statements/oc-rpol:statement/oc-rpol:conditions/oc-bgp-pol:bgp-conditions/oc-bgp-pol:as-path-length" {
        deviate not-supported;
        description  "Not supported on IOS-XE 16.7.1.";
      }

 deviation "/oc-rpol:routing-policy/oc-rpol:policy-definitions/oc-rpol:policy-definition/oc-rpol:statements/oc-rpol:statement/oc-rpol:conditions/oc-bgp-pol:bgp-conditions/oc-bgp-pol:community-count" {
        deviate not-supported;
        description  "Not supported on IOS-XE 16.7.1.";
      }


  deviation "/oc-rpol:routing-policy/oc-rpol:policy-definitions/oc-rpol:policy-definition/oc-rpol:statements/oc-rpol:statement/oc-rpol:conditions/oc-bgp-pol:bgp-conditions/oc-bgp-pol:config/oc-bgp-pol:afi-safi-in" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:config/oc-bgp-pol:local-pref-eq" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:config/oc-bgp-pol:med-eq" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:config/oc-bgp-pol:next-hop-in" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:config/oc-bgp-pol:origin-eq" {
        deviate not-supported;
        description  "Not supported on IOS-XE 16.7.1.";
      }


 deviation "/oc-rpol:routing-policy/oc-rpol:policy-definitions/oc-rpol:policy-definition/oc-rpol:statements/oc-rpol:statement/oc-rpol:conditions/oc-bgp-pol:bgp-conditions/oc-bgp-pol:state/oc-bgp-pol:afi-safi-in" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:state/oc-bgp-pol:local-pref-eq" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:state/oc-bgp-pol:med-eq" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:state/oc-bgp-pol:next-hop-in" {
        deviate not-supported;
        description  "Not supported on IOS-XE 16.7.1.";
      }

  deviation "/oc-rpol:routing-policy/oc-rpol:policy-definitions/oc-rpol:policy-definition/oc-rpol:statements/oc-rpol:statement/oc-rpol:conditions/oc-bgp-pol:bgp-conditions/oc-bgp-pol:state/oc-bgp-pol:origin-eq" {
        deviate not-supported;
        description  "Not supported on IOS-XE 16.7.1.";
      }

  deviation "/oc-rpol:routing-policy/oc-rpol:defined-sets/oc-bgp-pol:bgp-defined-sets/oc-bgp-pol:ext-community-sets/oc-bgp-pol:ext-community-set/oc-bgp-pol:config/oc-bgp-pol:ext-community-member" {
        deviate add {
             min-elements 1;
           }
      }

}
