module Cisco-IOS-XE-wireless-mcast-oper {
  yang-version 1;
  namespace "http://cisco.com/ns/yang/Cisco-IOS-XE-wireless-mcast-oper";
  prefix wireless-mcast-oper;

  import Cisco-IOS-XE-wireless-enum-types {
    prefix wireless-enum-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for wireless multicast operational data.
     Copyright (c) 2018 by Cisco Systems, Inc.
     All rights reserved.";

  revision 2018-08-15 {
    description
      "- Add Fabric multicast oper yang
       - Change Multicast over Multicast to ipv4 and ipv6 specific";
    reference "2.0.0";
  }
  revision 2018-01-29 {
    description
      "Initial revision";
    reference "1.0.0";
  }

  grouping mcast-client-entry {
    description
      "Multicast client entries";
    leaf vlan {
      type uint16;
      description
        "Multicast client vlan";
    }
    leaf mgid {
      type uint16;
      description
        "Multicast client mgid";
    }
    leaf used {
      type uint8;
      description
        "Multicast client entry used";
    }
    leaf source {
      type inet:ip-address;
      description
        "Multicast client source IP address";
    }
    leaf group {
      type inet:ip-address;
      description
        "Multicast client group IP address";
    }
    leaf client-status {
      type wireless-enum-types:enm-mcast-client-status;
      description
        "Multicast client status";
    }
    leaf qos {
      type wireless-enum-types:media-stream-qos;
      description
        "Multicast client QOS";
    }
  }

  grouping ewlc-multicast-oper-data {
    description
      "Multicast operational data";
    leaf ms-mac-address {
      type yang:mac-address;
      description
        "Client mac address";
    }
    leaf client-ip {
      type inet:ip-address;
      description
        "Client IP address";
    }
    leaf capwap-iif-id {
      type uint64;
      description
        "Client capwap IIF ID";
    }
    leaf num-entries {
      type uint8;
      description
        "Number of currently filled entries";
    }
    list entry {
      max-elements "16";
      description
        "Multicast client entry";
      uses wireless-mcast-oper:mcast-client-entry;
    }
    leaf client-ipv6 {
      type inet:ip-address;
      description
        "Multicast client IPv6 address";
    }
    leaf epoch-count {
      type uint32;
      description
        "Multicast client epoch count";
    }
  }

  grouping mcast-mgid-client-entry {
    description
      "multicast mgid client entry";
    leaf client-mac-addr {
      type yang:mac-address;
      description
        "client mac address";
    }
    leaf client-ip-addr {
      type inet:ip-address;
      description
        "client ipv4 address";
    }
    leaf status {
      type string;
      description
        "status MC-only or MC-UC";
    }
    leaf client-status {
      type wireless-enum-types:enm-mcast-client-status;
      description
        "client status";
    }
    leaf epoch-count {
      type uint32;
      description
        "client epoch count";
    }
  }

  grouping mcast-mgid-entry {
    description
      "Multicast MGID entries";
    leaf mgid {
      type uint16;
      description
        "Multicast MGID";
    }
    leaf vlan {
      type uint16;
      description
        "Multicast VLAN";
    }
    leaf source {
      type inet:ip-address;
      description
        "Multicast source IP address";
    }
    leaf group {
      type inet:ip-address;
      description
        "Multicast group IP address";
    }
    leaf mc-only-num-clients {
      type uint32;
      description
        "Multicast number of MC-only clients";
    }
    leaf mc2uc-num-clients {
      type uint32;
      description
        "Multicast number of MC-UC clients";
    }
    leaf mc2uc-num-deny-clients {
      type uint32;
      description
        "Multicast number of MC-UC deny clients";
    }
    leaf mc2uc-num-pending-clients {
      type uint32;
      description
        "Multicat number of MC-UC pending client";
    }
    leaf epoch-count {
      type uint32;
      description
        "Multicast mgid epoch count";
    }
    list mcast-mgid-client-list {
      key "client-mac-addr";
      description
        "Multicast MGID client list";
      uses wireless-mcast-oper:mcast-mgid-client-entry;
    }
  }

  grouping mcast-flex-client-grp-info {
    description
      "Multicast flex client group information";
    leaf is-direct {
      type boolean;
      description
        "Stream is Multicast-Direct or Multicast";
    }
    leaf mcast-ip {
      type inet:ip-address;
      description
        "Multicast IP";
    }
    leaf stream-name {
      type string;
      description
        "Stream name";
    }
    leaf ap-mac {
      type yang:mac-address;
      description
        "AP MAC on which Multicast group is reported";
    }
  }

  grouping mcast-flex-client-info {
    description
      "Multicast flex client information";
    leaf client-mac {
      type yang:mac-address;
      description
        "Multicast flex client mac address";
    }
    leaf vlan-id {
      type uint16;
      description
        "Multicast flex client vlan";
    }
    list flex-mcast-client-group {
      key "mcast-ip";
      description
        "Flex multicast client group";
      uses wireless-mcast-oper:mcast-flex-client-grp-info;
    }
  }

  grouping mcast-fabric-client-grp-info {
    description
      "Multicast fabric client group information";
    leaf is-direct {
      type boolean;
      description
        "Stream is Multicast-Direct or Multicast";
    }
    leaf mcast-ip {
      type inet:ip-address;
      description
        "Multicast IP";
    }
    leaf stream-name {
      type string;
      description
        "Stream name";
    }
    leaf ap-mac {
      type yang:mac-address;
      description
        "AP MAC on which Multicast group is reported";
    }
  }

  grouping mcast-fabric-client-info {
    description
      "Multicast fabric client information";
    leaf client-mac {
      type yang:mac-address;
      description
        "Multicast fabric client mac address";
    }
    leaf vlan-id {
      type uint16;
      description
        "Multicast fabric client vlan";
    }
    list fabric-mcast-client-group {
      key "mcast-ip";
      description
        "Fabric multicast client group";
      uses wireless-mcast-oper:mcast-fabric-client-grp-info;
    }
  }

  grouping vlan-l2-mgid-op {
    description
      "vlan L2 MGID";
    leaf vlan-index {
      type uint32;
      description
        "Multicast vlan index";
    }
    leaf is-nonip-multicast-enabled {
      type boolean;
      description
        "Is non IP multicast enabled";
    }
    leaf is-broadcast-enable {
      type boolean;
      description
        "Is broadcast enabled";
    }
    leaf is-mgid-enabled {
      type boolean;
      description
        "Is MGID enabled";
    }
  }

  grouping bcast-cfg-op {
    description
      "Broadcast config";
    leaf policy-state {
      type wireless-enum-types:apf-qos-def-pm-create-status;
      description
        "Broadcast policy state";
    }
    leaf is-mdns-bridging {
      type boolean;
      description
        "Is MDNS bridging";
    }
  }

  grouping st-rrc-history-client-record-data-op {
    description
      "RRC history client record data";
    leaf user-timestamp {
      type yang:date-and-time;
      description
        "RRC history client user timestamp";
    }
    leaf timestamp {
      type yang:date-and-time;
      description
        "RRC history client timestamp";
    }
    leaf client-mac {
      type yang:mac-address;
      description
        "RRC history client mac address";
    }
    leaf decision {
      type uint32;
      description
        "RRC history client decision";
    }
    leaf reason-code {
      type uint32;
      description
        "RRC history client reason code";
    }
    leaf cac-enabled {
      type uint32;
      description
        "RRC history client CAC enabled";
    }
    leaf lrad-mac {
      type yang:mac-address;
      description
        "RRC history client LRAD mac address";
    }
    leaf slot-id {
      type uint32;
      description
        "RRC history client slot ID";
    }
    leaf stream-name {
      type string;
      description
        "RRC history client stream name";
    }
    leaf src-ip-address {
      type inet:ip-address;
      description
        "RRC history client source IP address";
    }
    leaf dst-ip-address {
      type inet:ip-address;
      description
        "RRC history client destination IP address";
    }
    leaf vap-id {
      type uint16;
      description
        "RRC history client WLAN ID";
    }
    leaf qos {
      type uint16;
      description
        "RRC history client QOS";
    }
    leaf cfg-stream-bw {
      type uint32;
      description
        "RRC history client config stream Bandwidth";
    }
    leaf current-rate {
      type uint32;
      description
        "RRC history client current rate";
    }
    leaf video-pkt-size {
      type uint32;
      description
        "RRC history client video packet size";
    }
    leaf curr-video-util {
      type uint32;
      description
        "RRC history client current video utilization";
    }
    leaf curr-voice-util {
      type uint32;
      description
        "RRC history client current voice utilization";
    }
    leaf curr-channel-util {
      type uint32;
      description
        "RRC history client current channel utilization";
    }
    leaf curr-queue-util {
      type uint32;
      description
        "RRC history client current queue utilization";
    }
    leaf curr-video-pps {
      type uint32;
      description
        "RRC history client current video PPS";
    }
    leaf video-delay-hist-severe {
      type uint32;
      description
        "RRC history client video delay history severe";
    }
    leaf video-pkt-loss-discard {
      type uint32;
      description
        "RRC history client video packet loss discard";
    }
    leaf video-pkt-loss-fail {
      type uint32;
      description
        "RRC history client video packet loss fail";
    }
    leaf num-video-streams {
      type uint32;
      description
        "RRC history number of video streams";
    }
  }

  grouping st-mstream-client-entry-key {
    description
      "Media-stream client entries";
    leaf name-stream {
      type string;
      description
        "Media-stream client name-stream";
    }
    leaf group-ip {
      type inet:ip-address;
      description
        "Media-stream client group IP address";
    }
    leaf cl-mac {
      type yang:mac-address;
      description
        "Media-stream client mac address";
    }
  }

  grouping st-rrc-sr-radio-record-key {
    description
      "RRC stream radio record";
    leaf ap-mac {
      type yang:mac-address;
      description
        "RRC stream radio AP mac address";
    }
    leaf slot-id {
      type uint32;
      description
        "RRC stream radio slot ID";
    }
  }

  grouping st-groups {
    description
      "Groups";
    leaf dest-ip {
      type inet:ip-address;
      description
        "Group destination IP address";
    }
    leaf no-of-streams {
      type uint16;
      description
        "Group number of streams";
    }
  }

  grouping st-rrc-sr-radio-record {
    description
      "RRC stream radio record";
    leaf last-re-rrc {
      type yang:date-and-time;
      description
        "RRC stream radio last re RRC";
    }
    leaf radio-type {
      type uint32;
      description
        "RRC stream radio type";
    }
    leaf initial-band-width {
      type uint32;
      description
        "RRC stream radio iinitial bandwidth";
    }
    leaf duplicated-band-width {
      type uint32;
      description
        "RRC stream radio duplicated bandwidth";
    }
    leaf number-of-admitted {
      type uint16;
      description
        "RRC stream radio number of admitted";
    }
    leaf timer-count {
      type uint32;
      description
        "RRC stream radio timer count";
    }
    leaf timer-max {
      type uint32;
      description
        "RRC stream radio timer max";
    }
    list rrc-groups-in-radio {
      key "dest-ip";
      description
        "RRC stream groups in radio";
      uses wireless-mcast-oper:st-groups;
    }
  }

  grouping st-rrc-stream-record-key {
    description
      "RRC stream records";
    leaf client-mac {
      type yang:mac-address;
      description
        "RRC stream client mac address";
    }
    leaf dest-ip {
      type inet:ip-address;
      description
        "RRC stream destination IP address";
    }
  }

  grouping st-rrc-stream-record-time {
    description
      "RRC stream record time";
    leaf last-updated {
      type yang:date-and-time;
      description
        "RRC stream last updated";
    }
    leaf client-mac {
      type yang:mac-address;
      description
        "RRC stream client mac address";
    }
    leaf dest-ip {
      type inet:ip-address;
      description
        "RRC stream destination IP address";
    }
  }

  grouping st-rrc-stream-record {
    description
      "RRC stream record";
    leaf source-ip {
      type inet:ip-address;
      description
        "RRC stream source IP address";
    }
    leaf priority {
      type uint16 {
        range "1 .. 8";
      }
      description
        "RRC stream priority";
    }
    leaf qos {
      type wireless-enum-types:media-stream-qos;
      description
        "RRC stream QOS";
    }
    leaf vap-id {
      type uint32;
      description
        "RRC stream VAP ID";
    }
    leaf vlan {
      type uint32;
      description
        "RRC stream VLAN";
    }
    leaf mgid {
      type uint32;
      description
        "RRC stream MGID";
    }
    leaf rerrc-enable {
      type boolean;
      description
        "RRC stream re-RRC enable";
    }
    leaf rerrc-drop {
      type boolean;
      description
        "RRC stream re-RRC drop";
    }
    leaf start-time {
      type yang:date-and-time;
      description
        "RRC stream start time";
    }
    leaf last-updated {
      type yang:date-and-time;
      description
        "RRC stream last updated";
    }
    leaf kbps-bandwidth {
      type uint32 {
        range "1 .. 35000";
      }
      description
        "RRC stream KBPS bandwidth";
    }
    leaf decision {
      type wireless-enum-types:media-stream-decision-status;
      description
        "RRC stream decision";
    }
    container rrc-radio-record {
      description
        "RRC stream radio record";
      uses wireless-mcast-oper:st-rrc-sr-radio-record-key;
    }
    leaf wlan-id {
      type uint16;
      description
        "RRC stream WLAN ID";
    }
    leaf stream-name {
      type string;
      description
        "RRC stream stream name";
    }
    leaf radio {
      type wireless-enum-types:enm-radio-type;
      description
        "RRC stream radio";
    }
    leaf ap-name {
      type string;
      description
        "RRC stream AP name";
    }
  }

  grouping mcast-config-info {
    description
      "Multicast config information";
    leaf src-ipv4-addr {
      type inet:ipv4-address;
      description
        "Multicast config source IP address";
    }
    leaf previous-mom-ipv4-addr {
      type inet:ipv4-address;
      description
        "Multicast config previous mom IP address";
    }
    leaf previous-iif-id {
      type uint32;
      description
        "Multicast config previous IIF ID";
    }
    leaf mom-ipv4-addr {
      type inet:ipv4-address;
      description
        "Multicast config mom IP address";
    }
    leaf iif-id {
      type uint32;
      description
        "Multicast config IIF ID";
    }
    leaf pmtu {
      type uint16;
      description
        "Multicast config PMTU";
    }
    leaf is-mcast-enabled {
      type boolean;
      description
        "Is multicast enabled";
    }
    leaf ios-tunnel-plumbed {
      type boolean;
      description
        "Multicast config IOS tunnel plumbed";
    }
    leaf if-unit {
      type uint32;
      description
        "Multicast config unit";
    }
    leaf slot-unit {
      type uint32;
      description
        "Multicast config slot unit";
    }
    leaf sw-if-number {
      type uint32;
      description
        "Multicast config software IF number";
    }
    leaf hw-if-index {
      type uint32;
      description
        "Multicast config hardware IF number";
    }
    leaf vlan-id {
      type uint16;
      description
        "Multicast MOM tunnel vlan 1id";
    }
    leaf is-bcast-enabled {
      type boolean;
      description
        "Is wireless broadcast enabled";
    }
    leaf is-nonipmcast-enabled {
      type boolean;
      description
        "Is non-IP multicast enabled";
    }
    leaf epoch-count {
      type uint32;
      description
        "Multicast config epoch count";
    }
    leaf src-ipv6-addr {
      type inet:ipv6-address;
      description
        "Multicast config source IP address";
    }
    leaf previous-mom-ipv6-addr {
      type inet:ipv6-address;
      description
        "Multicast config previous mom IP address";
    }
    leaf previous-v6-iif-id {
      type uint32;
      description
        "Multicast config previous IIF ID";
    }
    leaf mom-ipv6-addr {
      type inet:ipv6-address;
      description
        "Multicast config mom IP address";
    }
    leaf v6-iif-id {
      type uint32;
      description
        "Multicast config IIF ID";
    }
    leaf v6-pmtu {
      type uint16;
      description
        "Multicast config PMTU";
    }
    leaf ios-v6-tunnel-plumbed {
      type boolean;
      description
        "Multicast config IOS tunnel plumbed";
    }
    leaf v6-if-unit {
      type uint32;
      description
        "Multicast config unit";
    }
    leaf v6-slot-unit {
      type uint32;
      description
        "Multicast config slot unit";
    }
    leaf v6-sw-if-number {
      type uint32;
      description
        "Multicast config software IF number";
    }
    leaf v6-hw-if-index {
      type uint32;
      description
        "Multicast config hardware IF number";
    }
    leaf v6-vlan-id {
      type uint16;
      description
        "Multicast MOM tunnel vlan 1id";
    }
  }

  container mcast-oper-data {
    config false;
    description
      "Wireless multicast operational data";
    list rrc-history-client-record-data {
      key "user-timestamp";
      description
        "RRC history client record data";
      uses wireless-mcast-oper:st-rrc-history-client-record-data-op;
    }
    list rrc-sr-radio-record {
      key "ap-mac slot-id";
      description
        "RRC stream radio record";
      uses wireless-mcast-oper:st-rrc-sr-radio-record-key;
      uses wireless-mcast-oper:st-rrc-sr-radio-record;
    }
    list rrc-stream-record {
      key "name-stream group-ip cl-mac";
      description
        "RRC stream record";
      uses wireless-mcast-oper:st-rrc-stream-record;
      uses wireless-mcast-oper:st-mstream-client-entry-key;
      uses wireless-mcast-oper:st-rrc-stream-record-key;
    }
    list rrc-stream-admit-record {
      key "last-updated client-mac dest-ip";
      description
        "RRC stream admit record";
      uses wireless-mcast-oper:st-rrc-stream-record-time;
    }
    list rrc-stream-deny-record {
      key "last-updated client-mac dest-ip";
      description
        "RRC stream deny record";
      uses wireless-mcast-oper:st-rrc-stream-record-time;
    }
    list flex-mediastream-client-summary {
      key "client-mac";
      description
        "FLEX media-stream client summary";
      uses wireless-mcast-oper:mcast-flex-client-info;
    }
    list fabric-media-stream-client-summary {
      key "client-mac";
      description
        "Fabric media-stream client summary";
      uses wireless-mcast-oper:mcast-fabric-client-info;
    }
    list mcast-mgid-info {
      key "mgid";
      description
        "Multicast MGID information";
      uses wireless-mcast-oper:mcast-mgid-entry;
    }
    container mcast-config-info {
      presence "mcast-config-info";
      description
        "Multicast config information";
      uses wireless-mcast-oper:mcast-config-info;
    }
    list vlan-l2-mgid-op {
      key "vlan-index";
      description
        "VLAN L2 MGID";
      uses wireless-mcast-oper:vlan-l2-mgid-op;
    }
    container bcast-cfg-op {
      presence "BcastCfg-op";
      description
        "Broadcast config";
      uses wireless-mcast-oper:bcast-cfg-op;
    }
    list multicast-oper-data {
      key "ms-mac-address";
      description
        "Multicast Operational data";
      uses wireless-mcast-oper:ewlc-multicast-oper-data;
    }
  }
}
