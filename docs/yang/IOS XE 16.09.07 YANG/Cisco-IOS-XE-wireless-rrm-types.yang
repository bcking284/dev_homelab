module Cisco-IOS-XE-wireless-rrm-types {
  yang-version 1;
  namespace "http://cisco.com/ns/yang/Cisco-IOS-XE-wireless-rrm-types";
  prefix wireless-rrm-types;

  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless rrm data types.
     Copyright (c) 2016-2018 by Cisco Systems, Inc.
     All rights reserved.";

  revision 2018-06-18 {
    description
      "Remove of grouping. List of Channel Numbers";
    reference "3.0.0";
  }
  revision 2018-01-24 {
    description
      "The first generally available version";
    reference "2.0.0";
  }
  revision 2017-05-05 {
    description
      "Initial revision";
    reference "1.0.0";
  }

  typedef enm-rrm-phy-type {
    type enumeration {
      enum "rrm-phy-80211b" {
        value 1;
        description
          "Represents the 802.11b/g interface type for this entry.";
      }
      enum "rrm-phy-80211a" {
        value 2;
        description
          "Represents the 802.11a/c interface type for this entry.";
      }
      enum "rrm-phy-80211xor" {
        value 3;
        description
          "Represents the 802.11abgn interface type for this entry.";
      }
    }
    description
      "This object uniquely represents the 802.11 interface type for this entry.";
  }

  typedef enm-rrm-ctrl-mode {
    type enumeration {
      enum "rrm-automatic-mode" {
        value 0;
        description
          "Represents group mode as Auto selection mode";
      }
      enum "rrm-run-once-mode" {
        value 1;
        description
          "Represents group mode as Run once selection mode";
      }
      enum "rrm-static-mode" {
        value 2;
        description
          "Represents group mode as Static selection mode";
      }
      enum "rrm-leader-mode" {
        value 3;
        description
          "Represents group mode as rf static leader";
      }
      enum "rrm-restart-mode" {
        value 4;
        description
          "Represents group mode as restart";
      }
    }
    description
      "This object represents current rf group mode";
  }

  typedef enm-ca-si-capable {
    type enumeration {
      enum "spectrum-mode-ca" {
        value 1;
        description
          "Represents the Access point is CA type for this entry.";
      }
      enum "spectrum-mode-si" {
        value 2;
        description
          "Represents the Access point is SI type for this entry.";
      }
      enum "spectrum-mode-invalid" {
        value 3;
        description
          "Represents the Access point is CA type for this entry.";
      }
    }
    description
      "This object uniquely represents the 802.11 interface type for this entry.";
  }

  grouping st-member-id {
    description
      "This object represents the rf group member identifier";
    leaf-list byte-var {
      type uint8;
      max-elements "6";
      ordered-by user;
      description
        "This value contains the ip address of member in the first four bytes and the last two bytes contains  the maximum number of Radios handled by the rf group leader";
    }
  }

  grouping st-group-id {
    description
      "This object represents the rf group identifier";
    leaf wlc-mac {
      type yang:mac-address;
      description
        "This value contains the rf group leader's ip address in the first four bytes and the last two bytes contains  the maximum number of Radios handled by the rf group leader";
    }
    leaf cnt {
      type uint16;
      description
        "This value contains a radom counter that is created every time the rf group initialises";
    }
  }

  grouping st-rrm-msg-seq {
    description
      "Field is used in rrm message retry mechanism";
    leaf seq-num {
      type uint32;
      description
        "Indicates rrm message sequence number";
    }
    leaf duplicate {
      type uint32;
      description
        "Indicates if the message received is duplicate of previously received message";
    }
  }

  grouping st-rrm-channel-list {
    description
      "This object value represents rrm channel list";
    leaf chan-cnt {
      type uint8;
      description
        "Represents the number of channels present in the list.";
    }
    leaf-list chans {
      type uint8;
      max-elements "64";
      ordered-by user;
      description
        "Represents array of channel numbers available in the list.";
    }
  }

  grouping st-rrm-channels-list {
    description
      "List of Channel Numbers";
    leaf-list channel {
      type uint8;
      max-elements "64";
      ordered-by user;
      description
        "Channel Number";
    }
  }

  grouping st-rrm-common-ctrl-confg {
    description
      "This object represents rrm common control config for various algorithms";
    leaf mode {
      type wireless-rrm-types:enm-rrm-ctrl-mode;
      description
        "Represents algorithms current mode";
    }
    leaf update-counter {
      type uint32;
      description
        "Indicates the number of times the corresponding algorithm has run";
    }
    leaf update-interval-sec {
      type uint32;
      description
        "Time interval before which the algorithm was run";
    }
    leaf contribution {
      type uint8;
      description
        "Contributing factors to the algorithm";
    }
  }

  grouping st-rrm-dpc-config {
    description
      "Represents rrm tpc algorithm related configs";
    container rf {
      description
        "Contains general configs that is applicable to all the algorithms";
      uses wireless-rrm-types:st-rrm-common-ctrl-confg;
    }
    leaf dpc-min-tx-power-limit {
      type int8;
      description
        "Minimum tx power that the tpc algorithm can assign to any radio";
    }
    leaf dpc-max-tx-power-limit {
      type int8;
      description
        "Maximum tx power that the tpc algorithm can assign to any radio";
    }
    leaf tx-power-control-threshold {
      type int8;
      description
        "Indicates tx power threshold for tpc alogorithm";
    }
  }
}
