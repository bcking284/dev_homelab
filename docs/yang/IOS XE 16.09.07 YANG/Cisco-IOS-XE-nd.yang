module Cisco-IOS-XE-nd {
  namespace "http://cisco.com/ns/yang/Cisco-IOS-XE-nd";
  prefix ios-nd;

  import Cisco-IOS-XE-native {
    prefix ios;
  }


  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Neighbor Discovery (ND) Yang model.
     Copyright (c) 2016-2018 by Cisco Systems, Inc.
     All rights reserved.";

  // =========================================================================
  // REVISION
  // =========================================================================
  revision 2018-07-26 {
     description
       "Added support for some interface ipv4 nd options";
  }

  revision 2017-11-27 {
     description
       "Added Change 25GE name";
  }

  revision 2017-11-14 {
    description
      "Add support for 40 and 100GE interfaces";
  }

  revision 2017-10-12 {
    description
      "Add support for command 'ipv6 nd suppress policy *'";
  }

  revision 2017-09-18 {
    description
      "This revision has changes for new 2gig interface addition";
 }

  revision 2017-08-16 {
    description
      "This revision has changes for new 5gig and 25gig interfaces addition";
  }

  revision 2017-04-07 {
    description
      "Add default-route";
  }

  revision 2017-02-07 {
    description
      "Initial revision";
  }

  grouping config-ipv6-nd-grouping {
    container inspection {
      description
        "Configure NDP Inspection";
      list policy {
        description
          "Configure a policy for feature NDP inspection";
        key "name-nd-inspection-policy" ;
        leaf name-nd-inspection-policy {
          type string;
        }
        container device-role {
          description
            "Sets the role of the device attached to the port";
          leaf host {
            description
              "Attached device is a host (default)";
            type empty;
          }
          leaf monitor {
            description
              "Attached device is a monitor/sniffer";
            type empty;
          }
          leaf router {
            description
              "Attached device is a route";
            type empty;
          }
          leaf switch {
            description "Attached device is a switch";
            type empty;
          }
        }
        leaf drop-unsecure {
          description "drop unsecure (3971) messages";
          type empty;
        }
        container limit {
          description "Specifies a limit";
          leaf address-count {
            description "Configure maximum address per port";
            type uint16 {
              range "1..10000";
            }
          }
        }
        container sec-level {
          description "Specifies a minimum sec-level";
          leaf minimum {
            description "Configure minimum sec-level";
            type uint8 {
              range "1..7";
            }
          }
        }
        container tracking {
          description "Override default tracking behavior";
          container disable {
            description "Tracking off";
            presence true;
            container stale-lifetime {
              description "Time entry is kept inactive before delete";
              leaf seconds {
                description "Seconds";
                type uint32 {
                  range "1..86400";
                }
              }
              leaf infinite {
                description "Keep in STALE forever";
                type empty;
              }
            }
          }
          container enable {
            description "Tracking on";
            presence true;
            container reachable-lifetime {
              description "Time entry is kept REACHABLE";
              leaf seconds {
                description "Seconds";
                type uint32 {
                  range "1..86400";
                }
              }
              leaf infinite {
                description "Keep in REACHABLE forever";
                type empty;
              }
            }
          }
        }
        leaf trusted-port {
          description "setup trusted port";
          type empty;
        }
        container validate {
          description
            "specific validation";
          leaf source-mac {
            description
              "check source mac against link-layer-address";
            type empty;
          }
        }
      }
    }
    container cache {
      description
        "Cache entry";
      container expire {
        description
          "Expiry time for ND entries";
        leaf time {
          type uint16;
        }
        leaf refresh {
          description
            "Automatically refresh entry";
          type empty;
        }
      }
    }
    container raguard {
      description
        "Configure RA guard";
      list policy {
        description
          "Configure a policy for feature RA guard";
        key "raguard-policy-name" ;
        leaf raguard-policy-name{
          type string;
        }
        container device-role {
          description "Sets the role of the device attached to the port";
          leaf host {
            description "Attached device is a host (default)";
            type empty;
          }
          leaf monitor {
            description "Attached device is a monitor/sniffer";
            type empty;
          }
          leaf router {
            description "Attached device is a router";
            type empty;
          }
          leaf switch {
            description "Attached device is a switch";
            type empty;
          }
        }
        container hop-limit {
          description
            "Enable verification of the advertised Hop count limit";
          leaf maximum {
            description
              "Maximum hop count value allowed";
            type uint8 {
              range "1..255";
            }
          }
          leaf minimum {
            description
              "Minimum hop count value allowed";
            type uint8 {
              range "1..255";
            }
          }
        }
        leaf trusted-port {
          description
            "setup trusted port";
          type empty;
        }
      }
      leaf attach-policy {
        description
          "Configure a policy for feature RA guard";
        type string;
      }
    }
    container default-route {
      list vrf {
        ordered-by user;
        key "word";
        leaf word {
	  type string;
        }
        leaf limit {
          type uint8 {
            range "0..5";
          }
        }
      }
      leaf limit {
        type uint8 {
          range "0..5";
        }
      }
    }
    container suppress {
      description
        "Configure ND multicast suppress";
      list policy {
        description
          "Configure a policy for feature nd suppress";
        key "nd-suppress-policy-name";
        leaf nd-suppress-policy-name {
          type string;
        }
        // submode CLIs will be modelled later.
      }
    }
  }

  grouping config-interface-ipv6-nd-grouping {
    container raguard {
      description
        "Configure RA guard on the interface";
      leaf attach-policy {
        description
          "Apply a policy for feature RA guard";
        type string;
      }
    }
    container autoconfig {
      description
        "Obtain address using autoconfiguration";
        leaf default-route {
          description
            "Insert default route";
          type empty;
        }
        leaf prefix {
          description
            "Insert auto-configured prefix";
          type empty;
        }
    }

    leaf managed-config-flag {
      description
        "Use DHCP for IPv6 address configuration";
      type empty;
    }

    leaf other-config-flag {
      description
        "Hosts should use DHCP for non-address config";
      type empty;
    }

    leaf router-preference {
      description
        "Set default router preference value";
      type enumeration {
        enum "High";
        enum "Medium";
        enum "Low";
      }
      default "Medium";
    }

    container prefix {
      description
        "Configure IPv6 Routing Prefix Advertisement";
      list ipv6-prefix-list {
        description
          "IPv6 prefix x:x::y/<z>";
        key ipv6-prefix;
        leaf ipv6-prefix {
          type ios-types:ipv6-prefix;
        }
        leaf no-advertise {
          description
            "Do not advertise prefix";
          type empty;
        }
      }
    }

    container ra {
      description
        "IPv6 nd router alert configuration";
      container suppress {
        description
          "Suppress IPv6 router-alert configuration";
        presence "true";
        leaf all {
          description
            "Suppress all IPv6 RA";
          type empty;
        }
      }
    }
  }

  /////////////////////////////////////////////////////////
  // ipv6 / nd
  /////////////////////////////////////////////////////////
  augment "/ios:native/ios:ipv6/ios:nd" {
    //nd
    uses config-ipv6-nd-grouping;
  }

  /////////////////////////////////////////////////////////
  // interface * ipv6 nd
  /////////////////////////////////////////////////////////
  augment "/ios:native/ios:interface/ios:FastEthernet/ios:ipv6/ios:nd" {
    //interface ipv6 nd
    uses config-interface-ipv6-nd-grouping;
  }
  augment "/ios:native/ios:interface/ios:GigabitEthernet/ios:ipv6/ios:nd" {
    uses config-interface-ipv6-nd-grouping;
  }

  augment "/ios:native/ios:interface/ios:TenGigabitEthernet/ios:ipv6/ios:nd" {
    uses config-interface-ipv6-nd-grouping;
  }

  augment "/ios:native/ios:interface/ios:FiveGigabitEthernet/ios:ipv6/ios:nd" {
    uses config-interface-ipv6-nd-grouping;
  }

  augment "/ios:native/ios:interface/ios:TwentyFiveGigE/ios:ipv6/ios:nd" {
    uses config-interface-ipv6-nd-grouping;
  }

  augment "/ios:native/ios:interface/ios:TwoGigabitEthernet/ios:ipv6/ios:nd" {
    uses config-interface-ipv6-nd-grouping;
  }

  augment "/ios:native/ios:interface/ios:FortyGigabitEthernet/ios:ipv6/ios:nd" {
    uses config-interface-ipv6-nd-grouping;
  }

  augment "/ios:native/ios:interface/ios:HundredGigE/ios:ipv6/ios:nd" {
    uses config-interface-ipv6-nd-grouping;
  }

  augment "/ios:native/ios:interface/ios:Port-channel/ios:ipv6/ios:nd" {
    uses config-interface-ipv6-nd-grouping;
  }

  augment "/ios:native/ios:interface/ios:Loopback/ios:ipv6/ios:nd" {
    uses config-interface-ipv6-nd-grouping;
  }

  augment "/ios:native/ios:interface/ios:Tunnel/ios:ipv6/ios:nd" {
    uses config-interface-ipv6-nd-grouping;
  }

  augment "/ios:native/ios:interface/ios:vasileft/ios:ipv6/ios:nd" {
    uses config-interface-ipv6-nd-grouping;
  }

  augment "/ios:native/ios:interface/ios:vasiright/ios:ipv6/ios:nd" {
    uses config-interface-ipv6-nd-grouping;
  }
} //module
