module Cisco-IOS-XE-ppp {
  namespace "http://cisco.com/ns/yang/Cisco-IOS-XE-ppp";
  prefix ios-ppp;

  import ietf-inet-types {
    prefix inet;
  }

  import Cisco-IOS-XE-native {
    prefix ios;
  }


  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Point-to-Point Protocol (PPP) Yang model.
     Copyright (c) 2016-2018 by Cisco Systems, Inc.
     All rights reserved.";

  // =========================================================================
  // REVISION
  // =========================================================================
  revision 2018-04-16 {
    description
      "added ppp pap conatiner";
  }
  revision 2018-02-03 {
    description
      "reorder the CLIs, when deleting ppp config under interface serial";
  }
  revision 2017-11-29 {
    description
      "Add disable node for ppp multilink fragment disable";
  }
  revision 2017-02-07 {
    description
      "Initial revision";
  }


  grouping config-ppp-grouping {
    container packet {
      description
        "Configure control packet rate throttling";
      leaf throttle {
        description
          "Configure control packet rate throttling";
        type uint32 {
          range "1..100000";
        }
      }
      leaf allow_time {
        type uint32 {
          range "1..3600";
        }
      }
      leaf block_time {
        type uint32 {
          range "2..3600";
        }
      }
    }
  }

  grouping config-multilink-grouping {
    leaf bundle-name {
      description
        "Select method for naming multilink bundles";
      type enumeration {
        enum "authenticated";
        enum "both";
        enum "endpoint";
        enum "rfc";
      }
    }
    leaf virtual-template {
      description
        "virtual-template interface";
      type uint16 {
        range "1..4095";
      }
    }
  }

  grouping config-interface-p2p-grouping {
    // interface * / ppp
    container ppp {
      description
        "Point-to-Point Protocol";
      leaf accounting {
        description
          "Set PPP network accounting method";
        type union {
          type string;
          type enumeration {
            enum "default";
          }
        }
      }
      // interface * /ppp chap
      container chap {
        description
          "Set CHAP authentication parameters";
        leaf hostname {
          description
            "Set alternate CHAP hostname";
          type string;
        }
        container challenge-length {
          description
            "Challenge Length for CHAP";
          
          leaf minimum {
            description
              "Minimum length for CHAP challenge";
            type uint8 {
              range "16..63";
            }
          }
          leaf maximum {
            description
              "Maximum length for CHAP challenge";
            when "../minimum";  
            type uint8 {
              range "16..63";
            }
          }
        }
        container password {
          description
            "Set default CHAP password";
          
          leaf enryption-type {
            description 
              "Encryption type (0=not yet encrypted) (7=encrypted) password";
            type enumeration {
              enum "0";
              enum "7";
            }
          }
          leaf ppp-auth-password {
            description 
              "Default PPP authentication password";
            type string;
          }
        }
      }
      // interface * /ppp pap
      container pap {
        description
          "Set PAP authentication parameters";
        container refuse {
          description 
            "Refuse to authenticate using PAP";
          presence "true";
          leaf callin {
            description
              "Refuse to authenticate on incoming call only";
            type empty;
          }
        }
        container sent-username {
          description
            "Set Outbound PAP username";
          container username {
            description
              "Outbound PAP username";
            
            leaf username-string {
              description
                "Outbound PAP username";
              type string;
            }
            leaf password {
              description
                "Set outbound PAP password";
              type empty;
            }
            leaf enryption-type {
              description 
                "Encryption type (0=not yet encrypted) (7=encrypted) password";
              when "../password";
              type enumeration {
                enum "0";
                enum "7";
              }
            }
            leaf ppp-auth-password {
              description 
                "Outbound PAP password";
              when "../password";
              type string;
            }
          }
        }
        leaf wait {
          description
            "Wait for caller to authenticate first";
          type empty;
        }
      }
      // interface * / ppp authentication
      container authentication {
        description
          "Set PPP link authentication method";
        leaf method {
          type enumeration {
            enum "chap";
            enum "eap";
            enum "ms-chap";
            enum "ms-chap-v2";
            enum "pap";
          }
        }
        leaf list-name {
          type string;
        }
        leaf chap {
          description
            "Challenge Handshake Authentication Protocol (CHAP)";
          when "not(../method = 'chap')" {
          }
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          when "not(../method = 'eap')" {
          }
          type empty;
        }
        leaf ms-chap {
          description
            "Microsoft Challenge Handshake Authentication Protocol (MS-CHAP)";
          when "not(../method = 'ms-chap')" {
          }
          type empty;
        }
        leaf ms-chap-v2 {
          description
            "Microsoft CHAP Version 2 (MS-CHAP-V2)";
          when "not(../method = 'ms-chap-v2')" {
          }
          type empty;
        }
        leaf one-time {
          description
            "Allow use of username*OTP for one-time passwords";
          type empty;
        }
        leaf optional {
          description
            "Allow peer to refuse to authenticate";
          type empty;
        }
        leaf pap {
          description
            "Password Authentication Protocol (PAP)";
          when "not(../method = 'pap')" {
          }
          type empty;
        }
      }
      // interface * / ppp authorization
      leaf authorization {
        description
          "Set PPP network authorization method";
        type union {
          type string;
          type enumeration {
            enum "default";
          }
        }
      }
      // interface * / ppp ipcp
      container ipcp {
        description
          "Set IPCP negotiation options";
        container dns {
          description
            "Specify DNS negotiation options";
          container primary {
            description
              "Primary DNS IP address";
            
            leaf primary-dns-address {
              description
                "Primary DNS IP address";
              type inet:ipv4-address;

            }
            leaf secondary-dns-address {
              description
                "Secondary DNS IP address";
              type inet:ipv4-address;
            }
            leaf aaa {
              description
                "Use DNS data from AAA";
              type empty;
            }
            leaf accept {
              description
                "Accept any non zero DNS address";
              type empty;
            }
          }
          leaf accept {
            description
              "Accept any non zero DNS address";
            type empty;
          }
          leaf reject {
            description
              "Reject negotiations with the peer";
            type empty;
          }
          container request {
            description
              "Request server addresses from peer";
            presence "true";
            leaf accept {
              description
                "Accept any non zero DNS address";
              type empty;
            }
          }
        }
        container wins {
          description
            "Specify WINS negotiation options";
          container primary {
            description
              "Primary WINS IP address";
            
            leaf primary-wins-address {
              description
                "Primary WINS IP address";
              type inet:ipv4-address;

            }
            leaf secondary-wins-address {
              description
                "Secondary WINS IP address";
              type inet:ipv4-address;
            }
            leaf aaa {
              description
                "Use WINS data from AAA";
              type empty;
            }
            leaf accept {
              description
                "Accept any non zero WINS address";
              type empty;
            }
          }
          leaf accept {
            description
              "Accept any non zero WINS address";
            type empty;
          }
          leaf reject {
            description
              "Reject negotiations with the peer";
            type empty;
          }
          container request {
            description
              "Request server addresses from peer";
            presence "true";
            leaf accept {
              description
                "Accept any non zero WINS address";
              type empty;
            }
          }
        }
      }
      // interface * / ppp multilink
      container multilink {
        description
          "Make interface multilink capable";
        presence "true";
        container links {
          description
            "Specify the limits on the number of links in a bundle";
          container minimum {
            description
              "Minimum number of links desired in the bundle";
            
            leaf minimum-value {
              type uint8;
            }
            leaf mandatory {
              description
                "Disable network layer until minimum number of links is reach";
              type empty;
            }
          }
        }
        // interface * / ppp multilink group
        leaf group {
          description
            "Put interface in a multilink bundle";
          type uint32 {
            range "1..2147483647";
          }
        }
        // interface * / ppp multilink endpoint
        container endpoint {
          description
            "Configure the local Endpoint Discriminator";
          leaf string {
            description
              "Use specified string";
            type string;
          }
        }
        // interface * / ppp multilink fragment
        container fragment {
          description
            "Specify fragmentation parameters";
          container delay {
            description
              "Specify the maximum delay for each fragment";
            
            leaf delay-value {
              type uint16 {
                range "0..1000";
              }
            }
            leaf additional-delay-value {
              type uint16 {
                range "1..999";
              }
            }
          }
          leaf disable {
            description
              "Suppress multilink fragmentation when possible";
            type empty;
          }
        }
        
        leaf interleave {
          description
            "Allow interleaving of small packets with fragments";
          type empty;
        }
      }
    }
  }
  /////////////////////////////////////////////////////////
  // native / ppp
  /////////////////////////////////////////////////////////
  augment "/ios:native/ios:ppp" {
    uses config-ppp-grouping;
  }

  /////////////////////////////////////////////////////////
  // native / multilink
  /////////////////////////////////////////////////////////
  augment "/ios:native/ios:multilink" {
    uses config-multilink-grouping {
      if-feature ios-features:multilink;
    }    
  }

  /////////////////////////////////////////////////////////
  // native / interface
  /////////////////////////////////////////////////////////
  augment "/ios:native/ios:interface/ios:Multilink" {
      uses config-interface-p2p-grouping {
        if-feature ios-features:multilink;
      } 
  }

  augment "/ios:native/ios:interface/ios:Serial" {
      uses config-interface-p2p-grouping {
        if-feature ios-features:multilink;
      }    
  }

  augment "/ios:native/ios:interface/ios:Virtual-Template" {
      uses config-interface-p2p-grouping {
        if-feature ios-features:multilink;
      }
  }

  augment "/ios:native/ios:interface/ios:Dialer" {
      uses config-interface-p2p-grouping {
        if-feature ios-features:multilink;
      }   
  }

} //module
