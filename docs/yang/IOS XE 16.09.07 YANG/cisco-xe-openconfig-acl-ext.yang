module cisco-xe-openconfig-acl-ext{

  yang-version "1";

  // namespace
  namespace "http://cisco.com/ns/yang/cisco-xe-openconfig-acl-ext";

  prefix "oc-acl-cisco";

  import openconfig-packet-match-types { prefix "oc-pkt-match-types";}
  import openconfig-acl { prefix oc-acl; }
  import ietf-inet-types { prefix inet; }


  // import some basic types
  import openconfig-extensions { prefix oc-ext; }
  import tailf-common { prefix tailf; }


  // meta
  organization "Cisco";

  contact
    "www.cisco.com";

  description
    "Cisco augmentation to oc-acl model.";

  oc-ext:openconfig-version "1.0.2";

  revision "2017-03-30" {
    description
      "Added support for ip and ipv6 ACEs";
  }

  // Add IP and IPV6 as protocol options for ACEs model

  identity IP {
    base oc-pkt-match-types:IP_PROTOCOL;
    description
      "IP protocol";
  }
  identity IPV6 {
    base oc-pkt-match-types:IP_PROTOCOL;
    description
      "IPV6 protocol";
  }

  // Augment to add ip-version leaf for acl type

//  augment "/oc-acl:acl/oc-acl:acl-sets/oc-acl:acl-set" +
//            "/oc-acl:config" {
//    leaf acl-type {
//      type inet:ip-version;
//      description
//        "The type of the access-list set";
//    }
//  }
}
