module Cisco-IOS-XE-wireless-mobility-oper {
  yang-version 1;
  namespace "http://cisco.com/ns/yang/Cisco-IOS-XE-wireless-mobility-oper";
  prefix wireless-mobility-oper;

  import Cisco-IOS-XE-wireless-mobility-types {
    prefix wireless-mobility-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless mobility operational data.
     Copyright (c) 2016-2018 by Cisco Systems, Inc.
     All rights reserved.";

  revision 2018-09-06 {
    description
      "- Added Units to leaves carrying timestamps
       - Added roam and delete handoff statistics in mobility event statistics
       - Added roam and handoff stats in mobility peer stats";
    reference "4.0.0";
  }
  revision 2018-03-22 {
    description
      "Table renames";
    reference "3.0.0";
  }
  revision 2018-01-24 {
    description
      "The first generally available version";
    reference "2.0.0";
  }
  revision 2017-05-05 {
    description
      "Initial revision";
    reference "1.0.0";
  }

  typedef mobility-ap-list-source-type {
    type enumeration {
      enum "self" {
        value 0;
        description
          "AP entry connected locally";
      }
      enum "mobility-group" {
        value 1;
        description
          "AP entry from other controllers in mobility group";
      }
    }
    description
      "AP entries connected locally or from the other
       controllers in the mobility group";
  }

  grouping mm-mobility-stats {
    description
      "Global mobility statistics";
    leaf mcfsm-invalid-events {
      type uint32;
      description
        "Invalid events of fsm";
    }
    leaf mcfsm-internal-error {
      type uint32;
      description
        "Internal errors in mobility state machine";
    }
    leaf mcfsm-delete-internal-error {
      type uint32;
      description
        "Internal delete errors that have occurred in mobility state machine";
    }
    leaf mcfsm-roam-internal-error {
      type uint32;
      description
        "Internal roam errors that have occurred in mobility state machine";
    }
    leaf event-data-allocs {
      type uint32;
      description
        "Event data allocation failure count";
    }
    leaf event-data-frees {
      type uint32;
      description
        "Event data freed count";
    }
    leaf inter-wncd-roam-count {
      type uint32;
      description
        "Inter process roam count";
    }
    leaf l2-roam-count {
      type uint32;
      description
        "Client L2 roam count";
    }
    leaf l3-roam-count {
      type uint32;
      description
        "Client L3 roam count";
    }
    leaf flex-client-roaming-count {
      type uint32;
      description
        "Flex client roam count within the box";
    }
    leaf joined-as-local {
      type uint32;
      description
        "Client joined as local to the box";
    }
    leaf joined-as-foreign {
      type uint32;
      description
        "Client joined as foreign to the box";
    }
    leaf joined-as-export-foreign {
      type uint32;
      description
        "Client joined as export foreign to the box";
    }
    leaf joined-as-export-anchor {
      type uint32;
      description
        "Client joined as export anchor to the box";
    }
    leaf local-to-anchor {
      type uint32;
      description
        "Count of clients whose state changes from local to 
         anchor";
    }
    leaf anchor-to-local {
      type uint32;
      description
        "Count of clients whose state changes from anchor to 
         local";
    }
    leaf foreign-to-local {
      type uint32;
      description
        "Count of clients whose state changes from foreign to 
         local";
    }
    leaf local-delete {
      type uint32;
      description
        "Count of clients where the deletion was local 
         decision";
    }
    leaf remote-delete {
      type uint32;
      description
        "Count of clients where the deletion was triggered
         by the remote mobility peer";
    }
    leaf fsm-set-allocs {
      type uint32;
      description
        "Number of mobility FSM instances allocated";
    }
    leaf fsm-set-frees {
      type uint32;
      description
        "Number of mobility FSM instances freed";
    }
    leaf timer-allocs {
      type uint32;
      description
        "Number of timer allocs";
    }
    leaf timer-frees {
      type uint32;
      description
        "Number of timer frees";
    }
    leaf timer-starts {
      type uint32;
      description
        "Number of timer starts";
    }
    leaf timer-stops {
      type uint32;
      description
        "Number of timer stops";
    }
    leaf exp-anc-req-sent {
      type uint32;
      description
        "Number of export anchor request sent";
    }
    leaf exp-anc-req-received {
      type uint32;
      description
        "Number of export anchor request received";
    }
    leaf exp-anc-resp-ok-sent {
      type uint32;
      description
        "Number of export anchor response ok sent";
    }
    leaf exp-anc-resp-generic-deny-sent {
      type uint32;
      description
        "Number of export anchor response generic deny sent";
    }
    leaf exp-anc-resp-client-blacklisted-sent {
      type uint32;
      description
        "Number of export anchor response deny sent due to client blacklisted";
    }
    leaf exp-anc-resp-limit-reached-sent {
      type uint32;
      description
        "Number of export anchor response deny sent due to client limit reached";
    }
    leaf exp-anc-resp-profile-mismatch-sent {
      type uint32;
      description
        "Number of export anchor response deny sent due to profile mismatch";
    }
    leaf exp-anc-resp-ok-received {
      type uint32;
      description
        "Number of export anchor response ok received";
    }
    leaf exp-anc-resp-generic-deny-received {
      type uint32;
      description
        "Number of export anchor response generic deny received";
    }
    leaf exp-anc-resp-client-blacklisted-received {
      type uint32;
      description
        "Number of export anchor response deny received due to client blacklisted";
    }
    leaf exp-anc-resp-limit-reached-received {
      type uint32;
      description
        "Number of export anchor response deny received due to client limit reached";
    }
    leaf exp-anc-resp-profile-mismatch-received {
      type uint32;
      description
        "Number of export anchor response deny received due to profile mismatch";
    }
    leaf exp-anc-resp-unknown-received {
      type uint32;
      description
        "Number of export anchor response deny with unknown reasons";
    }
    leaf handoff-sent-ms-blacklist {
      type uint32;
      description
        "Total number of handoff status blacklisted client sent";
    }
    leaf handoff-received-ms-blacklist {
      type uint32;
      description
        "Total number of handoff status blacklisted client
         received";
    }
  }

  grouping mm-global-msg-stats {
    description
      "Global mobility message statistics";
    list ipc-stats {
      max-elements "255";
      description
        "Array for IPC statistics of CAPWAP messages";
      uses wireless-mobility-types:mm-msg-stats;
    }
    list dgram-stats {
      max-elements "255";
      description
        "Array for datagram statistics of CAPWAP messages";
      uses wireless-mobility-types:mm-msg-stats;
    }
    list dgram-data-stats {
      max-elements "255";
      description
        "Array for datagram data statistics of CAPWAP messages";
      uses wireless-mobility-types:mm-msg-stats;
    }
  }

  grouping mm-global-stats {
    description
      "Mobility global statistics";
    container mm-mblty-stats {
      description
        "MM mobility event statistics";
      uses wireless-mobility-oper:mm-mobility-stats;
    }
  }

  grouping mm-client-stats {
    description
      "Mobility and message statistics for client";
    leaf client-mac {
      type yang:mac-address;
      description
        "Ethernet MAC of client";
    }
    container mm-mblty-stats {
      description
        "Mobility statistics for client";
      uses wireless-mobility-oper:mm-mobility-stats;
    }
    list ipc-stats {
      max-elements "255";
      description
        "Array for IPC statistics of CAPWAP messages";
      uses wireless-mobility-types:mm-msg-stats;
    }
    list dgram-stats {
      max-elements "255";
      description
        "Array for datagram statistics of CAPWAP messages";
      uses wireless-mobility-types:mm-msg-stats;
    }
  }

  grouping mobility-client-params {
    description
      "Mobility client parameters";
    leaf client-mac {
      type yang:mac-address;
      description
        "Client MAC address";
    }
    leaf client-ifid {
      type uint32;
      description
        "Client IFID";
    }
    leaf owner-instance {
      type uint8;
      description
        "Owner instance for mobility client";
    }
    leaf assoc-time-stamp {
      type yang:date-and-time;
      units "seconds";
      description
        "Client association time";
    }
    leaf mobility-state {
      type wireless-mobility-types:mm-mobility-state;
      description
        "Mobility state";
    }
    leaf client-role {
      type wireless-mobility-types:mm-client-role;
      description
        "Client Role";
    }
    leaf client-type {
      type wireless-mobility-types:mm-client-type;
      description
        "Client Type";
    }
    leaf client-mode {
      type wireless-mobility-types:mm-client-mode;
      description
        "Mobility client mode";
    }
    leaf client-roam-type {
      type wireless-mobility-types:mm-client-roam-type;
      description
        "Mobility client roam type";
    }
    leaf peer-ip {
      type inet:ip-address;
      description
        "Peer IP";
    }
    leaf entry-last-update-time {
      type yang:date-and-time;
      units "seconds";
      description
        "Mobility client last update time";
    }
    leaf client-create-time {
      type yang:date-and-time;
      units "seconds";
      description
        "Mobility client create time";
    }
    leaf wlan-profile {
      type string;
      description
        "Mobility client wlan profile";
    }
  }

  grouping wlan-info-entry {
    description
      "Wlan info";
    leaf wlan-profile {
      type string;
      description
        "Name of the wlan profile";
    }
    leaf curr-clients-count {
      type uint32;
      description
        "Number of clients connected to the wlan";
    }
  }

  grouping capability {
    description
      "Architecture, DTLS and Tunnel capability for mobility";
    leaf arch {
      type wireless-mobility-types:arch-capability;
      description
        "Architecture capability for mobility";
    }
    leaf dtls {
      type wireless-mobility-types:dtls-capability;
      description
        "DTLS capability for mobility";
    }
    leaf tunnel {
      type wireless-mobility-types:tunnel-capability;
      description
        "Tunnel capability for mobility";
    }
  }

  grouping ping-id {
    description
      "Ping ID for keepalive state";
    leaf id {
      type uint32;
      description
        "ID for the ping ID of corresponding keepalive state";
    }
  }

  grouping keepalive-state {
    description
      "Keepalive status for peer and link";
    leaf peer-responses-in-interval {
      type uint8;
      description
        "Responses for peer (in interval)";
    }
    leaf intervals-without-response {
      type uint8;
      description
        "Peer intervals without response";
    }
    list ping-ids {
      description
        "Ping IDs for peer";
      uses wireless-mobility-oper:ping-id;
    }
    leaf peer-status {
      type boolean;
      description
        "Keepalive status of peer";
    }
    leaf link-status {
      type boolean;
      description
        "Keepalive status of link";
    }
    leaf packet-failure-cnt {
      type uint32;
      description
        "Packet failure counter";
    }
    leaf flaps-cnt {
      type uint32;
      description
        "Link flap counter";
    }
    leaf last-flap-timestamp {
      type yang:date-and-time;
      units "seconds";
      description
        "Last flap timestamp";
    }
  }

  grouping mobility-dtls-info {
    description
      "Mobility DTLS information";
    leaf connection-status {
      type wireless-mobility-types:mm-dtls-status;
      description
        "Mobility DTLS status of connection";
    }
    leaf num-link-down-intervals {
      type uint8;
      description
        "Number for keepalive intervals for which link is 
         down";
    }
  }

  grouping policy-id {
    description
      "Policy Id for anchor management";
    leaf id {
      type uint32;
      description
        "ID for the policy of the anchor";
    }
  }

  grouping mm-node-stats {
    description
      "Mobility Node Statistics";
    leaf l2-roam-cnt {
      type uint32;
      description
        "Mobility l2 roam count";
    }
    leaf l3-roam-cnt {
      type uint32;
      description
        "Mobility l3 roam count";
    }
    leaf handoff-sent-ok {
      type uint32;
      description
        "Successfull handoffs sent to the peer";
    }
    leaf handoff-recvd-ok {
      type uint32;
      description
        "Successfull handoffd received from the peer";
    }
    leaf handoff-recvd-grp-mismatch {
      type uint32;
      description
        "Handoff receive group mismatch";
    }
    leaf handoff-recvd-ms-unknown {
      type uint32;
      description
        "Handoff receive ms unknown";
    }
    leaf handoff-recvd-ms-blacklist {
      type uint32;
      description
        "Handoff receive ms blacklist";
    }
    leaf handoff-recvd-ms-ssid {
      type uint32;
      description
        "Handoff receive ms ssid";
    }
    leaf handoff-recvd-deny {
      type uint32;
      description
        "Handoff receive deny";
    }
    leaf handoff-sent-grp-mismatch {
      type uint32;
      description
        "Handoff send group mismatch";
    }
    leaf handoff-sent-ms-unknown {
      type uint32;
      description
        "Handoff send ms unknown";
    }
    leaf handoff-sent-ms-blacklist {
      type uint32;
      description
        "Handoff send ms blacklist";
    }
    leaf handoff-sent-ms-ssid {
      type uint32;
      description
        "Handoff send ms ssid";
    }
    leaf handoff-sent-deny {
      type uint32;
      description
        "Handoff send deny";
    }
  }

  grouping mobility-node-list-entry {
    description
      "Entry for mobility node list";
    leaf node-ip {
      type inet:ip-address;
      description
        "Mobility node IP";
    }
    leaf nat-ip {
      type inet:ip-address;
      description
        "Mobility node NAT IP";
    }
    leaf node-mac-addr {
      type yang:mac-address;
      description
        "Mobility node MAC Address";
    }
    leaf ulink-status {
      type wireless-mobility-types:unified-link-status;
      description
        "Mobility node link status";
    }
    leaf tunnel-ifid {
      type uint32;
      description
        "Mobility node tunnel IFID";
    }
    leaf group-name {
      type string;
      description
        "Mobility node group name";
    }
    leaf seq-num {
      type uint32;
      description
        "Mobility node sequence number";
    }
    leaf num-clients {
      type uint32;
      description
        "Total number of clients at mobility node";
    }
    leaf tunnel-plumbed {
      type boolean;
      description
        "Tunnel plumbing status for mobility node";
    }
    leaf ios-tunnel-plumbed {
      type boolean;
      description
        "IOS Tunnel plumbing status for mobility node";
    }
    leaf pmtu {
      type uint32;
      units "bytes";
      description
        "PMTU for mobility node";
    }
    leaf pmtu-xid {
      type uint32;
      description
        "PMTU XID of mobility node";
    }
    list peer-capability {
      max-elements "2";
      description
        "Architecture, DTLS and Tunnel capability of peer for
         mobility node";
      uses wireless-mobility-oper:capability;
    }
    container ctrl-state {
      description
        "Control keepalive state for mobility node";
      uses wireless-mobility-oper:keepalive-state;
    }
    container data-state {
      description
        "Data keepalive state for mobility node";
      uses wireless-mobility-oper:keepalive-state;
    }
    leaf-list group-digest {
      type uint8;
      max-elements "16";
      ordered-by user;
      description
        "Group digest for mobility node";
    }
    leaf dtls-session-id {
      type uint64;
      description
        "DP dtls session id";
    }
    leaf data-dtls-session-id {
      type uint64;
      description
        "DP data dtls session id";
    }
    leaf link-connect-timestamp {
      type yang:date-and-time;
      units "seconds";
      description
        "Link connection timestamp for mobility node";
    }
    list dtls-info {
      max-elements "2";
      description
        "DTLS information for mobility node";
      uses wireless-mobility-oper:mobility-dtls-info;
    }
    leaf is-anchor {
      type boolean;
      description
        "flag to indicate whether node is anchor";
    }
    leaf is-anchor-full {
      type boolean;
      description
        "flag to indicate whether anchor is full";
    }
    leaf num-exported-clients {
      type uint32;
      description
        "Number of clients anchored to mobility node";
    }
    leaf num-imported-clients {
      type uint32;
      description
        "Number of anchored clients from  mobility node";
    }
    list policy-ids {
      description
        "Policy IDs";
      uses wireless-mobility-oper:policy-id;
    }
    leaf idb-info-unit {
      type uint32;
      description
        "Mobility IDB interface unit value";
    }
    leaf idb-info-slotunit {
      type uint32;
      description
        "Mobility IDB interface slotunit value";
    }
    leaf sw-if-number {
      type uint32;
      description
        "Mobility IDB interface if_number value";
    }
    leaf hw-if-index {
      type uint32;
      description
        "Mobility IDB interface hw_if_index value";
    }
    container node-stats {
      description
        "Statistics for mobility node";
      uses wireless-mobility-oper:mm-node-stats;
    }
  }

  grouping mm-sclient {
    description
      "Mobility sclient";
    leaf client-mac {
      type yang:mac-address;
      description
        "Mobility sclient MAC address";
    }
    leaf username {
      type string;
      description
        "Mobility sclient user name";
    }
    leaf password {
      type string;
      description
        "Mobility sclient password";
    }
    leaf vap-ssid {
      type string;
      description
        "VAP SSID for mobility sclient";
    }
    leaf sclient-timestamp {
      type yang:date-and-time;
      units "seconds";
      description
        "Mobility sclient timestamp";
    }
  }

  grouping mesh-ap-channel-list-peer {
    description
      "Represents a list of mobility members from which bridge group name and channel is learnt";
    leaf node-ip {
      type inet:ip-address;
      description
        "Represents IP Address of the mobility member from which bridge group name and channel is learnt";
    }
  }

  grouping mesh-ap-channel-list {
    description
      "Represent list of bridge group name and channel learnt from mobility members";
    leaf local-wncd-info {
      type uint32;
      description
        "Represents the information about WNCD instance from which bridge group name and channel is learnt";
    }
    list mm-ap-channel-list-peer-ip {
      key "node-ip";
      description
        "Represents Ip Address of the member controller frm which bridge group name and channel information is learnt";
      uses wireless-mobility-oper:mesh-ap-channel-list-peer;
    }
  }

  grouping mesh-ap-channel-peer-list-info {
    description
      "Represents if the Ip Address bridge group name Channel entry information";
    leaf stale {
      type uint8;
      description
        "Represents if the Ip address bridge group name channel entry is stale";
    }
  }

  grouping mobility-ap-list-entry {
    description
      "Each entry in this table provides information about AP
       that is reported by this MC or its peer MC or its MA.";
    leaf mac-addr {
      type yang:mac-address;
      description
        "Reported AP's mac address.";
    }
    leaf name {
      type string;
      description
        "Reported AP's name";
    }
    leaf controller-ip {
      type inet:ip-address;
      description
        "Reporting device's IP address";
    }
    leaf source {
      type wireless-mobility-oper:mobility-ap-list-source-type;
      description
        "Reporting device's IP address type";
    }
  }

  grouping mobility-ap-list-peer-entry {
    description
      "Each entry in this table provides information on total 
       number of APs that is reported by this MC or its peer 
       MC or its MA";
    leaf peer-ip {
      type inet:ip-address;
      description
        "Reporting device's IP address";
    }
    leaf ap-count {
      type uint32;
      description
        "Total number of APs reported by this device: this 
         MC, or its peer MC or its MA";
    }
    leaf source {
      type wireless-mobility-oper:mobility-ap-list-source-type;
      description
        "Reporting device's IP address type";
    }
    leaf seq-number {
      type uint8;
      description
        "Reporting device's current update sequence number";
    }
    leaf last-seq-number {
      type uint8;
      description
        "Reporting device's last update sequence number";
    }
  }

  container mobility-oper-data {
    config false;
    description
      "Yang model for wireless mobility oper";
    container global-stats {
      presence "tbl-mm-global-stats";
      description
        "Table for global mobility statistics";
      uses wireless-mobility-oper:mm-global-stats;
    }
    container tbl-mm-global-msg-stats {
      presence "tbl-mm-global-msg-stats";
      description
        "Table for global mobility message statistics";
      uses wireless-mobility-oper:mm-global-msg-stats;
    }
    list client-parameters {
      key "client-mac";
      description
        "Each entry in this table provides information about
         one 802.11 LWAPP Mobility Clients on this MC";
      uses wireless-mobility-oper:mobility-client-params;
    }
    list ap-cache {
      key "mac-addr";
      description
        "Each entry in this table provides information about
         AP that is reported by this MC or its peer MC or its
         MA";
      uses wireless-mobility-oper:mobility-ap-list-entry;
    }
    list ap-peer-list {
      key "peer-ip";
      description
        "Each entry in this table provides information on 
         total number of APs that is reported by this MC or 
         its peer MC or its MA";
      uses wireless-mobility-oper:mobility-ap-list-peer-entry;
    }
    list mobility-client-stats {
      key "client-mac";
      description
        "Table for mobility and message statistics";
      uses wireless-mobility-oper:mm-client-stats;
    }
    list node-cache {
      key "node-ip";
      description
        "Table for mobility node cache";
      uses wireless-mobility-oper:mobility-node-list-entry;
    }
    list tbl-wlan-info {
      key "wlan-profile";
      description
        "Table for wlan info";
      uses wireless-mobility-oper:wlan-info-entry;
    }
    list sleeping-client-stats {
      key "client-mac";
      description
        "Mobility sclient";
      uses wireless-mobility-oper:mm-sclient;
    }
    list mm-ap-channel-list {
      key "bgn channel";
      description
        "Table for mobility subset channel list";
      uses wireless-types:bgn-channel-key;
      uses wireless-mobility-oper:mesh-ap-channel-list;
    }
    list mm-ap-channel-peer-list {
      key "node-ip bgn channel";
      description
        "Table for mobility subset channel list learnt from peers";
      uses wireless-types:ipaddr-bgn-channel-key;
      uses wireless-mobility-oper:mesh-ap-channel-peer-list-info;
    }
  }
}
