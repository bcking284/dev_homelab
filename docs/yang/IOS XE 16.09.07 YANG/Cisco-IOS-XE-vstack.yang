module Cisco-IOS-XE-vstack {
  namespace "http://cisco.com/ns/yang/Cisco-IOS-XE-vstack";
  prefix ios-vstack;

  import ietf-inet-types {
    prefix inet;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Cisco Smart Install (VSTACK) Yang model.
     Copyright (c) 2016 by Cisco Systems, Inc.
     All rights reserved.";

  // =========================================================================
  // REVISION
  // =========================================================================
  revision 2017-02-07 {
    description
      "Initial revision";
  }

  grouping config-vstack-grouping {
    container vstack {
      description "Configure vstack parameters and enable or disable SmartInstall";
      leaf director {
        description "Configure director's IP address";
        type inet:ipv4-address;
      }
    }
  }

  /////////////////////////////////////////////////////////
  // native / vstack
  /////////////////////////////////////////////////////////
  augment "/ios:native" {
    uses config-vstack-grouping;
  }
} //module
