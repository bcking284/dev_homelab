module Cisco-IOS-XE-platform-oper {
  yang-version 1;
  namespace "http://cisco.com/ns/yang/Cisco-IOS-XE-platform-oper";
  prefix platform-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of platform components.
     Copyright (c) 2016-2017 by Cisco Systems, Inc.
     All rights reserved.";

  revision 2017-10-11 {
    description
      "Enum name fix";
    reference "2.0.0";
  }
  revision 2017-02-06 {
    description
      "Initial revision";
    reference "1.0.0";
  }

  typedef platform-comp-type {
    type enumeration {
      enum "comp-chassis" {
        value 0;
      }
      enum "comp-backplane" {
        value 1;
      }
      enum "comp-power-supply" {
        value 2;
      }
      enum "comp-fan" {
        value 3;
      }
      enum "comp-sensor" {
        value 4;
      }
      enum "comp-module" {
        value 5;
      }
      enum "comp-linecard" {
        value 6;
      }
      enum "comp-port" {
        value 7;
      }
      enum "comp-cpu" {
        value 8;
      }
      enum "comp-operating-system" {
        value 9;
      }
      enum "comp-optical-channel" {
        value 10;
      }
      enum "comp-container" {
        value 11;
      }
    }
    description
      "Component Type";
  }

  typedef platform-prop-value-type {
    type enumeration {
      enum "property-string" {
        value 0;
      }
      enum "property-boolean" {
        value 1;
      }
      enum "property-int64" {
        value 2;
      }
      enum "property-uint64" {
        value 3;
      }
      enum "property-decimal64" {
        value 4;
      }
    }
    description
      "Property value type";
  }

  grouping platform-comp-temp {
    description
      "Temperature state data for device components";
    leaf temp-instant {
      type decimal64 {
        fraction-digits 2;
      }
      description
        "Instantaneous temperature value of a component";
    }
    leaf temp-avg {
      type decimal64 {
        fraction-digits 2;
      }
      description
        "Arithmetic mean value of the statistic over a
         sampling period";
    }
    leaf temp-max {
      type decimal64 {
        fraction-digits 2;
      }
      description
        "High water mark value of the statistic over a
         sampling period";
    }
    leaf temp-min {
      type decimal64 {
        fraction-digits 2;
      }
      description
        "Low water mark value of the statistic over a
         sampling period";
    }
  }

  grouping platform-property-value {
    description
      "Property values can take on a variety of types.
       Signed and unsigned integer types may be provided in smaller sizes,
       e.g., int8, uint16, etc.";
    choice property-value-choice {
      description
        "Value choice";
      case property-string {
        leaf string {
          type string;
          description
            "String property value";
        }
      }
      case property-boolean {
        leaf boolean {
          type boolean;
          description
            "Boolean property value";
        }
      }
      case property-int64 {
        leaf intsixfour {
          type int64;
          description
            "Integer64 property value";
        }
      }
      case property-uint64 {
        leaf uintsixfour {
          type uint64;
          description
            "Unsigned integer64 property value";
        }
      }
      case property-decimal64 {
        leaf decimal {
          type decimal64 {
            fraction-digits 2;
          }
          description
            "Decimal64 property value";
        }
      }
    }
  }

  grouping platform-state {
    description
      "Operational state data for device components";
    leaf type {
      type platform-ios-xe-oper:platform-comp-type;
      description
        "Type of component as identified by the system";
    }
    leaf id {
      type string;
      description
        "Unique identifier assigned to the component
         by the system";
    }
    leaf description {
      type string;
      description
        "System-supplied description of the component";
    }
    leaf mfg-name {
      type string;
      description
        "System-supplied identifier for the manufacturer of the
         component.  This data is particularly useful when a
         component manufacturer is different than the overall
         device vendor";
    }
    leaf version {
      type string;
      description
        "System-defined version string for a hardware, firmware,
         or software component";
    }
    leaf serial-no {
      type string;
      description
        "System-assigned serial number of the component";
    }
    leaf part-no {
      type string;
      description
        "System-assigned part number for the component.  This should
         be present in particular if the component is also an FRU
         (field replacable unit)";
    }
    container temp {
      description
        "Temperature in degrees Celsius of the component. Values include
         the instantaneous, average, minimum, and maximum statistics. If
         avg/min/max statistics are not supported, the target is expected
         to just supply the instant value";
      uses platform-ios-xe-oper:platform-comp-temp;
    }
  }

  grouping platform-component {
    description
      "Top-level grouping for components in the device inventory";
    leaf cname {
      type string;
      description
        "References component name";
    }
    container state {
      description
        "Operational state data for each component";
      uses platform-ios-xe-oper:platform-state;
    }
    container platform-properties {
      description
        "Platform component properties";
      list platform-property {
        key "name";
        description
          "List of platform component properties";
        uses platform-ios-xe-oper:platform-properties;
      }
    }
    container platform-subcomponents {
      description
        "Platform subcomponents";
      list platform-subcomponent {
        key "name";
        description
          "List of platform subcomponents";
        uses platform-ios-xe-oper:platform-subcomponents;
      }
    }
  }

  grouping platform-subcomponents {
    description
      "Platform subcomponents";
    leaf name {
      type string;
      description
        "Subcomponent name";
    }
  }

  grouping platform-properties {
    description
      "Top-level grouping";
    leaf name {
      type string;
      description
        "Property name";
    }
    container value {
      description
        "Property value";
      uses platform-ios-xe-oper:platform-property-value;
    }
    leaf configurable {
      type boolean;
      description
        "Indication of whether the property is user-configurable";
    }
  }

  container components {
    config false;
    description
      "Enclosing container for the components in the system";
    list component {
      key "cname";
      description
        "List of components, keyed by component name";
      uses platform-ios-xe-oper:platform-component;
    }
  }
}
